ALCATEL-NGOAW-BASE-MIB DEFINITIONS ::= BEGIN

IMPORTS
    MODULE-IDENTITY, OBJECT-IDENTITY, enterprises
FROM
    SNMPv2-SMI;


alcatelNGOAWBaseMIB MODULE-IDENTITY

    LAST-UPDATED  "201609010000Z"
    ORGANIZATION  "AL-Enterprise Inc."
    CONTACT-INFO
        "Please consult with Customer Service to ensure the most appropriate
         version of this document is used with the products in question:

                    AL-Enterprise Inc.
                   (Formerly Alcatel Internetworking, Incorporated)
                           26801 West Agoura Road
                        Agoura Hills, CA  91301-5122
                          United States Of America

        Telephone:               North America  +1 800 995 2696
                                 Latin America  +1 877 919 9526
								 Europe         +800 00200100 (Toll Free) or +1(650)385-2193
								 Asia Pacific: +65 6240 8484

                                 All Other      +1 818 878 4507

        Electronic Mail:         ebg_global_supportcenter@al-enterprise.com
        World Wide Web:          http://alcatel-lucent.com/wps/portal/enterprise
        File Transfer Protocol:  ftp://ftp.ind.alcatel.com/pub/products/mibs"

    DESCRIPTION
        "This module describes an authoritative enterprise-specific Simple
         Network Management Protocol (SNMP) Management Information Base (MIB):

             This module provides base definitions for modules
             developed to manage Alcatel-Lucent infrastructure products.

         The right to make changes in specification and other information
         contained in this document without prior notice is reserved.

         No liability shall be assumed for any incidental, indirect, special, or
         consequential damages whatsoever arising from or related to this
         document or the information contained herein.

         Vendors, end-users, and other interested parties are granted
         non-exclusive license to use this specification in connection with
         management of the products for which it is intended to be used.

                     Copyright (C) 2016 AL-Enterprise
                         ALL RIGHTS RESERVED WORLDWIDE"

    REVISION      "201609010000Z"
    DESCRIPTION
        "Branch for NGOAW wireless Enterprise devices under AL-Enterprise Corporate Private Enterprise Number."

    ::= { alcatel 802 }

alcatel OBJECT-IDENTITY
    STATUS current
    DESCRIPTION
        "Alcatel-Lucent Corporate Private Enterprise Number."
    ::= { enterprises 6486 }

alcatelNGOAWManagement OBJECT-IDENTITY
    STATUS current
    DESCRIPTION
        "AL-Enterprise NGOAW Management Branch."
    ::= { alcatelNGOAWBaseMIB 1 }

managementNGOAWHardware OBJECT-IDENTITY
    STATUS current
    DESCRIPTION
        "Hardware Feature Management Branch."
    ::= { alcatelNGOAWManagement 1 }


managementNGOAWSoftware OBJECT-IDENTITY
    STATUS current
    DESCRIPTION
        "Software Feature Management Branch."
    ::= { alcatelNGOAWManagement 2 }

managementNGOAWAgentCapabilities OBJECT-IDENTITY
    STATUS current
    DESCRIPTION
        "Notifications Related Management Branch."
    ::= { alcatelNGOAWManagement 4 }

hardwareNGOAWEntities OBJECT-IDENTITY
    STATUS current
    DESCRIPTION
        "Branch For Hardware Feature Related ENTITY-MIB Extensions."
    ::= { managementNGOAWHardware 1 }


hardwareNGOAWDevices OBJECT-IDENTITY
    STATUS current
    DESCRIPTION
        "Branch Where Object Indentifiers For Chassis And Modules Are Defined."
    ::= { managementNGOAWHardware 2 }


softwareNGOAWEntities OBJECT-IDENTITY
    STATUS current
    DESCRIPTION
        "Branch For Software Feature Related Extensions."
    ::= { managementNGOAWSoftware 1 }

softwareNGOAWServices OBJECT-IDENTITY
    STATUS current
    DESCRIPTION
        "Branch For Software Features Related to any service related extensions.
        Usually management for non AOS devices or software."
    ::= { managementNGOAWSoftware 2 }


END
