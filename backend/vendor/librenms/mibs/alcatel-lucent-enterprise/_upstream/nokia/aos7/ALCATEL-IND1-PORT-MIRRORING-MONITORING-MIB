ALCATEL-IND1-PORT-MIRRORING-MONITORING-MIB DEFINITIONS ::= BEGIN

IMPORTS
        OBJECT-TYPE,
        MODULE-IDENTITY,
        OBJECT-IDENTITY, Integer32,
        NOTIFICATION-TYPE              FROM SNMPv2-SMI
        MODULE-COMPLIANCE,
        OBJECT-GROUP,
        NOTIFICATION-GROUP             FROM SNMPv2-CONF
        TEXTUAL-CONVENTION,
        TruthValue,
        RowStatus                      FROM SNMPv2-TC
        SnmpAdminString                FROM SNMP-FRAMEWORK-MIB
        InterfaceIndex                 FROM IF-MIB
        softentIND1PortMirroringMonitoring              FROM ALCATEL-IND1-BASE
        sFlowFsEntry,
        sFlowCpEntry,
        SFlowInstance                  FROM SFLOW-MIB
        InetAddress,
        InetAddressType                FROM INET-ADDRESS-MIB;


        alcatelIND1PortMirrorMonitoringMIB MODULE-IDENTITY
            LAST-UPDATED "201911270000Z"
            ORGANIZATION "ALE USA Inc."
            CONTACT-INFO
             "Please consult with Customer Service to ensure the most appropriate
              version of this document is used with the products in question:

                              ALE USA Inc. Enterprise
                                26801 West Agoura Road
                             Agoura Hills, CA  91301-5122
                               United States Of America

             Telephone:          +1 800 995 2696

             Electronic Mail:    ebg_global_supportcenter@al-enterprise.com
             World Wide Web:     https://www.al-enterprise.com"

                DESCRIPTION
                        "This module describes an authoritative enterprise-specific Simple
             Network Management Protocol (SNMP) Management Information Base (MIB):

                 For the OmniSwitch Product Line
                 Port Mirroring and Monitoring for mirroring/monitoring session control

             The right to make changes in specification and other information
             contained in this document without prior notice is reserved.

             No liability shall be assumed for any incidental, indirect, special, or
             consequential damages whatsoever arising from or related to this
             document or the information contained herein.

             Vendors, end-users, and other interested parties are granted
             non-exclusive license to use this specification in connection with
             management of the products for which it is intended to be used.

                       Copyright (C) ALE USA Inc. 2014-2019
                       Copyright (C) 1995-2013 Alcatel-Lucent
                           ALL RIGHTS RESERVED WORLDWIDE"

        REVISION      "201911270000Z"
        DESCRIPTION
            "Updated the latest contact and Copyright information for ALE USA Inc."

        REVISION      "200704030000Z"
        DESCRIPTION
            "Addressing discrepancies with Alcatel Standard."
                ::= { softentIND1PortMirroringMonitoring 1}

-- xxxxxxxxxxxxxxxxxxxxxxxxxxxxxxxxxxxxxxxxxxxxxxxxxxxxxxxxxxxxxx

        alcatelIND1PortMirMonMIBNotifications OBJECT-IDENTITY
        STATUS current
        DESCRIPTION
                "Root For Port Mirroring and Monitoring
                Subsystem Managed Notifications."
                ::= { alcatelIND1PortMirrorMonitoringMIB 0 }

        alcatelIND1PortMirMonMIBObjects OBJECT-IDENTITY
        STATUS current
        DESCRIPTION
            "Branch For Port Mirroring and Monitoring
            Subsystem Managed Objects."
            ::= { alcatelIND1PortMirrorMonitoringMIB 1 }


    alcatelIND1PortMirMonMIBConformance OBJECT-IDENTITY
        STATUS current
        DESCRIPTION
            "Branch For Port Mirroring and Monitoring
            Subsystem Conformance Information."
            ::= { alcatelIND1PortMirrorMonitoringMIB 2 }


    alcatelIND1PortMirMonMIBGroups OBJECT-IDENTITY
        STATUS current
        DESCRIPTION
            "Branch For Port Mirroring and Monitoring
            Subsystem Units Of Conformance."
            ::= { alcatelIND1PortMirMonMIBConformance 1}


    alcatelIND1PortMirMonMIBCompliances OBJECT-IDENTITY
        STATUS current
        DESCRIPTION
            "Branch For Port Mirroring and Monitoring
            Subsystem Compliance Statements."
            ::= { alcatelIND1PortMirMonMIBConformance 2}

-- xxxxxxxxxxxxxxxxxxxxxxxxxxxxxxxxxxxxxxxxxxxxxxxxxxxxxxxxxxxxxx

        mirmonMirroring  OBJECT IDENTIFIER ::= { alcatelIND1PortMirMonMIBObjects 1 }

-- xxxxxxxxxxxxxxxxxxxxxxxxxxxxxxxxxxxxxxxxxxxxxxxxxxxxxxxxxxxxxx

mirrorTable  OBJECT-TYPE
            SYNTAX  SEQUENCE OF MirrorEntry
            MAX-ACCESS  not-accessible
            STATUS  current
            DESCRIPTION
                "A list of port mirroring instances."
            ::= { mirmonMirroring 1 }


mirrorEntry  OBJECT-TYPE
        SYNTAX  MirrorEntry
        MAX-ACCESS  not-accessible
        STATUS  current
        DESCRIPTION
                "A port  mirroring entry."
        INDEX { mirrorSessionNumber }
            ::= { mirrorTable 1 }


MirrorEntry ::= SEQUENCE {
        mirrorSessionNumber
                Integer32,
        mirrorMirroredIfindex
                InterfaceIndex,
        mirrorMirroringIfindex
                InterfaceIndex,
        mirrorStatus
                INTEGER,
        mirrorUnblockedVLAN
                Integer32,
        mirrorRowStatus
                RowStatus,
        mirrorDirection
                INTEGER,
        mirrorSessOperStatus
                INTEGER,
        mirrorTaggedVLAN
                Integer32,
        mirrorModeLoopback
                INTEGER
        }

mirrorSessionNumber OBJECT-TYPE
        SYNTAX  Integer32 (1..2147483647)
        MAX-ACCESS read-only
        STATUS current
        DESCRIPTION
                "Identifies a specific port mirroring instance."
           DEFVAL  { 1 }
           ::= { mirrorEntry 1 }

mirrorMirroredIfindex  OBJECT-TYPE
        SYNTAX  InterfaceIndex
        MAX-ACCESS  read-create
        STATUS deprecated
        DESCRIPTION
                " This variable is deprecated and value will be ignored. Please use mirrorSrcTable
                 to configure mirrored ports.
                The physical identification number for this mirroring port instance (mirrorred port)."
        ::= { mirrorEntry 2 }

mirrorMirroringIfindex  OBJECT-TYPE
        SYNTAX  InterfaceIndex
        MAX-ACCESS  read-create
        STATUS  deprecated
        DESCRIPTION
                " The physical identification number for this mirroring port instance (mirroring port)."
            ::= { mirrorEntry 3 }

mirrorStatus  OBJECT-TYPE
        SYNTAX  INTEGER {
                off (1),
                on (2)
        }
        MAX-ACCESS  read-create
        STATUS  current
        DESCRIPTION
                "Whether mirroring is enabled or disabled for this port.
                 Prior to enabling mirroring, or at the same time all other
                 read write values in this table for the same row must
                 be set to appropriate values, or defaults will be assumed."
            DEFVAL  { on }
            ::= { mirrorEntry 4 }



mirrorUnblockedVLAN OBJECT-TYPE
        SYNTAX  Integer32 (0..4094)
        MAX-ACCESS read-create
        STATUS current
        DESCRIPTION
                "A VLAN identifier which specifies the VLAN identifier that must remain unblocked no matter what is the output of the spanning tree algorithm.Value 0 indicates this parameter is not set"
           ::= { mirrorEntry 5 }



mirrorRowStatus OBJECT-TYPE
                SYNTAX  RowStatus
                MAX-ACCESS  read-create
                STATUS  current
                DESCRIPTION
                        "The status of this table entry.
                         "
           ::= { mirrorEntry 6 }

mirrorDirection  OBJECT-TYPE
        SYNTAX  INTEGER {
                inport (1),
                outport (2),
                bidirectional (3)
        }
        MAX-ACCESS  read-create
        STATUS  deprecated
        DESCRIPTION
                 " This variable is deprecated and the value will be ignored.
                 Please use mirrorSrcTable to set the direction of mirroring.
                        Direction of mirroring."
            DEFVAL  { bidirectional }
            ::= { mirrorEntry 7 }

mirrorSessOperStatus OBJECT-TYPE
        SYNTAX  INTEGER {
                off (1),
                on (2)
        }
        MAX-ACCESS  read-only
        STATUS  current
        DESCRIPTION
                "Whether mirroring session is active. "
        DEFVAL  { on }
            ::= { mirrorEntry 8 }

mirrorTaggedVLAN OBJECT-TYPE
        SYNTAX  Integer32 (0..4094)
        MAX-ACCESS read-create
        STATUS current
        DESCRIPTION
                "A VLAN identifier which specifies the VLAN identifier that must used to tag the mirrored packets going
out of the MTP for remote port mirroring .Value 0 indicates this parameter is not set"
           ::= { mirrorEntry 9 }

mirrorModeLoopback OBJECT-TYPE
        SYNTAX  INTEGER {
                enable (1),
                disable (2)
        }
        MAX-ACCESS  read-create
        STATUS  current
        DESCRIPTION
                 "To enable loopback mechanism on the destination port of the respective	 
                  remote port mirroring session. To disable the loopback mechanism, remove the session completely. "	 
    DEFVAL  { disable }
            ::= { mirrorEntry 10 }

-- xxxxxxxxxxxxxxxxxxx
-- Mirror Source Table
-- xxxxxxxxxxxxxxxxxxx


mirrorSrcTable  OBJECT-TYPE
            SYNTAX  SEQUENCE OF MirrorSrcEntry
            MAX-ACCESS  not-accessible
            STATUS  current
            DESCRIPTION
                "A list of port mirroring instances."
            ::= { mirmonMirroring 2 }


mirrorSrcEntry  OBJECT-TYPE
        SYNTAX  MirrorSrcEntry
        MAX-ACCESS  not-accessible
        STATUS  current
        DESCRIPTION
                "A port  mirroring entry."
        INDEX { mirrorSessionNumber, mirrorSrcMirroredIf }
            ::= { mirrorSrcTable 1 }


MirrorSrcEntry ::= SEQUENCE {
        mirrorSrcMirroredIf
                InterfaceIndex,
        mirrorSrcStatus
                INTEGER,
        mirrorSrcDirection
                INTEGER,
        mirrorSrcRowStatus
                RowStatus,
        mirrorSrcOperStatus
                INTEGER
        }

mirrorSrcMirroredIf  OBJECT-TYPE
        SYNTAX  InterfaceIndex
        MAX-ACCESS  read-only
        STATUS  current
        DESCRIPTION
                "The physical identification number for this mirroring port instance (mirrorred port)."
        ::= { mirrorSrcEntry 1 }

mirrorSrcStatus  OBJECT-TYPE
        SYNTAX  INTEGER {
                disable (1),
                enable (2)
        }
        MAX-ACCESS  read-create
        STATUS  current
        DESCRIPTION
                "Whether mirroring is enabled or disabled for this port.
                 Prior to enabling mirroring, or at the same time all other
                 read write values in this table for the same row must
                 be set to appropriate values, or defaults will be assumed."
            DEFVAL  { enable }
            ::= { mirrorSrcEntry 2 }

mirrorSrcDirection  OBJECT-TYPE
        SYNTAX  INTEGER {
                inport (1),
                outport (2),
                bidirectional (3)
        }
        MAX-ACCESS  read-create
        STATUS  current
        DESCRIPTION
                 "Direction of mirroring on the source port of this entry."
            DEFVAL  { bidirectional }
            ::= { mirrorSrcEntry 3 }

mirrorSrcRowStatus OBJECT-TYPE
                SYNTAX  RowStatus
                MAX-ACCESS  read-create
                STATUS  current
                DESCRIPTION
                        "The status of this table entry.Row Status to control creation,
                        modification and deletion of this entry. "
           ::= { mirrorSrcEntry 4 }

mirrorSrcOperStatus  OBJECT-TYPE
        SYNTAX  INTEGER {
                off (1),
                on (2)
        }
        MAX-ACCESS  read-only
        STATUS  current
        DESCRIPTION
                 "The mirroring operational status of this mirrored source. "
            DEFVAL  { on }
            ::= { mirrorSrcEntry 5 }

--xxxxxxxxxxxxxxxxxxxx
-- Mirror Destination table
--xxxxxxxxxxxxxxxxxxxx

mirrorDstTable  OBJECT-TYPE
            SYNTAX  SEQUENCE OF MirrorDstEntry
            MAX-ACCESS  not-accessible
            STATUS  current
            DESCRIPTION
                "A list of port mirroring instances."
            ::= { mirmonMirroring 3 }


mirrorDstEntry  OBJECT-TYPE
        SYNTAX  MirrorDstEntry
        MAX-ACCESS  not-accessible
        STATUS  current
        DESCRIPTION
                "A port  mirroring entry."
        INDEX { mirrorSessionNumber, mirrorDstMirroringIf }
            ::= { mirrorDstTable 1 }


MirrorDstEntry ::= SEQUENCE {
        mirrorDstMirroringIf
                InterfaceIndex,
        mirrorDstOperStatus
                INTEGER,
        mirrorDstAdminStatus
                INTEGER,
        mirrorDstRowStatus
                RowStatus,
        mirrorDstTagRemove
                TruthValue
        }

mirrorDstMirroringIf  OBJECT-TYPE
        SYNTAX  InterfaceIndex
        MAX-ACCESS  not-accessible
        STATUS  current
        DESCRIPTION
                "The physical identification number for this mirroring port instance (mirrorred port)."
        ::= { mirrorDstEntry 1 }

mirrorDstOperStatus  OBJECT-TYPE
        SYNTAX  INTEGER {
                off (1),
                on (2)
        }
        MAX-ACCESS  read-only
        STATUS  current
        DESCRIPTION
                 "The mirroring operational status of this mirrored Destination. "
            DEFVAL  { on }
            ::= { mirrorDstEntry 2 }

mirrorDstAdminStatus  OBJECT-TYPE
        SYNTAX  INTEGER {
                enable (1),
                disable (2)
        }
        MAX-ACCESS  read-create
        STATUS  current
        DESCRIPTION
                 "The mirroring admin status of mirrored destination. "
            DEFVAL  { disable }
            ::= { mirrorDstEntry 3 }

mirrorDstRowStatus OBJECT-TYPE
                SYNTAX  RowStatus
                MAX-ACCESS  read-create
                STATUS  current
                DESCRIPTION
                        "The status of this table entry.Row Status to control creation,
                        modification and deletion of this entry. "
           ::= { mirrorDstEntry 4 }

mirrorDstTagRemove OBJECT-TYPE
        SYNTAX  TruthValue
                MAX-ACCESS  read-create
                STATUS  current
                DESCRIPTION
                        "The mirroring tag-remove value of this mirrored destination."
                DEFVAL  { false }
           ::= { mirrorDstEntry 5 }

-- End of Mirror Destination Table





-- xxxxxxxxxxxxxxxxxxxxxxxxxxxxxxxxxxxxxxxxxxxxxxxxxxxxxxxxxxxxxx

        mirmonMonitoring  OBJECT IDENTIFIER ::= { alcatelIND1PortMirMonMIBObjects 2 }


-- xxxxxxxxxxxxxxxxxxxxxxxxxxxxxxxxxxxxxxxxxxxxxxxxxxxxxxxxxxxxxx


monitorTable OBJECT-TYPE
               SYNTAX  SEQUENCE OF MonitorEntry
               MAX-ACCESS  not-accessible
               STATUS  current
           DESCRIPTION
                       "A list of port monitoring instances."
                   ::= { mirmonMonitoring 1 }

       monitorEntry  OBJECT-TYPE
               SYNTAX  MonitorEntry
               MAX-ACCESS  not-accessible
               STATUS  current
               DESCRIPTION
                       "A port  monitoring entry."
                   INDEX { monitorSessionNumber }
                   ::= { monitorTable 1 }

       MonitorEntry ::= SEQUENCE {
               monitorSessionNumber
                       Integer32,
               monitorIfindex
                       InterfaceIndex,
               monitorFileStatus
                       INTEGER,
               monitorFileName
                       SnmpAdminString ,
               monitorFileSize
                       Integer32,
               monitorScreenStatus
                       INTEGER,
               monitorScreenLine
                       Integer32,
               monitorTrafficType
                       INTEGER,
               monitorStatus
                       INTEGER,
               monitorFileOverWrite
                         INTEGER,
               monitorDirection
                         INTEGER,
               monitorTimeout
                         Integer32,
               monitorRowStatus
                       RowStatus,
               monitorCaptureType
                       INTEGER

               }


       monitorSessionNumber OBJECT-TYPE
               SYNTAX  Integer32 (1..2147483647)
               MAX-ACCESS read-only
               STATUS current
               DESCRIPTION
                       "Identifies a specific port monitoring instance."
                  DEFVAL  { 1 }
                  ::= { monitorEntry 1 }

       monitorIfindex  OBJECT-TYPE
               SYNTAX  InterfaceIndex
               MAX-ACCESS  read-create
               STATUS deprecated 
               DESCRIPTION
                       "The physical identification number for this monitoring port instance."
                   DEFVAL  { 1 }
                   ::= { monitorEntry 2 }

       monitorFileStatus OBJECT-TYPE
               SYNTAX  INTEGER {
                       off (1),
                       on (2)
               }
               MAX-ACCESS read-create
               STATUS current
               DESCRIPTION
                       "The status of the file option of a monitoring port instance (default off)"
                   DEFVAL  { off }
                   ::= { monitorEntry 3 }

       monitorFileName  OBJECT-TYPE
               SYNTAX  SnmpAdminString(SIZE(0..63))
               MAX-ACCESS  read-create
               STATUS  current
               DESCRIPTION
                       "The name of the file in which the traffic will be stored (default PMONITOR.ENC)."
                   ::= { monitorEntry 4 }

       monitorFileSize OBJECT-TYPE
               SYNTAX  Integer32 (1..32)
               MAX-ACCESS read-create
               STATUS current
               DESCRIPTION
       "The number of  65536 ( 64K ) bytes allowed for the file. The file contains only the last monitorFileSize bytes of the current port monitoring instance (default 65536 bytes)."
                   DEFVAL  { 1}
                   ::= {  monitorEntry 5 }

       monitorScreenStatus  OBJECT-TYPE
               SYNTAX  INTEGER {
                       off (1),
                       on (2)
               }
               MAX-ACCESS  read-create
               STATUS  current
               DESCRIPTION
                       "The status of the screen option of a monitoring port instance (default off)"
                   DEFVAL  { off }
                   ::= { monitorEntry 6 }

       monitorScreenLine  OBJECT-TYPE
               SYNTAX  Integer32 (1..100)
               MAX-ACCESS  read-create
               STATUS  current
               DESCRIPTION
                       "The number of lines used when the screen option is activated (default 24)"
                   DEFVAL  { 24 }
                   ::= { monitorEntry 7 }

       monitorTrafficType OBJECT-TYPE
               SYNTAX  INTEGER {
                       all         (1),
                       unicast     (2),
                       multicast   (3),
                       broadcast   (4),
                       unimulti    (5),
                       unibroad    (6),
                       multibroad  (7)
               }
               MAX-ACCESS  read-create
               STATUS  current
               DESCRIPTION
                       "The type of traffic being monitored (default all)"
               DEFVAL  { all }
               ::= { monitorEntry 8 }

       monitorStatus OBJECT-TYPE
               SYNTAX  INTEGER {
                       off (1),
                       on  (2),
                       suspended (3)
               }
               MAX-ACCESS  read-create
               STATUS  current
               DESCRIPTION
                       "The status of the port monitoring instance"
                   DEFVAL  { off }
                   ::= { monitorEntry 9 }


-- anand
       monitorFileOverWrite  OBJECT-TYPE
               SYNTAX  INTEGER {
                       off (1),
                       on (2)
               }
               MAX-ACCESS  read-create
               STATUS  current
               DESCRIPTION
                       "The status of the File Over Write option of a monitoring port instance (default on)"
                   DEFVAL  { on }
                   ::= { monitorEntry 10 }
       monitorDirection  OBJECT-TYPE
                        SYNTAX  INTEGER {
                                inport (1),
                                outport (2),
                                bidirectional (3)
                       }
                       MAX-ACCESS  read-create
                       STATUS  deprecated
                       DESCRIPTION
                                "Direction of monitoring."
                           DEFVAL  { bidirectional }

                           ::= { monitorEntry 11 }


       monitorTimeout OBJECT-TYPE
               SYNTAX  Integer32 (0..2147483647)
               MAX-ACCESS read-create
               STATUS current
               DESCRIPTION
                       "The number of seconds allowed for this session before the session gets deleted.
                        (default:forever 0 second)."
               DEFVAL  { 0 }
               ::= { monitorEntry 12 }


       monitorRowStatus OBJECT-TYPE
                       SYNTAX  RowStatus
                       MAX-ACCESS  read-create
                       STATUS  current
                       DESCRIPTION
                               "The status of this table entry.
                                Create,Delete and Modify."
                  ::= { monitorEntry 13 }


       monitorCaptureType OBJECT-TYPE
               SYNTAX  INTEGER {
                       brief(1),
                       full(2)
               }
               MAX-ACCESS read-create
               STATUS current
               DESCRIPTION
       "The number of bytes per packet allowed to capture .(brief: 64 bytes, full: Entire packet)."
                   DEFVAL  {brief}
                   ::= {  monitorEntry 14 }



--xxxxxxxxxxxxxxxxxxxxxxxxxxxxxxxxxxxxxxxxxxxxxxxx
--Source Monitoring Table----
--xxxxxxxxxxxxxxxxxxxxxxxxxxxxxxxxxxxxxxxxxxxxxxxxx

monitorSrcTable OBJECT-TYPE
               SYNTAX  SEQUENCE OF MonitorSrcEntry
               MAX-ACCESS  not-accessible
               STATUS  current
               DESCRIPTION
                       "A list of port monitoring instances."
                   ::= { mirmonMonitoring 2 }

       monitorSrcEntry  OBJECT-TYPE
               SYNTAX  MonitorSrcEntry
               MAX-ACCESS  not-accessible
               STATUS  current
               DESCRIPTION
                       "A port  monitoring entry."
                   INDEX { monitorSessionNumber, monitorSrcIfindex }
                   ::= { monitorSrcTable 1 }

       MonitorSrcEntry ::= SEQUENCE {
               monitorSrcIfindex
                       InterfaceIndex,
               monitorSrcStatus
                       INTEGER,
               monitorSrcDirection
                         INTEGER,
               monitorSrcRowStatus
                       RowStatus

               }


       monitorSrcIfindex  OBJECT-TYPE
               SYNTAX  InterfaceIndex
               MAX-ACCESS  not-accessible
               STATUS  current
               DESCRIPTION
                       "The physical identification number for this monitoring port instance."
                   ::= { monitorSrcEntry 1 }

       monitorSrcStatus OBJECT-TYPE
               SYNTAX  INTEGER {
                       off (1),
                       on  (2)
               }
               MAX-ACCESS  read-create
               STATUS  current
               DESCRIPTION
                       "The status of the port monitoring instance"
               DEFVAL  { off }
               ::= { monitorSrcEntry 2 }


       monitorSrcDirection  OBJECT-TYPE
               SYNTAX  INTEGER {
                        inport (1),
                        outport (2),
                        bidirectional (3)
                       }
               MAX-ACCESS  read-create
               STATUS  current
               DESCRIPTION
               "Direction of monitoring."
               DEFVAL  { bidirectional }

               ::= { monitorSrcEntry 3 }


        monitorSrcRowStatus OBJECT-TYPE
               SYNTAX  RowStatus
               MAX-ACCESS  read-create
               STATUS  current
               DESCRIPTION
               "The status of this table entry.
                                Create,Delete and Modify."
               ::= { monitorSrcEntry 4 }


--xxxxxxxxxxxxxxxxxxxxxxxxxxxxxxxxxxxxxxxxx
--End of SrcMonitoringTable--------
--xxxxxxxxxxxxxxxxxxxxxxxxxxxxxxxxxxxxxxxxx





 -- xxxxxxxxxxxxxxxxxxxxxxxxxxxxxxxxxxxxxxxxxxxxxxxxxxxxxxxxxxxxxx

        mirmonNotificationVars  OBJECT IDENTIFIER ::= { alcatelIND1PortMirMonMIBObjects 3 }

-- xxxxxxxxxxxxxxxxxxxxxxxxxxxxxxxxxxxxxxxxxxxxxxxxxxxxxxxxxxxxxx

MirMonErrorIds ::= TEXTUAL-CONVENTION
        STATUS  current
        DESCRIPTION
                "This data type is used to define the different type of error
                occured while configuring Mirroring/Monitoring."
        SYNTAX INTEGER {
                other (1),
                wrongSession (2), -- Wrong session given to NI.
                hwQError (3),     -- HW queue error on NI
                swQError (4)      -- SW queue error on NI
                }

mirmonPrimarySlot OBJECT-TYPE
                SYNTAX  Integer32 (1..16)
                MAX-ACCESS  read-only
                STATUS  current
                DESCRIPTION
                        "Slot of mirrored or monitored interface."
           ::= { mirmonNotificationVars 1 }

mirmonPrimaryPort OBJECT-TYPE
                SYNTAX  Integer32 (1..128)
                MAX-ACCESS  read-only
                STATUS  current
                DESCRIPTION
                        "Port of mirrored or monitored interface."
           ::= { mirmonNotificationVars 2 }

mirroringSlot OBJECT-TYPE
                SYNTAX  Integer32 (1..16)
                MAX-ACCESS  read-only
                STATUS  current
                DESCRIPTION
                        "Slot of mirroring interface."
           ::= { mirmonNotificationVars 3 }

mirroringPort OBJECT-TYPE
                SYNTAX  Integer32 (1..128)
                MAX-ACCESS  read-only
                STATUS  current
                DESCRIPTION
                        "Port of mirroring interface."
           ::= { mirmonNotificationVars 4 }

mirMonSession   OBJECT-TYPE
         SYNTAX  Integer32 (1..2147483647)
         MAX-ACCESS  read-only
         STATUS  current
         DESCRIPTION
                "The Mirroring session number."
         ::= {mirmonNotificationVars 5 }

mirMonError OBJECT-TYPE
        SYNTAX  MirMonErrorIds
        MAX-ACCESS read-only
        STATUS     current
        DESCRIPTION
                "The Error returned by the NI which failed to configure Mirroring/Monitoring"
        ::= {mirmonNotificationVars  6 }

mirMonErrorNi OBJECT-TYPE
           SYNTAX  Integer32 (1..16)
           MAX-ACCESS  read-only
           STATUS  current
           DESCRIPTION
                 "The NI slot number. "
           ::= { mirmonNotificationVars 7 }


-- xxxxxxxxxxxxxxxxxxxxxxxxxxxxxxxxxxxxxxxxxxxxxxxxxxxxxxxxxx
--  NOTIFICATIONS
-- xxxxxxxxxxxxxxxxxxxxxxxxxxxxxxxxxxxxxxxxxxxxxxxx
mirrorConfigError NOTIFICATION-TYPE
        OBJECTS {
                mirmonPrimarySlot,
                mirmonPrimaryPort,
                mirroringSlot,
                mirroringPort,
                mirMonErrorNi, -- NI which reported the error.
                mirMonError    -- Error
                }
        STATUS current
        DESCRIPTION
                "The Mirroring Configuration failed on NI.
                This trap is sent when any NI fails to configure mirroring.
                Due to this error, port mirroring session will be terminated."
        ::= { alcatelIND1PortMirMonMIBNotifications 1 }

monitorFileWritten NOTIFICATION-TYPE
       OBJECTS {
                       mirmonPrimarySlot,
                       mirmonPrimaryPort,
                       monitorFileName,
                       monitorFileSize
                       }
  STATUS current
               DESCRIPTION
                       "A File Written Trap is sent when the amount of data requested
                       by the user has been written by the port monitoring instance."
               ::= { alcatelIND1PortMirMonMIBNotifications 2 }


mirrorUnlikeNi  NOTIFICATION-TYPE
        OBJECTS {
                mirmonPrimarySlot,
                mirmonPrimaryPort,
                mirroringSlot,
                mirroringPort,
                mirMonErrorNi  -- NI slot number where the Unlike NI is inserted.
                }
        STATUS current
        DESCRIPTION
                " The Mirroring Configuration is deleted due to the swapping of different
                  NI board type. Port Mirroring session which was active on a slot,cannot
                  continue with the insertion of different NI type in the same slot. "
        ::= { alcatelIND1PortMirMonMIBNotifications 3 }





-- xxxxxxxxxxxxxxxxxxxxxxxxxxxxxxxxxxxxxxxxxxxxxxxxxxxxxxxxxx

        mirmonSFlowObjects  OBJECT IDENTIFIER ::= { alcatelIND1PortMirMonMIBObjects 4}

-- xxxxxxxxxxxxxxxxxxxxxxxxxxxxxxxxxxxxxxxxxxxxxxxxxxxxxxxxxx

-- xxxxxxxxxxxxxxxxxxxxxxxxxxxxxxxxxxxxxxxxxxxxxxxxxxxxxxxxxx
-- Flow Sampling Table
-- xxxxxxxxxxxxxxxxxxxxxxxxxxxxxxxxxxxxxxxxxxxxxxxxxxxxxxxxxx
      alasFlowFsTable OBJECT-TYPE
              SYNTAX      SEQUENCE OF AlaSFlowFsEntry
              MAX-ACCESS  not-accessible
              STATUS      current
              DESCRIPTION
                "A table of the flow samplers within a device."
              ::= { mirmonSFlowObjects 1 }

      alasFlowFsEntry OBJECT-TYPE
              SYNTAX      AlaSFlowFsEntry
              MAX-ACCESS  not-accessible
              STATUS      current
              DESCRIPTION
                "Attributes of a flow sampler."
              AUGMENTS  { sFlowFsEntry }
              ::= { alasFlowFsTable 1 }

      AlaSFlowFsEntry ::= SEQUENCE {
              alasFlowFsDeleteEntry      INTEGER
              }

      alasFlowFsDeleteEntry OBJECT-TYPE
          SYNTAX INTEGER   {
                  active(1),
                  notInService(2),
                  delete(6)
             }
          MAX-ACCESS  read-write
          STATUS      current
          DESCRIPTION
                  "The object is used to delete entries in the sFlowFsTable.
                  Only value 6 is supported."
          ::= { alasFlowFsEntry 1 }

-- xxxxxxxxxxxxxxxxxxxxxxxxxxxxxxxxxxxxxxxxxxxxxxxxxxxxxxxxxx
-- Counter Polling Table
-- xxxxxxxxxxxxxxxxxxxxxxxxxxxxxxxxxxxxxxxxxxxxxxxxxxxxxxxxxx
      alasFlowCpTable OBJECT-TYPE
              SYNTAX      SEQUENCE OF AlaSFlowCpEntry
              MAX-ACCESS  not-accessible
              STATUS      current
              DESCRIPTION
                "A table of the flow samplers within a device."
              ::= { mirmonSFlowObjects 2 }

      alasFlowCpEntry OBJECT-TYPE
              SYNTAX      AlaSFlowCpEntry
              MAX-ACCESS  not-accessible
              STATUS      current
              DESCRIPTION
                "Attributes of a flow sampler."
              AUGMENTS  { sFlowCpEntry }
              ::= { alasFlowCpTable 1 }

      AlaSFlowCpEntry ::= SEQUENCE {
              alasFlowCpDeleteEntry      INTEGER
              }

      alasFlowCpDeleteEntry OBJECT-TYPE
          SYNTAX INTEGER   {
                active(1),
                notInService(2),
                  delete(6)
             }
          MAX-ACCESS  read-write
          STATUS      current
          DESCRIPTION
                  "The object is used to delete entries in the sFlowCpTable.
                   Only value 6 is supported."
          ::= { alasFlowCpEntry 1 }

-- xxxxxxxxxxxxxxxxxxxxxxxxxxxxxxxxxxxxxxxxxxxxxxxxxxxxxxxxxx
--  Agent IP Information
--  xxxxxxxxxxxxxxxxxxxxxxxxxxxxxxxxxxxxxxxxxxxxxxxxxxxxxxxxxx

       alasFlowAgentConfigType OBJECT-TYPE
           SYNTAX      INTEGER {
                      default(1),
                      user(2)
                 }
           MAX-ACCESS read-write
           STATUS        current
           DESCRIPTION
                  "The Agent Config Information
                   1 -- Default
                   2 -- sFlow Interface IP Specified by User"
           DEFVAL        { default }
          ::= {  mirmonSFlowObjects 3}

       alasFlowAgentAddressType OBJECT-TYPE
               SYNTAX      InetAddressType
               MAX-ACCESS  read-write
               STATUS      current
               DESCRIPTION
                 "The address type of the address associated with this agent.
                  Only ipv4 and ipv6 types are supported."
               ::= { mirmonSFlowObjects 4}

       alasFlowAgentAddress OBJECT-TYPE
           SYNTAX InetAddress
           MAX-ACCESS  read-write
           STATUS      current
           DESCRIPTION
                 "The IP address associated with this agent. In the case of a
                  multi-homed agent, this should be the loopback address of the
                  agent. The sFlowAgent address must provide SNMP connectivity
                  to the agent. The address should be an invariant that does not
                  change as interfaces are reconfigured, enabled, disabled,
                  added or removed. A manager should be able to use the
                  sFlowAgentAddress as a unique key that will identify this
                  agent over extended periods of time so that a history can
                  be maintained."
           ::= { mirmonSFlowObjects 5 }
-- xxxxxxxxxxxxxxxxxxxxxxxxxxxxxxxxxxxxxxxxxxxxxxxxxxxxxxxxxx
-- Flow Sampling Ext Table 
-- xxxxxxxxxxxxxxxxxxxxxxxxxxxxxxxxxxxxxxxxxxxxxxxxxxxxxxxxxx
      alasFlowFsExtTable OBJECT-TYPE
              SYNTAX      SEQUENCE OF AlaSFlowFsExtEntry
              MAX-ACCESS  not-accessible
              STATUS      current
              DESCRIPTION
                "A table of the flow samplers within a device."
              ::= { mirmonSFlowObjects 6 }

      alasFlowFsExtEntry OBJECT-TYPE
              SYNTAX      AlaSFlowFsExtEntry
              MAX-ACCESS  not-accessible
              STATUS      current
              DESCRIPTION
                "Attributes of a flow sampler."
              INDEX { alasFlowFsInstance }
              ::= { alasFlowFsExtTable 1 }

      AlaSFlowFsExtEntry ::= SEQUENCE {
              alasFlowFsInstance            SFlowInstance,
              alasFlowFsRate            Integer32,
              alasFlowFsRateRowStatus        RowStatus
              }

       alasFlowFsInstance OBJECT-TYPE
           SYNTAX      SFlowInstance
           MAX-ACCESS  not-accessible
           STATUS      current
           DESCRIPTION
                 "Flow samplers instance"
           ::= { alasFlowFsExtEntry 1 }

       alasFlowFsRate OBJECT-TYPE
           SYNTAX      Integer32 
           MAX-ACCESS  read-create
           STATUS      current
           DESCRIPTION
                 "Flow samplers rate"
           ::= { alasFlowFsExtEntry 2 }

        alasFlowFsRateRowStatus OBJECT-TYPE
                SYNTAX  RowStatus
                MAX-ACCESS  read-create
                STATUS  current
                DESCRIPTION
                        "The status of this table entry.Row Status to control creation,
                        modification and deletion of this entry. "
           ::= { alasFlowFsExtEntry 3 }     

-- xxxxxxxxxxxxxxxxxxxxxxxxxxxxxxxxxxxxxxxxxxxxxxxxxxxxxxxxxxxxxx

--        SFLOW EXTENDED SWITCH/ROUTER/GATEWAY OBJECTS (RFC 3176)

-- xxxxxxxxxxxxxxxxxxxxxxxxxxxxxxxxxxxxxxxxxxxxxxxxxxxxxxxxxxxxxx

       alasFlowExtendedSwitch OBJECT-TYPE
           SYNTAX  INTEGER {
                enabled (1),
                disabled  (2)
           }
           MAX-ACCESS  read-write
           STATUS      current
           DESCRIPTION
                "Indicates whether extended switch data sampling is enabled or disabled in the sFlow record.
                 When enabled (1), additional extended switch data is included in the sFlow record. 
                 When disabled (2), extended switch data is not included."
           DEFVAL  { enabled }                 
           ::= { mirmonSFlowObjects 7 }

       alasFlowExtendedRouter OBJECT-TYPE
           SYNTAX  INTEGER {
                enabled (1),
                disabled  (2)
           }
           MAX-ACCESS  read-write
           STATUS      current
           DESCRIPTION
                "Indicates whether extended router data sampling is enabled or disabled in the sFlow record.
                 When enabled (1), additional extended router data is included in the sFlow record. 
                 When disabled (2), extended router data is not included."
           DEFVAL  { disabled }                 
           ::= { mirmonSFlowObjects 8 }
                  
 -- xxxxxxxxxxxxxxxxxxxxxxxxxxxxxxxxxxxxxxxxxxxxxxxxxxxxxxxxxxxxxx

        mirmonGlobalConfig    OBJECT IDENTIFIER ::= { alcatelIND1PortMirMonMIBObjects 5 }

-- xxxxxxxxxxxxxxxxxxxxxxxxxxxxxxxxxxxxxxxxxxxxxxxxxxxxxxxxxxxxxx

        mirrorTrafficPriority OBJECT-TYPE
            SYNTAX  INTEGER {
                        normal(1),
                        high(2)
            }
            MAX-ACCESS  read-create
            STATUS      current
            DESCRIPTION
                "To set priority for mirroring traffic."
            DEFVAL  { normal }
            ::= {  mirmonGlobalConfig 1}

-- xxxxxxxxxxxxxxxxxxxxxxxxxxxxxxxxxxxxxxxxxxxxxxxxxxxxxxxxxx
-- COMPLIANCE
-- xxxxxxxxxxxxxxxxxxxxxxxxxxxxxxxxxxxxxxxxxxxxxxxx

    alcatelIND1PortMirMonMIBCompliance MODULE-COMPLIANCE
        STATUS  current
        DESCRIPTION
            "Compliance statement for
             Port Mirroring and Monitoring."
        MODULE
            MANDATORY-GROUPS
            {
                portMirroringGroup,
                portMonitoringGroup,
                portNotificationVarsGroup
            }

        ::= { alcatelIND1PortMirMonMIBCompliances 1 }


-- xxxxxxxxxxxxxxxxxxxxxxxxxxxxxxxxxxxxxxxxxxxxxxxxxxxxxxxxxx
-- UNITS OF CONFORMANCE
-- xxxxxxxxxxxxxxxxxxxxxxxxxxxxxxxxxxxxxxxxxxxxxxxxxxxxxxxxxx

    portMirroringGroup OBJECT-GROUP
        OBJECTS
        {
                        mirrorSessionNumber,     -- port mirroring table
                        mirrorMirroredIfindex,
                        mirrorMirroringIfindex,
                        mirrorStatus,
                        mirrorUnblockedVLAN,
                        mirrorRowStatus,
                        mirrorDirection,
                        mirrorSessOperStatus,
                        mirrorSrcMirroredIf,
                        mirrorSrcStatus,
                        mirrorSrcDirection,
                        mirrorSrcRowStatus,
                        mirrorSrcOperStatus,
                        mirrorDstOperStatus,
                        mirrorDstAdminStatus,
                        mirrorDstRowStatus,
                        mirrorDstTagRemove,
                        mirrorTrafficPriority

        }
        STATUS  current
        DESCRIPTION
            "Collection of objects for management of Port Mirroring."
        ::= { alcatelIND1PortMirMonMIBGroups 1 }

   portMonitoringGroup OBJECT-GROUP
        OBJECTS
        {
                        monitorSessionNumber,     -- port monitoring table
                        monitorIfindex,
                        monitorFileStatus,
                        monitorFileName,
                        monitorFileSize,
                        monitorScreenStatus,
                        monitorScreenLine,
                        monitorTrafficType,
                        monitorStatus,
                        monitorFileOverWrite,
                        monitorDirection ,
                        monitorTimeout ,
                        monitorRowStatus,
                        monitorCaptureType,
                        monitorSrcStatus,   
                        monitorSrcDirection,    
                        monitorSrcRowStatus    

        }                  
        STATUS  current    
        DESCRIPTION
            "Collection of objects for management of Port Monitoring."
        ::= { alcatelIND1PortMirMonMIBGroups 2 }


    portNotificationVarsGroup OBJECT-GROUP
        OBJECTS
        {
                       mirmonPrimarySlot,
                       mirmonPrimaryPort,
                       mirroringSlot,
                       mirroringPort,
                       mirMonSession,
                       mirMonError,
                       mirMonErrorNi
        }
        STATUS  current
        DESCRIPTION
            "Collection of objects which appear only in notifications."
        ::= { alcatelIND1PortMirMonMIBGroups 3 }


    mirmonTrapsGroup NOTIFICATION-GROUP
        NOTIFICATIONS {
            mirrorConfigError,
            mirrorUnlikeNi,
            monitorFileWritten
        }
        STATUS  current
        DESCRIPTION
            "Collection of Traps for port mirroring and monitoring."
        ::= { alcatelIND1PortMirMonMIBGroups 4 }


    sFlowAgentGroup OBJECT-GROUP
        OBJECTS {
            alasFlowAgentAddress ,
            alasFlowAgentAddressType ,
            alasFlowAgentConfigType,
            alasFlowExtendedSwitch,
            alasFlowExtendedRouter
        }
        STATUS  current
        DESCRIPTION
            "Collection of objects for sFlow agent configuration."
        ::= { alcatelIND1PortMirMonMIBGroups 5 }

    portMirrorGroup OBJECT-GROUP
        OBJECTS {
                mirrorSessionNumber ,
                mirrorMirroredIfindex ,
                mirrorMirroringIfindex ,
                mirrorStatus ,
                mirrorUnblockedVLAN ,
                mirrorRowStatus ,
                mirrorDirection ,
                mirrorSessOperStatus ,
                mirrorTaggedVLAN,
                mirrorModeLoopback
        }
        STATUS  current
        DESCRIPTION
            "Collection of objects for Mirror configuration."
        ::= { alcatelIND1PortMirMonMIBGroups 6 }

    portSFlowCpGroup OBJECT-GROUP
        OBJECTS {
              alasFlowCpDeleteEntry
              }
        STATUS  current
        DESCRIPTION
            "Collection of objects for sFlow Cp configuration."
        ::= { alcatelIND1PortMirMonMIBGroups 7 }


    portSFlowFsGroup OBJECT-GROUP
        OBJECTS {
              alasFlowFsDeleteEntry,
              alasFlowFsRate
              }
        STATUS  current
        DESCRIPTION
            "Collection of objects for sFlow Fs configuration."
        ::= { alcatelIND1PortMirMonMIBGroups 8 }

    portSFlowFsExtGroup OBJECT-GROUP
        OBJECTS {
              alasFlowFsRate,
              alasFlowFsRateRowStatus
              }
        STATUS  current
        DESCRIPTION
            "Collection of objects for sFlow Fs configuration."
        ::= { alcatelIND1PortMirMonMIBGroups 9 }
END
