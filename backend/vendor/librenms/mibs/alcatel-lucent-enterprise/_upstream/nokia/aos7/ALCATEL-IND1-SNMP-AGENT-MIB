ALCATEL-IND1-SNMP-AGENT-MIB DEFINITIONS ::= BEGIN

IMPORTS
        OBJECT-TYPE,
        OBJECT-IDENTITY,
        MODULE-IDENTITY,
        NOTIFICATION-TYPE, 
        IpAddress               FROM SNMPv2-SMI
        TEXTUAL-CONVENTION, RowStatus      FROM SNMPv2-TC
        SnmpEngineID, SnmpAdminString       FROM SNMP-FRAMEWORK-MIB
        OBJECT-GROUP,
        MODULE-COMPLIANCE,
        NOTIFICATION-GROUP       FROM SNMPv2-CONF
        softentIND1SnmpAgt      FROM ALCATEL-IND1-BASE
        InetAddressType, InetAddress        FROM INET-ADDRESS-MIB
        snmp                                FROM SNMPv2-MIB;

        
alcatelIND1SNMPAgentMIB  MODULE-IDENTITY
    LAST-UPDATED "201911270000Z"
    ORGANIZATION "ALE USA Inc."
    CONTACT-INFO
     "Please consult with Customer Service to ensure the most appropriate
      version of this document is used with the products in question:

                      ALE USA Inc. Enterprise
                        26801 West Agoura Road
                     Agoura Hills, CA  91301-5122
                       United States Of America

     Telephone:          +1 800 995 2696

     Electronic Mail:    ebg_global_supportcenter@al-enterprise.com
     World Wide Web:     https://www.al-enterprise.com"
        DESCRIPTION
            "This module describes an authoritative enterprise-specific Simple
             Network Management Protocol (SNMP) Management Information Base (MIB):

                 For the OmniSwitch Product Line
                 SNMP Agent Subsystem.

             The right to make changes in specification and other information
             contained in this document without prior notice is reserved.

             No liability shall be assumed for any incidental, indirect, special, or
             consequential damages whatsoever arising from or related to this
             document or the information contained herein.

             Vendors, end-users, and other interested parties are granted
             non-exclusive license to use this specification in connection with
             management of the products for which it is intended to be used.

                       Copyright (C) ALE USA Inc. 2014-2019
                       Copyright (C) 1995-2013 Alcatel-Lucent
                           ALL RIGHTS RESERVED WORLDWIDE"

        REVISION      "201911270000Z"
        DESCRIPTION
            "Updated the latest contact and Copyright information for ALE USA Inc."

        REVISION      "201407150000Z"
        DESCRIPTION
            "Addressing discrepancies with Alcatel Standard."
        ::= { softentIND1SnmpAgt 1 }

    alcatelIND1SNMPAgentMIBNotifications OBJECT-IDENTITY
        STATUS current
        DESCRIPTION
            "Branch For SNMP Agent Subsystem Notifications."
        ::= { alcatelIND1SNMPAgentMIB 0 }

    alcatelIND1SNMPAgentMIBObjects OBJECT-IDENTITY
        STATUS current
        DESCRIPTION
            "Branch For SNMP Agent Subsystem Managed Objects."
        ::= { alcatelIND1SNMPAgentMIB 1 }


    alcatelIND1SNMPAgentMIBConformance OBJECT-IDENTITY
        STATUS current
        DESCRIPTION
            "Branch For SNMP Agent Subsystem Conformance Information."
        ::= { alcatelIND1SNMPAgentMIB 2 }


    alcatelIND1SNMPAgentMIBGroups OBJECT-IDENTITY
        STATUS current
        DESCRIPTION
            "Branch For SNMP Agent Subsystem Units Of Conformance."
        ::= { alcatelIND1SNMPAgentMIBConformance 1 }


    alcatelIND1SNMPAgentMIBCompliances OBJECT-IDENTITY
        STATUS current
        DESCRIPTION
            "Branch For SNMP Agent Subsystem Compliance Statements."
        ::= { alcatelIND1SNMPAgentMIBConformance 2 }


--
-- SNMP Agent configuration
--

snmpAgtConfig  OBJECT IDENTIFIER ::= { alcatelIND1SNMPAgentMIBObjects 1 }

SnmpAgtSecurityLevel ::= TEXTUAL-CONVENTION
        STATUS current
        DESCRIPTION
        "The switch security level"
        SYNTAX INTEGER {
                noSec(1),
                authSet(2),
                authAll(3),
                privSet(4),
                privAll(5),
                trapOnly(6)
        }

snmpAgtSecurityLevel OBJECT-TYPE
        SYNTAX     SnmpAgtSecurityLevel
        MAX-ACCESS read-write
        STATUS     current
        DESCRIPTION
        "Level of security required for SNMP get or SET.
         noSec: no security; all the PDU with a known user id
                are accepted
         authSet: authentication required for set; all GET
                are accepted, but not authenticated SET are
                rejected.
         authAll: authentication required for SET and GET; not
                authenticated SET and GET are rejected.
         privSet: authentication required for GET and encryption
                required for SET.
         privAll: encryption required for SET and GET.
         trapOnly: no SNMP GET or SET are accepted."
        DEFVAL     { privAll }
        ::= { snmpAgtConfig 1}

snmpAgtCommunityMode OBJECT-TYPE
        SYNTAX  INTEGER {
                enabled(1),
                disabled(2) }
        MAX-ACCESS  read-write
        STATUS  current
        DESCRIPTION
                "If the community mode is enabled,
                 the SNMPv1/v2 packets must use
                 the community names."
        DEFVAL { disabled }
        ::= { snmpAgtConfig 2 }

snmpAgtTsmAdminState OBJECT-TYPE
        SYNTAX  INTEGER {
                enable(1),
                disable(2) }
        MAX-ACCESS  read-write
        STATUS  current
        DESCRIPTION
                "Tsm status (enable/disable)."
        DEFVAL { disable }
        ::= { snmpAgtConfig 3 }

snmpAgtTlsAdminState OBJECT-TYPE
        SYNTAX INTEGER
                {
                  enable(1),
                  disable(2)
                }
        MAX-ACCESS read-write
        STATUS current
        DESCRIPTION
            "The global SNMP TLS admin state."
        DEFVAL { enable }
    ::= { snmpAgtConfig 4  }

--
-- SNMP Agent Epilogue Control Files anchoring
--

      snmpAgtCtlFiles OBJECT-IDENTITY
        STATUS current
        DESCRIPTION
        "MIB entity on which to attach the MODULE-IDENTITY for the
        Epilogue(R) control files."
        ::= { alcatelIND1SNMPAgentMIBObjects 3}

--
-- SNMP Source Ip Preferred Configuration
--

      snmpAgtSourceIpConfig  OBJECT-TYPE
        SYNTAX INTEGER {
             default (1),
             noLoopback0 (2),
             ipInterface (3)
       }
       MAX-ACCESS read-only
       STATUS        deprecated
       DESCRIPTION
              "The SNMP Agent Configuration
              1 -- Default(Loopback0 or closest IP)
              2 -- No Loopback0
              3 -- Interface IP Specified by User
              NOTE: this configuration option has been deprecated.
              Please see alaIpServiceSourceIpTable for SNMP Source
              IP Preferred Configuration (in ALCATEL-IND1-IP-MIB)."
       DEFVAL        { default }
       ::= {  alcatelIND1SNMPAgentMIBObjects 4 }

      snmpAgtSourceIp  OBJECT-TYPE
        SYNTAX     IpAddress
        MAX-ACCESS read-only
        STATUS        deprecated
        DESCRIPTION
               "The Source IP of SNMP Packets.
               NOTE: this configuration option has been deprecated.
               Please see alaIpServiceSourceIpTable for SNMP Source
               IP Preferred Configuration (in ALCATEL-IND1-IP-MIB)."
        ::= {  alcatelIND1SNMPAgentMIBObjects 5 }

--
-- SNMP Agent (switch wide) EngineId Configuration
--
      snmpAgtEngineIdType  OBJECT-TYPE
        SYNTAX INTEGER {
                         reserved(0),
                         ipv4(1),
                         ipv6(2),
                         mac(3),
                         text(4),
                         octets(5)
        }
        MAX-ACCESS read-write
        STATUS  current
        DESCRIPTION
              "The SNMP Agent (switch) Engine ID Type Configuration."

        ::= {  alcatelIND1SNMPAgentMIBObjects 6 }

      snmpAgtEngineId  OBJECT-TYPE
        SYNTAX  SnmpEngineID
        MAX-ACCESS read-write
        STATUS  current
        DESCRIPTION
              "The SNMP Agent (switch) Engine ID Configuration."
        ::= {  alcatelIND1SNMPAgentMIBObjects 7 }

--
-- SNMP TSM Map User Table
--

      alaSnmpTsmUserTable OBJECT-TYPE
        SYNTAX       SEQUENCE OF AlaSnmpTsmUserEntry
        MAX-ACCESS   not-accessible
        STATUS       current
        DESCRIPTION
              "The table of user remote identity configured in the SNMP."
        ::= { alcatelIND1SNMPAgentMIBObjects 8 }

      alaSnmpTsmUserEntry OBJECT-TYPE
        SYNTAX       AlaSnmpTsmUserEntry
        MAX-ACCESS   not-accessible
        STATUS       current
        DESCRIPTION
              "Information about a particular user remote identity."
        INDEX       { alaSnmpTsmUserRemoteIdentity }
        ::= { alaSnmpTsmUserTable 1 }

      AlaSnmpTsmUserEntry ::= SEQUENCE {
        alaSnmpTsmUserRemoteIdentity      SnmpAdminString,
        alaSnmpTsmUserName                SnmpAdminString,
        alaSnmpTsmUserStatus              RowStatus
        }

      alaSnmpTsmUserRemoteIdentity OBJECT-TYPE
        SYNTAX      SnmpAdminString (SIZE(1..128))
        MAX-ACCESS  not-accessible
        STATUS      current
        DESCRIPTION
              "Remote identifier is file name of the X.509 certificate."
        ::= { alaSnmpTsmUserEntry 1 }

      alaSnmpTsmUserName OBJECT-TYPE
        SYNTAX      SnmpAdminString (SIZE(1..32 ))
        MAX-ACCESS  read-create
        STATUS      current
        DESCRIPTION
              "Name of the user."
        ::= { alaSnmpTsmUserEntry 2 }

      alaSnmpTsmUserStatus OBJECT-TYPE
        SYNTAX       RowStatus
        MAX-ACCESS   read-create
        STATUS       current
        DESCRIPTION
              "The status of this conceptual row in the alaSnmpTsmUserTable."
        ::= { alaSnmpTsmUserEntry 3 }

snmpAuthTrapMode OBJECT-TYPE
        SYNTAX INTEGER
                {
                  standard(1),
                  private(2),
                  both(3)
                }
        MAX-ACCESS read-write
        STATUS current
        DESCRIPTION
            "The global SNMP authentication trap mode."
        DEFVAL { standard }
    ::= { snmp 33 }

--
-- Compliance Statements
--

    alcatelIND1SNMPAgentMIBCompliance MODULE-COMPLIANCE
        STATUS  current
        DESCRIPTION
            "Compliance statement for SNMP Agent Subsystem."
        MODULE  -- this module

            MANDATORY-GROUPS
            {
                snmpAgtConfigGroup,
                alaSnmpTsmUserGroup,
                alaSnmpGroup
            }

        ::= { alcatelIND1SNMPAgentMIBCompliances 1 }

-- Notification Objects
    alaAuthenticationFailureNotificationObj   OBJECT IDENTIFIER ::= { alcatelIND1SNMPAgentMIBObjects 9 }

    alaClientIPAddrType OBJECT-TYPE
        SYNTAX       InetAddressType
        MAX-ACCESS    accessible-for-notify
        STATUS        current
        DESCRIPTION
            "Client IP type causing AuthenticationFailure"
        ::= { alaAuthenticationFailureNotificationObj 1 }

    alaClientIPAddr OBJECT-TYPE
        SYNTAX       InetAddress 
        MAX-ACCESS    accessible-for-notify
        STATUS        current
        DESCRIPTION
            "Client IP causing AuthenticationFailure"
        ::= { alaAuthenticationFailureNotificationObj 2 }

-- ******************************************************************
-- NOTIFICATIONS (TRAPS)
-- ******************************************************************
   alaAuthenticationFailure NOTIFICATION-TYPE
        OBJECTS  {
                alaClientIPAddrType,
				alaClientIPAddr
           }
       STATUS  current
       DESCRIPTION
               "Instead of standard authentificationFailure Notification, 
                alaAuthenticationFailure is to provide IP Address information
                of source. An alaAuthenticationFailure trap signifies that the SNMP
                entity has received a protocol message that is not
                properly authenticated.  While all implementations
                of SNMP entities MAY be capable of generating this
                trap, the snmpEnableAuthenTraps object indicates
                whether this trap will be generated."
       ::= { alcatelIND1SNMPAgentMIBNotifications 1 }
--
-- Units Of Conformance
--

     snmpAgtConfigGroup OBJECT-GROUP
        OBJECTS
        {
            snmpAgtSecurityLevel,
            snmpAgtCommunityMode,
            snmpAgtSourceIp,
            snmpAgtSourceIpConfig,
            snmpAgtEngineIdType,
            snmpAgtEngineId,
            snmpAgtTsmAdminState,
            snmpAgtTlsAdminState
        }
        STATUS  current
        DESCRIPTION
            "Collection of objects for SNMP Agent configuration."
        ::= { alcatelIND1SNMPAgentMIBGroups 1 }

     alaSnmpTsmUserGroup OBJECT-GROUP
        OBJECTS
        {
            alaSnmpTsmUserName,
            alaSnmpTsmUserStatus
        }
        STATUS  current
        DESCRIPTION
            "Collection of objects for SNMP map user configuration."
        ::= { alcatelIND1SNMPAgentMIBGroups 2 }

     alaSnmpBasicNotificationsGroup NOTIFICATION-GROUP
       NOTIFICATIONS { alaAuthenticationFailure }
       STATUS        current
       DESCRIPTION
          "The basic notifications implemented by an SNMP entity
           supporting command responder applications."
       ::= { alcatelIND1SNMPAgentMIBGroups 3 }

     alaSnmpGroup OBJECT-GROUP
        OBJECTS
        {
            snmpAuthTrapMode
        }
        STATUS  current
        DESCRIPTION
            "Collection of objects for SNMP user configuration."
        ::= { alcatelIND1SNMPAgentMIBGroups 4 }
     alaAuthFailureGroup OBJECT-GROUP
        OBJECTS
        {
            alaClientIPAddrType,
            alaClientIPAddr
        }
        STATUS  current
        DESCRIPTION
            "Collection of objects for Alcatel Proprietary alaAuthenticationFailure notification."
        ::= { alcatelIND1SNMPAgentMIBGroups 5 }

END
