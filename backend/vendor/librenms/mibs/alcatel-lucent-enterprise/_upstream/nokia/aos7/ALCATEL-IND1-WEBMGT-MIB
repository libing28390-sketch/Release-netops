ALCATEL-IND1-WEBMGT-MIB DEFINITIONS ::= BEGIN

        IMPORTS
                OBJECT-TYPE, MODULE-IDENTITY, OBJECT-IDENTITY, NOTIFICATION-TYPE,
                Counter32, Integer32, IpAddress
                        FROM SNMPv2-SMI
                RowStatus
                        FROM SNMPv2-TC
                SnmpAdminString
                        FROM SNMP-FRAMEWORK-MIB
                MODULE-COMPLIANCE, OBJECT-GROUP, NOTIFICATION-GROUP
                        FROM SNMPv2-CONF
                InetAddress, InetAddressType
                        FROM INET-ADDRESS-MIB
                softentIND1WebMgt
                        FROM ALCATEL-IND1-BASE;

        alcatelIND1WebMgtMIB MODULE-IDENTITY
            LAST-UPDATED "201911270000Z"
            ORGANIZATION "ALE USA Inc."
            CONTACT-INFO
             "Please consult with Customer Service to ensure the most appropriate
              version of this document is used with the products in question:

                              Alcatel-Lucent Enterprise
                                26801 West Agoura Road
                             Agoura Hills, CA  91301-5122
                               United States Of America

             Telephone:          +1 800 995 2696

             Electronic Mail:    ebg_global_supportcenter@al-enterprise.com
             World Wide Web:     https://www.al-enterprise.com"

        DESCRIPTION
            "This module describes an authoritative enterprise-specific Simple
             Network Management Protocol (SNMP) Management Information Base (MIB):

                 For the OmniSwitch Product Line
                 WebView - web based embedded device manager.

             The right to make changes in specification and other information
             contained in this document without prior notice is reserved.

             No liability shall be assumed for any incidental, indirect, special, or
             consequential damages whatsoever arising from or related to this
             document or the information contained herein.

             Vendors, end-users, and other interested parties are granted
             non-exclusive license to use this specification in connection with
             management of the products for which it is intended to be used.

                   Copyright (C) ALE USA Inc. 2014-2019
                   Copyright (C) 1995-2013 Alcatel-Lucent
                       ALL RIGHTS RESERVED WORLDWIDE"

        REVISION      "201911270000Z"
        DESCRIPTION
            "Updated the latest contact and Copyright information for ALE USA Inc."

        REVISION      "201005130000Z"
        DESCRIPTION
            "Fixed the Notifications to use MIB Module OID.0 as Notifications root."
        ::= { softentIND1WebMgt 1 }



        alcatelIND1WebMgtMIBNotifications OBJECT-IDENTITY
        STATUS current
        DESCRIPTION
            "Branch For WebView MIB Subsystem Notifications."
        ::= { alcatelIND1WebMgtMIB 0 }

       alcatelIND1WebMgtMIBObjects OBJECT-IDENTITY
                STATUS current
                DESCRIPTION
                "Branch For WebView Subsystem Managed Objects."
                ::= { alcatelIND1WebMgtMIB  1 }

        alcatelIND1WebMgtMIBConformance OBJECT-IDENTITY
        STATUS current
                DESCRIPTION
                "Branch For WebView Subsystem Conformance Information."
                ::= { alcatelIND1WebMgtMIB  2 }


        alcatelIND1WebMgtMIBGroups OBJECT-IDENTITY
                STATUS current
                DESCRIPTION
                "Branch For WebView Subsystem Groups of managed objects."
                ::= { alcatelIND1WebMgtMIBConformance 1 }


        alcatelIND1WebMgtMIBCompliances OBJECT-IDENTITY
                STATUS current
                DESCRIPTION
                "Branch For WebView Subsystem Compliance Statements."
                ::= { alcatelIND1WebMgtMIBConformance 2 }

-- WebView Global Configuration parameters and objects

       alaIND1WebMgtAdminStatus OBJECT-TYPE
            SYNTAX  INTEGER {
                        enable(1),
                        disable(2)
                            }
            MAX-ACCESS  read-write
            STATUS  current
            DESCRIPTION
            "Enable/Disable access to WebView.  If WebView access is disabled, the
            WebView server will not be disabled automatically."
                DEFVAL { enable }
         ::= { alcatelIND1WebMgtMIBObjects 1 }


        alaIND1WebMgtSSL OBJECT-TYPE
            SYNTAX  INTEGER {
                        enable(1),
                        disable(2)
                              }
            MAX-ACCESS  read-write
            STATUS  current
            DESCRIPTION
            "Enable/Disable forced SSL for WebView."
                DEFVAL { enable }
         ::= { alcatelIND1WebMgtMIBObjects 2}


        alaIND1WebMgtHttpPort OBJECT-TYPE
            SYNTAX  Integer32 (80 | 1024..65535)
            MAX-ACCESS  read-write
            STATUS  current
            DESCRIPTION
                 "The user configurable TCP port for switch's
                 http access. Default is 80."
            DEFVAL { 80 }
         ::= { alcatelIND1WebMgtMIBObjects 3 }

        alaIND1WebMgtHttpsPort OBJECT-TYPE
            SYNTAX  Integer32 (443 | 1024..65535)
            MAX-ACCESS  read-write
            STATUS  current
            DESCRIPTION
                 "The user configurable TCP port for switch's https
                 access. Default is 443."
            DEFVAL { 443 }
         ::= { alcatelIND1WebMgtMIBObjects 4 }

        alaIND1WebMgtServerStatus OBJECT-TYPE
            SYNTAX  INTEGER {
                        enable(1),
                        disable(2),
			restarting(3),
                        error(4)
                              }
            MAX-ACCESS  read-write
            STATUS  current
            DESCRIPTION
            "Enable/Disable WebView embedded server.
             If the WebView server is disabled and WebView access is enabled, access will be
             automatically disabled.  However, if the server was disabled and changes to enabled,
             WebView access will not be automatically enabled.
             Status restarting and error are max-access read-only
             (the error code string can be read using alaIND1WebMgtServerError)."
                DEFVAL { enable }
         ::= { alcatelIND1WebMgtMIBObjects 5 }

        alaIND1WebMgtServerError OBJECT-TYPE
            SYNTAX  SnmpAdminString (SIZE (0..127))
            MAX-ACCESS  read-only
            STATUS  current
            DESCRIPTION
            "Error code string when WebView Server is in error status.
             Format is 'Error Num: {Number}. {String message}.' where
             {Number} is an integer representing the error code and
             {String message} is the error string message."
         ::= { alcatelIND1WebMgtMIBObjects 6 }

        alcatelIND1WebMgtCertObjects OBJECT-IDENTITY
            STATUS current
            DESCRIPTION
            "Branch For WebView SSL Certificate Objects."
         ::= { alcatelIND1WebMgtMIBObjects  8 }

        alaIND1WebMgtWlanIpPrecedence OBJECT-TYPE
            SYNTAX  INTEGER {
                        lldp(1),
                        configured(2)
                        }
            MAX-ACCESS  read-write
            STATUS  current
            DESCRIPTION
                 "The WLAN virtual cluster IP for Webview re-direct, can be  
		 obtained either via Configuration or via LLDP. The preference 
		 for the choice of the cluster IP can be set using this precedence object. 
 		 If the preference for the source of the 
		 cluster IP is not set, then the IP address obtained via LLDP will 
		 be used for the re-direct."
            DEFVAL { lldp }
         ::= { alcatelIND1WebMgtMIBObjects 9 }

        alaIND1WebMgtWlanConfiguredIpAddressType OBJECT-TYPE
            SYNTAX  InetAddressType { ipv4(1) }
            MAX-ACCESS  read-write
            STATUS  current
            DESCRIPTION
                 "IP address type of the WLAN virtual cluster IP address configured 
		 via CLI/SNMP/Webview. IPv4 (1) is the only type currently supported."
         ::= { alcatelIND1WebMgtMIBObjects 10 }

        alaIND1WebMgtWlanConfiguredIpAddress OBJECT-TYPE
            SYNTAX  InetAddress 
            MAX-ACCESS  read-write
            STATUS  current
            DESCRIPTION
                 "WLAN virtual cluster IP address configured manually via CLI/SNMP/Webview."
         ::= { alcatelIND1WebMgtMIBObjects 11 }

        alaIND1WebMgtWlanLldpIpAddressType OBJECT-TYPE
            SYNTAX  InetAddressType { ipv4(1) }
            MAX-ACCESS  read-only
            STATUS  current
            DESCRIPTION
                 "IP address type of the WLAN virtual cluster IP address obtained via LLDP.
		  IPv4 (1) is the only type currently supported."
         ::= { alcatelIND1WebMgtMIBObjects 12 }

        alaIND1WebMgtWlanLldpIpAddress OBJECT-TYPE
            SYNTAX  InetAddress 
            MAX-ACCESS  read-only
            STATUS  current
            DESCRIPTION
                 "WLAN virtual cluster IP address obtained via LLDP."
         ::= { alcatelIND1WebMgtMIBObjects 13 }

        alaIND1WebMgtSSLStrongCiphers OBJECT-TYPE
            SYNTAX  INTEGER {
                        enable(1),
                        disable(2)
                              }
            MAX-ACCESS  read-write
            STATUS  current
            DESCRIPTION
            "Enable/Disable SSL Strong Ciphers for WebView."
                DEFVAL { enable }
         ::= { alcatelIND1WebMgtMIBObjects 14}

        alaIND1WebMgtTlsVersion  OBJECT-TYPE
            SYNTAX      INTEGER {
                            versionOneDotZero(1),
                            versionOneDotOne (2),
                            versionOneDotTwo(3)
                        }
            MAX-ACCESS read-write
            STATUS current
            DESCRIPTION
                "This object is used for selecting the TLS version for Webview."
            DEFVAL { versionOneDotZero }
        ::= { alcatelIND1WebMgtMIBObjects 15 }

        alaIND1WebMgtInstallCertFilePath  OBJECT-TYPE
            SYNTAX      SnmpAdminString(SIZE(0..255))
            MAX-ACCESS  read-write
            STATUS      current
            DESCRIPTION
                "This object is used for install certificate file path for Webview."
        ::= { alcatelIND1WebMgtMIBObjects 16 }
 
        alaIND1WebMgtCertificate  OBJECT-TYPE
            SYNTAX      INTEGER {
                            default(1),
                            custom(2)
                        }
            MAX-ACCESS  read-only
            STATUS      current
            DESCRIPTION
                "Default: The self-sign webview certificcate.
                Custom: The user's webview certificate."
            DEFVAL { default }
        ::= { alcatelIND1WebMgtMIBObjects 17 }

-- WebView parameters and objects related to the SSL Certificate

        alcatelIND1WebMgtCertFile OBJECT-TYPE
            SYNTAX  INTEGER {
                        none(1),
                        default(2),
                        user(3)
                            }
            MAX-ACCESS  read-write
            STATUS  current
            DESCRIPTION
            "Triggers certificate file to be synchronize across the chassis.
            The default value may not be used when setting this object.
            The default will always be returned when getting this object."
                DEFVAL { none }
         ::= { alcatelIND1WebMgtCertObjects 1 } 

        alcatelIND1WebMgtCertMD5 OBJECT-TYPE
            SYNTAX  SnmpAdminString (SIZE (0..32))
            MAX-ACCESS  read-write
            STATUS  current
            DESCRIPTION
            "The md5 of the certificate indicated by alcatelIND1WebMgtCertFile.
            This value can be filled in when doing a set but it must match the md5
            of the file on the primary master CMM. This object will always return
            the default value."
            DEFVAL  { "" }
         ::= { alcatelIND1WebMgtCertObjects 2 } 


--
-- Trap definition
--

webMgtTrapsObj  OBJECT IDENTIFIER ::= { alcatelIND1WebMgtMIBObjects 7 }

  webMgtServerErrorTrap  NOTIFICATION-TYPE
      OBJECTS {
              webMgtServerError
            }
        STATUS  current
        DESCRIPTION
            "This trap is sent to management station(s) when the
             Web Management server goes into error state after
             crashing twice within a minute."
        ::= { alcatelIND1WebMgtMIBNotifications 1 }

  webMgtServerError  OBJECT-TYPE
      SYNTAX  SnmpAdminString (SIZE (0..127))
      MAX-ACCESS  read-only
      STATUS  current
      DESCRIPTION
            "Error code string of WebView Server error, same as alaIND1WebMgtServerError."
         ::= { webMgtTrapsObj 1 }


-- xxxxxxxxxxxxxxxxxxxxxxxxxxxxxxxxxxxxxxxxxxxxxxxxxxxxxxxxxx
-- COMPLIANCE
-- xxxxxxxxxxxxxxxxxxxxxxxxxxxxxxxxxxxxxxxxxxxxxxxx


alaIND1WebMgtConfigMIBCompliance MODULE-COMPLIANCE
    STATUS  current
    DESCRIPTION
        "Compliance statement for Learned Port Security."
    MODULE
        MANDATORY-GROUPS
        {
            alaIND1WebMgtConfigMIBGroup,
            alaIND1WebMgtNotificationGroup,
            alaIND1WebMgtConfigMIBCertGroup
        }
    ::= { alcatelIND1WebMgtMIBCompliances 1 }


-- xxxxxxxxxxxxxxxxxxxxxxxxxxxxxxxxxxxxxxxxxxxxxxxxxxxxxxxxxx
-- UNITS OF CONFORMANCE
-- xxxxxxxxxxxxxxxxxxxxxxxxxxxxxxxxxxxxxxxxxxxxxxxxxxxxxxxxxx

alaIND1WebMgtConfigMIBGroup OBJECT-GROUP
        OBJECTS
        {
            alaIND1WebMgtAdminStatus,
            alaIND1WebMgtSSL,
            alaIND1WebMgtHttpPort,
            alaIND1WebMgtHttpsPort,
            alaIND1WebMgtServerStatus,
            alaIND1WebMgtServerError,
            webMgtServerError,
            alaIND1WebMgtWlanIpPrecedence,
            alaIND1WebMgtWlanConfiguredIpAddressType,
            alaIND1WebMgtWlanConfiguredIpAddress,
            alaIND1WebMgtWlanLldpIpAddressType,
            alaIND1WebMgtWlanLldpIpAddress,
            alaIND1WebMgtSSLStrongCiphers,
            alaIND1WebMgtTlsVersion,
            alaIND1WebMgtInstallCertFilePath,
            alaIND1WebMgtCertificate
        }
        STATUS  current
        DESCRIPTION
            "Collection of objects for global configuration parameters defining
                         the behavior of the embedded web server."
        ::= { alcatelIND1WebMgtMIBGroups 1 }

alaIND1WebMgtNotificationGroup NOTIFICATION-GROUP
   NOTIFICATIONS
   {
       webMgtServerErrorTrap
   }
   STATUS  current
   DESCRIPTION
        "Collection of notifications for Web Management."
   ::= { alcatelIND1WebMgtMIBGroups 2 }

alaIND1WebMgtConfigMIBCertGroup OBJECT-GROUP
        OBJECTS
        {
            alcatelIND1WebMgtCertFile,
            alcatelIND1WebMgtCertMD5
        }
        STATUS  current
        DESCRIPTION
            "Collection of objects for global configuration parameters defining
                         the behavior of the embedded web server's SSL certificate."
        ::= { alcatelIND1WebMgtMIBGroups 3 }

END
