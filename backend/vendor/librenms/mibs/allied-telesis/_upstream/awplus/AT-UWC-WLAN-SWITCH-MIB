-- ============================================================================
-- AT-UWC-WLAN-SWITCH.MIB, Allied Telesis enterprise MIB: Wireless Controller
--
-- Copyright (c) 2014 by Allied Telesis, Inc.
-- Copyright (C) 2013 by Allied Telesis Holdings K.K.
-- Copyright 2001-2009 Broadcom Corporation.
-- All rights reserved.
--
-- ============================================================================

AT-UWC-WLAN-SWITCH-MIB DEFINITIONS ::= BEGIN

IMPORTS
    MODULE-IDENTITY, OBJECT-TYPE, NOTIFICATION-TYPE, IpAddress,
    Integer32, Unsigned32,Counter32,Counter64,TimeTicks
                                                    FROM SNMPv2-SMI
    RowStatus,TruthValue,DisplayString,
    MacAddress,TimeStamp,TEXTUAL-CONVENTION         FROM SNMPv2-TC
    wirelesslan, atUWC                              FROM AT-SMI-MIB;

    fastPathWLANSwitch MODULE-IDENTITY
        LAST-UPDATED "201412040000Z" -- 04 Dec 2014 12:00:00 GMT
        ORGANIZATION
          "Allied Telesis, Inc."
        CONTACT-INFO
          "  http://www.alliedtelesis.com"
        DESCRIPTION
          "The Allied Telesis Private MIB for AT-UWC"

        -- Revision history.
        REVISION
          "201412040000Z" -- 04 Dec 2014 12:00:00 GMT
        DESCRIPTION
          "3.0.4: Added enumerated values of the following MIB objects.
                    1. wsChannelPlanAPReasonCode
                    2. wsPowerPlanAPLastPwrAdjReasonCode"
        REVISION
          "201411070000Z" -- 07 Nov 2014 12:00:00 GMT
        DESCRIPTION
          "3.0.3: Changed enumerated values of wsAPCodeDownloadImageType."
        REVISION
          "201410290000Z" -- 29 Oct 2014 12:00:00 GMT
        DESCRIPTION
          "3.0.2: Added enumerated values of wsPowerPlanAPLastPwrAdjReasonCode."
        REVISION
          "201409300000Z" -- 30 Sep 2014 12:00:00 GMT
        DESCRIPTION
          "3.0.1: Changed the file name as below.
                    From: atkk-wlan-uwc-fastpathwlan.mib
                    To: at-uwc-wlan-switch.mib
                  Changed to import AT-SMI-MIB from ATKK-WLAN-SMI-MIB.
                  Changed for AW+ MIB standards."
        REVISION
          "201405290000Z" -- 29 May 2014 12:00:00 GMT
        DESCRIPTION
          "3.0.0: Supported for UWC Version 3.0.0"
        REVISION
          "201211290000Z" -- 29 Nov 2012 12:00:00 GMT
        DESCRIPTION
          "2.0.0: Supported for UWC Version 2.0.0"
        REVISION
          "201206150000Z" -- 15 Jun 2012 12:00:00 GMT
        DESCRIPTION
          "1.0.0: Initial version of this MIB module."

    ::= { atUWC 34 }

    at-uwc        OBJECT IDENTIFIER ::= { wirelesslan 21 }

--
-- Textual conventions
--
    WsOui ::= TEXTUAL-CONVENTION
      STATUS        current
      DESCRIPTION "24-bit Organizationally Unique Identifier.
                  Information on OUIs can be found in IEEE
                  802-2001 [802-2001] Clause 9."
      SYNTAX      OCTET STRING(SIZE(3))

    TspecSuppAC ::= TEXTUAL-CONVENTION
      STATUS        current
      DESCRIPTION
             "Access category (AC) used for TSPEC.  Only those ACs that
              support mandatory admission control are listed here."
      SYNTAX        INTEGER {
                      voice(0),
                      video(1)
                    }



-- -------------------------------------------------------------
-- MIB Objects
-- -------------------------------------------------------------

    wsTraps                                OBJECT IDENTIFIER ::= { fastPathWLANSwitch 0 }
    wsGlobalConfig                         OBJECT IDENTIFIER ::= { fastPathWLANSwitch 1 }
    discovery                              OBJECT IDENTIFIER ::= { fastPathWLANSwitch 2 }
    apProfile                              OBJECT IDENTIFIER ::= { fastPathWLANSwitch 3 }
    apCodeDownload                         OBJECT IDENTIFIER ::= { fastPathWLANSwitch 4 }
    rfManagement                           OBJECT IDENTIFIER ::= { fastPathWLANSwitch 5 }
    managedAP                              OBJECT IDENTIFIER ::= { fastPathWLANSwitch 6 }
    associatedClient                       OBJECT IDENTIFIER ::= { fastPathWLANSwitch 7 }
    peerSwitch                             OBJECT IDENTIFIER ::= { fastPathWLANSwitch 8 }
    intrusionDetection                     OBJECT IDENTIFIER ::= { fastPathWLANSwitch 9 }
    snmpTrapsConfig                        OBJECT IDENTIFIER ::= { fastPathWLANSwitch 10 }
    wsMibInfo                              OBJECT IDENTIFIER ::= { fastPathWLANSwitch 11 }
    wsCapability                           OBJECT IDENTIFIER ::= { fastPathWLANSwitch 12 }
    l2centTunnel                           OBJECT IDENTIFIER ::= { fastPathWLANSwitch 13 }
    wsOuiDatabase                          OBJECT IDENTIFIER ::= { fastPathWLANSwitch 14 }
    rrmNeighbor                            OBJECT IDENTIFIER ::= { fastPathWLANSwitch 15 }
    rrmChannelLoad                         OBJECT IDENTIFIER ::= { fastPathWLANSwitch 16 }
    tspec                                  OBJECT IDENTIFIER ::= { fastPathWLANSwitch 17 }
    provisioning                           OBJECT IDENTIFIER ::= { fastPathWLANSwitch 18 }
    wdsManagedAP                           OBJECT IDENTIFIER ::= { fastPathWLANSwitch 19 }
    deviceLocation                         OBJECT IDENTIFIER ::= { fastPathWLANSwitch 20 }
    authenticatedClient                    OBJECT IDENTIFIER ::= { fastPathWLANSwitch 21 }

--
-- MIB module version (for NMS convenience)
--

wsMibVersion OBJECT-TYPE
    SYNTAX Integer32
    MAX-ACCESS read-only
    STATUS current
    DESCRIPTION
        "The version number of this MIB module"
    ::= { wsMibInfo 1 }

--**************************************************************************************
-- wsGlobalGroup
--**************************************************************************************
    wsMode    OBJECT-TYPE
         SYNTAX      INTEGER {
                       enable(1),
                       disable(2)
                     }
         MAX-ACCESS  read-only
         STATUS      current
         DESCRIPTION
                     "Flag to enable/disable wireless controller functionality
                      on the device. Disable will purge all status and statistics
                      related to wireless functionality."
         DEFVAL      { disable }
         ::= { wsGlobalConfig 1 }

    wsCountryCode    OBJECT-TYPE
         SYNTAX      DisplayString (SIZE(2))
         MAX-ACCESS  read-only
         STATUS      current
         DESCRIPTION
                     "This object indicates country of operation for WLAN. Supported
                      country codes are:
                       Australia - AU, Austria - AT,  Austria - AT,
                       Belgium - BE, Brazil - BR, Canada - CA,
                       China - CN, Czech Republic - CZ, Denmark - DK,
                       Finland - FI, France - FR, Germany - DE,
                       Greece - GR, Hong Kong - HK, Hungary - HU,
                       Iceland - IS, India - IN, Ireland - IE,
                       Israel - IL, Italy - IT, Japan - JP,
                       Liechtenstein - LI,Luxembourg - LU,Malaysia - MY,
                       Mexico - MX, Netherlands - NL, New Zealand - NZ,
                       Norway - NO, Poland - PL, Portugal - PT,
                       Saudi Arabia - SA, Singapore - SG, Slovakia - SK,
                       Slovenia - SI, South Africa - ZA, South Korea - KR,
                       Spain - ES, Sweden - SE, Switzerland - CH,
                       Taiwan - TW, Thailand - TH, United Arab Emirates - AE,
                       United Kingdom - GB, United States - US."
         DEFVAL      { "US" }
         ::= { wsGlobalConfig 2 }

-- Object not supported in SMB builds
    wsPeerGroupId    OBJECT-TYPE
         SYNTAX      Integer32(1..255)
         MAX-ACCESS  read-only
         STATUS      current
         DESCRIPTION
                     "This object indicates which peer group this controller belongs to, there
                      may be more than one group of peer controllers in the WLAN."
         DEFVAL      { 1 }
         ::= { wsGlobalConfig 3 }

    wsAPValidationMethod    OBJECT-TYPE
         SYNTAX     INTEGER {
                         local(1),
                         radius(2)
                    }
         MAX-ACCESS  not-accessible
         STATUS      current
         DESCRIPTION
                     "This object indicates whether or not to verify newly discovered APs
                      and look up their configuration against the local database
                      or a RADIUS server."
         DEFVAL      { local }
         ::= { wsGlobalConfig 4 }

    wsAPAuthenticationMode    OBJECT-TYPE
         SYNTAX     INTEGER {
                         enable(1),
                         disable(2)
                    }
         MAX-ACCESS  read-only
         STATUS      current
         DESCRIPTION
                     "Flag to indicate if authentication is required for an AP to
                      establish communication with the controller."
         DEFVAL      { disable }
         ::= { wsGlobalConfig 5 }

    wsClientRoamAgeTime    OBJECT-TYPE
         SYNTAX     Unsigned32(1..120)
         MAX-ACCESS  read-only
         STATUS      current
         DESCRIPTION
                  "Time in seconds to wait after a client disassociates from a
                   managed AP before deleting the client association
                   database entry."
         DEFVAL      { 30 }
         ::= { wsGlobalConfig 6 }

    wsRFScanAgeTime    OBJECT-TYPE
         SYNTAX     Unsigned32(0..168)
         MAX-ACCESS  read-only
         STATUS      current
         DESCRIPTION
                  "Time in hours to wait before deleting an entry
                   obtained from an RF scan.A value of 0 in input range means that the entry never ages out."
         DEFVAL      { 24 }
         ::= { wsGlobalConfig 7 }

    wsAPFailureAgeTime    OBJECT-TYPE
         SYNTAX     Unsigned32(0..168)
         MAX-ACCESS  read-only
         STATUS      current
         DESCRIPTION
                  "Time in hours to wait before deleting an entry in
                   the AP association and authentication failure list.
                   A value of 0 in input range means that the entry never ages out."
         DEFVAL      { 24 }
         ::= { wsGlobalConfig 8 }

    wsAdHocClientAgeTime    OBJECT-TYPE
         SYNTAX     Unsigned32(0..168)
         MAX-ACCESS  not-accessible
         STATUS      current
         DESCRIPTION
                  "Time in hours to wait before deleting an entry in
                   Ad hoc client list.A value of 0 in input range means that the entry never ages out."
         DEFVAL      { 24 }
         ::= { wsGlobalConfig 9 }

    wsDetectedClientAgeTime    OBJECT-TYPE
         SYNTAX     Unsigned32(0..168)
         MAX-ACCESS  read-only
         STATUS      current
         DESCRIPTION
                  "Time in hours to wait before deleting an entry
                   from the detected clients database.A value of 0 in input range means that the entry never ages out."
         DEFVAL      { 24 }
         ::= { wsGlobalConfig 10 }

--
--  wsValidAPConfigTable
--
 wsValidAPConfigTable OBJECT-TYPE
     SYNTAX       SEQUENCE OF WsValidAPConfigEntry
     MAX-ACCESS   not-accessible
     STATUS       current
     DESCRIPTION
          "This table contains configurable parameters for a specific AP.
           When an AP is discovered and the wsValidationMethod is local,
           its MAC address is verified in this table to determine if it
           should be managed by the controller."
     ::= { wsGlobalConfig 11 }

 wsValidAPConfigEntry OBJECT-TYPE
     SYNTAX       WsValidAPConfigEntry
     MAX-ACCESS   not-accessible
     STATUS       current
     DESCRIPTION
         "Each entry has parameters that can be configured locally or
          on a RADIUS server, for a specific AP on the WLAN.

          As this table is indexed by wsAPMacAddress,
          - to create an entry, specify the AP MAC address and set object wsAPConfigRowStatus to createAndGo(4)
          - to delete an entry, select the entry from the list and set object wsAPConfigRowStatus to destroy(6)"
     INDEX    { wsAPMacAddress }
     ::= { wsValidAPConfigTable 1 }

 WsValidAPConfigEntry ::=
     SEQUENCE {
         wsAPMacAddress                   MacAddress,
         wsAPLocation                     DisplayString,
         wsAPMode                         INTEGER,
         wsAPAuthenticationPasswd         DisplayString,
         wsUseAPProfileId                 Integer32,
         wsAPRadio1Channel                Integer32,
         wsAPRadio2Channel                Integer32,
         wsAPRadio1TxPower                Integer32,
         wsAPRadio2TxPower                Integer32,
         wsAPStandaloneExpectedChannel    Integer32,
         wsAPStandaloneExpectedSecurity   INTEGER,
         wsAPStandaloneExpectedSsid       DisplayString,
         wsAPStandaloneExpectedWds        INTEGER,
         wsAPStandaloneExpectedWired      INTEGER,
         wsAPConfigRowStatus              RowStatus
 }

 wsAPMacAddress OBJECT-TYPE
     SYNTAX       MacAddress
     MAX-ACCESS   read-only
     STATUS       current
     DESCRIPTION
        "MAC address of an AP."
     ::= { wsValidAPConfigEntry 1 }

 wsAPLocation OBJECT-TYPE
     SYNTAX       DisplayString(SIZE(0..32))
     MAX-ACCESS   read-only
     STATUS       current
     DESCRIPTION
        "This object indicates description of an AP, often based on its location."
     ::= { wsValidAPConfigEntry 2 }

 wsAPMode OBJECT-TYPE
     SYNTAX       INTEGER {
                     wsManaged(1),
                     standalone(2),
                     rogue(3)
                 }
     MAX-ACCESS   read-only
     STATUS       current
     DESCRIPTION
        "This field indicates whether this AP is managed
        by the controller, by an administrator, or is a Rogue AP."
     DEFVAL    { wsManaged }
     ::= { wsValidAPConfigEntry 3 }

wsAPAuthenticationPasswd OBJECT-TYPE
     SYNTAX       DisplayString(SIZE(8..63))
     MAX-ACCESS   read-only
     STATUS       current
     DESCRIPTION
        "If AP authentication is enabled, this indicates the
         password for an AP to authenticate to the controller.
         This must match the password configured on an AP.
         When passwod is configured this object will always
         return '*****'."
     ::= { wsValidAPConfigEntry 4 }

 wsUseAPProfileId OBJECT-TYPE
     SYNTAX       Integer32(1..16)
     MAX-ACCESS   read-only
     STATUS       current
     DESCRIPTION
        "If AP is managed by controller, this object indicates
        Id of configuration profile for this AP."
     ::= { wsValidAPConfigEntry 5 }

 wsAPRadio1Channel OBJECT-TYPE
     SYNTAX       Integer32(0..14|36|40|42|44|48|50|52|56|58|60|
                            64|100|104|108|112|116|120|124|128|132|
                            136|140|149|152|153|157|160|161|165)
     MAX-ACCESS   read-only
     STATUS       current
     DESCRIPTION
        "This object indicates the fixed channel for the AP
         radio one. Zero indicates automatic channel
         assignment."
     DEFVAL       { 0 }
     ::= { wsValidAPConfigEntry 6 }

 wsAPRadio2Channel OBJECT-TYPE
     SYNTAX       Integer32(0..14|36|40|42|44|48|50|52|56|58|60|
                            64|100|104|108|112|116|120|124|128|132|
                            136|140|149|152|153|157|160|161|165)
     MAX-ACCESS   read-only
     STATUS       current
     DESCRIPTION
        "This object indicates the fixed channel for the AP
         radio two. Zero indicates automatic channel
         assignment."
     DEFVAL       { 0 }
     ::= { wsValidAPConfigEntry 7 }

 wsAPRadio1TxPower OBJECT-TYPE
     SYNTAX       Integer32(0..100)
     MAX-ACCESS  read-only
     STATUS       current
     DESCRIPTION
        "This indicates the power setting of AP radio one.
         Zero indicates automatic power adjustment."
     DEFVAL { 0 }
     ::= { wsValidAPConfigEntry 8 }

 wsAPRadio2TxPower OBJECT-TYPE
     SYNTAX       Integer32(0..100)
     MAX-ACCESS  read-only
     STATUS       current
     DESCRIPTION
        "This indicates the power setting of AP radio two.
         Zero indicates automatic power adjustment."
     DEFVAL { 0 }
     ::= { wsValidAPConfigEntry 9 }

 wsAPStandaloneExpectedChannel OBJECT-TYPE
     SYNTAX       Integer32(0..14|36|40|42|44|48|50|52|56|58|60|
                            64|100|104|108|112|116|120|124|128|132|
                            136|140|149|152|153|157|160|161|165)
     MAX-ACCESS   read-only
     STATUS       current
     DESCRIPTION
        "This object indicates the expected channel for the AP
         in standalone mode. Zero indicates that any channel is allowed."
     DEFVAL       { 0 }
     ::= { wsValidAPConfigEntry 10 }

 wsAPStandaloneExpectedSecurity OBJECT-TYPE
     SYNTAX       INTEGER {
                     any(0),
                     open(1),
                     wep(2),
                     wpa(3)
                 }
     MAX-ACCESS   read-only
     STATUS       current
     DESCRIPTION
        "This object indicates the expected security mode for the AP
         in standalone mode. Zero indicates that any security mode is allowed."
     DEFVAL    { any }
     ::= { wsValidAPConfigEntry 11 }

 wsAPStandaloneExpectedSsid OBJECT-TYPE
     SYNTAX       DisplayString(SIZE(0..32))
     MAX-ACCESS   read-only
     STATUS       current
     DESCRIPTION
        "This object indicates the expected SSID for the AP
         in standalone mode. A null string indicates that any
         SSID is allowed."
     ::= { wsValidAPConfigEntry 12 }

 wsAPStandaloneExpectedWds OBJECT-TYPE
     SYNTAX       INTEGER {
                     any(0),
                     normal(1),
                     bridge(2)
                 }
     MAX-ACCESS   read-only
     STATUS       current
     DESCRIPTION
        "This object indicates whether the AP is allowed to operate as a bridge.
         Configurable values are:
         any  Either WDS or normal mode is allowed
         normal - AP is not allowed to operate in WDS mode
         bridge - AP is only allowed to operate in WDS mode"
     DEFVAL    { any }
     ::= { wsValidAPConfigEntry 13 }

 wsAPStandaloneExpectedWired OBJECT-TYPE
     SYNTAX       INTEGER {
                     allowed(0),
                     not-allowed(1)
                 }
     MAX-ACCESS   read-only
     STATUS       current
     DESCRIPTION
        "This object indicates the expected wired network mode for the AP
         in standalone mode."
     DEFVAL    { allowed }
     ::= { wsValidAPConfigEntry 14 }

 wsAPConfigRowStatus OBJECT-TYPE
     SYNTAX       RowStatus
     MAX-ACCESS   read-only
     STATUS       current
     DESCRIPTION
        "This object is used to create or delete entries in the table.
         The supported values are:

         active(1)      - indicates a valid entry
         createAndGo(4) - creates a new entry in the table
         destroy(6)     - removes an existing entry from the table

         As this table is indexed by wsAPMacAddress,
         - to create an entry, specify the AP MAC address and set object value to createAndGo(4)
         - to delete an entry, select the entry from the list and set object value to destroy(6)"
     ::= { wsValidAPConfigEntry 15 }

--
--  wsGlobalStatus
--
   wsGlobalStatus                        OBJECT IDENTIFIER ::= { wsGlobalConfig 12 }

 wsIPAddress OBJECT-TYPE
     SYNTAX       IpAddress
     MAX-ACCESS   read-only
     STATUS       current
     DESCRIPTION
        "This object represents wireless controller IP address.
         When wireless mode is in disabled state, the value
         of controller IP address is zero."
     ::= { wsGlobalStatus 1 }

 wsOperationalStatus OBJECT-TYPE
     SYNTAX       INTEGER {
                     enabled(1),
                     enable-pending(2),
                     disabled(3),
                     disable-pending(4)
                  }
     MAX-ACCESS   read-only
     STATUS       current
     DESCRIPTION
        "Indicates the current operating status of the wireless
         system."
     ::= { wsGlobalStatus 2 }

 wsOperationalStatusDisableReason OBJECT-TYPE
     SYNTAX       INTEGER {
                    none(1),
                    admin-disabled(2),
                    no-ipAddress(3),
                    no-sslFiles(4),
                    no-loopback-interface(5),
                    routing-disabled(6),
                    no-active-interface(7)
                  }
     MAX-ACCESS   read-only
     STATUS       current
     DESCRIPTION
        "This object indicates the reason of operational status to be disabled.
         Values 5 and 6 are applicable only if routing functionality present."
     ::= { wsGlobalStatus 3 }

-- Object not supported in SMB builds
    wsTotalPeerSwitches    OBJECT-TYPE
         SYNTAX      Integer32(0..4)
         MAX-ACCESS  read-only
         STATUS      current
         DESCRIPTION
               "Total number of peer controllers detected on the
                network."
         ::= { wsGlobalStatus 4 }

   wsTotalAPs  OBJECT-TYPE
         SYNTAX      Unsigned32
         MAX-ACCESS  read-only
         STATUS      current
         DESCRIPTION
               "Sum of all the WS managed APs, connection failed APs, and
               discovered APs in the database."
         ::= { wsGlobalStatus 5 }

   wsTotalManagedAPs  OBJECT-TYPE
         SYNTAX      Integer32(0..48)
         MAX-ACCESS  read-only
         STATUS      current
         DESCRIPTION
               "Total number of WS managed APs currently
                authenticated to the controller."
         ::= { wsGlobalStatus 6 }

   wsTotalStandaloneAPs    OBJECT-TYPE
         SYNTAX      Unsigned32
         MAX-ACCESS  read-only
         STATUS      current
         DESCRIPTION
               "Total number of trusted AP's in the standalone mode."
         ::= { wsGlobalStatus 7 }

   wsTotalDiscoveredAPs    OBJECT-TYPE
         SYNTAX      Unsigned32
         MAX-ACCESS  read-only
         STATUS      current
         DESCRIPTION
               "Number of APs that are connected to the controller,
               but are not completely configured."
         ::= { wsGlobalStatus 8 }

   wsTotalConnectionFailedAPs  OBJECT-TYPE
         SYNTAX      Unsigned32
         MAX-ACCESS  read-only
         STATUS      current
         DESCRIPTION
               "Number of APs that were previously authenticated and managed,
               but currently do not have connection with the controller."
         ::= { wsGlobalStatus 9 }

    wsTotalRogueAPs    OBJECT-TYPE
         SYNTAX      Unsigned32
         MAX-ACCESS  read-only
         STATUS      current
         DESCRIPTION
               "Total number of Rogue APs detected on the WLAN."
         ::= { wsGlobalStatus 10 }

    wsTotalUnknownAPs    OBJECT-TYPE
         SYNTAX      Unsigned32
         MAX-ACCESS  read-only
         STATUS      current
         DESCRIPTION
               "Total number of Unknown APs detected on the WLAN."
         ::= { wsGlobalStatus 11 }

    wsMaximumManagedAPsInPeerGroup    OBJECT-TYPE
         SYNTAX      Unsigned32
         MAX-ACCESS  read-only
         STATUS      current
         DESCRIPTION
               "Maximum number of APs that can be managed by the wireless
               controller when it acts as Cluster Controller."
         ::= { wsGlobalStatus 12 }

   wsTotalClients  OBJECT-TYPE
         SYNTAX      Unsigned32
         MAX-ACCESS  read-only
         STATUS      current
         DESCRIPTION
               "Total number of clients present in the network."
         ::= { wsGlobalStatus 13 }

   wsTotalAuthenticatedClients  OBJECT-TYPE
         SYNTAX      Unsigned32
         MAX-ACCESS  read-only
         STATUS      current
         DESCRIPTION
               "Total number of authenticated clients across
               all APs managed by the controller."
         ::= { wsGlobalStatus 14 }

   wsMaximumAssociatedClients  OBJECT-TYPE
         SYNTAX      Unsigned32
         MAX-ACCESS  read-only
         STATUS      current
         DESCRIPTION
               "Maximum number of clients that can associate with the wireless system."
         ::= { wsGlobalStatus 15 }

   wsWLANUtilization    OBJECT-TYPE
         SYNTAX      Integer32(0..100)
         MAX-ACCESS  read-only
         STATUS      current
         DESCRIPTION
             "Total network utilization across all APs managed by
              this controller. This is based on global statistics."
         ::= { wsGlobalStatus 16 }


 wsGlobalStatusRegulatoryDomainFor2GHz OBJECT-TYPE
     SYNTAX       DisplayString(SIZE(8..32))
     MAX-ACCESS   read-only
     STATUS       current
     DESCRIPTION
          " Regulatory domain for 2GHz frequency channels."
     ::= { wsGlobalStatus 18 }

 wsGlobalStatusRegulatoryDomainFor5GHz OBJECT-TYPE
     SYNTAX       DisplayString(SIZE(8..32))
     MAX-ACCESS   read-only
     STATUS       current
     DESCRIPTION
          " Regulatory domain for 5GHz frequency channels."
     ::= { wsGlobalStatus 19 }

--
-- Global Status for Config Push
--

-- Object not supported in SMB builds
  wsGlobalPeerConfigRequestAction    OBJECT-TYPE
         SYNTAX      INTEGER {
                       none(1),
                       start(2)
                     }
         MAX-ACCESS  read-only
         STATUS      current
         DESCRIPTION
             "This action object is used to:
                - start - Start the config push into all the peer controllers in the peer
                  group.
                - Read on this object will always return none."
         DEFVAL      { none }
         ::= { wsGlobalStatus 20 }

-- Object not supported in SMB builds
   wsGlobalPeerConfigRequestStatus    OBJECT-TYPE
         SYNTAX      INTEGER {
                        notStarted(0),
                        requested(1),
                        savingConfig(2),
                        sendingConfig(3),
                        applyingAPprofileConfig(4),
                        complete(5)
                     }
         MAX-ACCESS  read-only
         STATUS      current
         DESCRIPTION
             "The global status for the configuration push operation to
              one or more peer controllers."
         DEFVAL      { notStarted }
         ::= { wsGlobalStatus 21 }

-- Object not supported in SMB builds
   wsGlobalPeerConfigReceiveStatus    OBJECT-TYPE
         SYNTAX      INTEGER {
                        notStarted(0),
                        receivingConfig(1),
                        savingConfig(2),
                        applyingAPprofileConfig(3),
                        failureInvalidCodeVersion(4),
                        failureInvalidHwVersion(5),
                        failureInvalidConfig(6),
                        failureInvalidPacketFormat(7),
                        failureTimeout(8),
                        success(9)
                     }
         MAX-ACCESS  read-only
         STATUS      current
         DESCRIPTION
             "The global status when wireless configuration is received
             from a peer controller."
         DEFVAL      { notStarted }
         ::= { wsGlobalStatus 22 }

-- Object not supported in SMB builds
   wsGlobalPeerConfigSwitchIp    OBJECT-TYPE
         SYNTAX      IpAddress
         MAX-ACCESS  read-only
         STATUS      current
         DESCRIPTION
             "IP Address of the last controller from which this controller received
             any wireless configuration data."
         ::= { wsGlobalStatus 23 }

-- Object not supported in SMB builds
    wsGlobalPeerConfigReceived    OBJECT-TYPE
         SYNTAX      BITS  {
                        none (1),
                        globalConfig(2),
                        discoveryConfig(3),
                        validAPDatabase(4),
                        channelPowerConfig(5),
                        profileNetworkConfig(6),
                        knownClientConfig(7),
                        captivePortalConfig(8),
                        radiusClientConfig(9),
                        qosAclConfig(10),
                        qosDiffServConfig(11),
                        wdsGroupConfig(12),
                        deviceLocationConfig(13)
                        }

         MAX-ACCESS  read-only
         STATUS      current
         DESCRIPTION
         "Indicates which portions of configuration were last received from a
          peer controller."
         ::= { wsGlobalStatus 24 }

-- Object not supported in SMB builds
    wsGlobalPeerConfigReceivedTimestamp    OBJECT-TYPE
         SYNTAX      DisplayString
         MAX-ACCESS  read-only
         STATUS      current
         DESCRIPTION
         "The last time this controller received any configuration data from a
          peer controller."
         ::= { wsGlobalStatus 25 }

    wsClusterControllerIndicator   OBJECT-TYPE
        SYNTAX       INTEGER {
                     yes(1),
                     no(2)
                  }
         MAX-ACCESS  read-only
         STATUS      current
         DESCRIPTION
             "Indicates if the controller is currently the Cluster Controller of the
              peer group or not."
         ::= { wsGlobalStatus 26 }

  wsClusterController    OBJECT-TYPE
         SYNTAX       IpAddress
         MAX-ACCESS   read-only
         STATUS       current
         DESCRIPTION
             "This object represents Cluster Controller's IP address."
         ::= { wsGlobalStatus 27 }


    wsRogueAPMitigationCount    OBJECT-TYPE
         SYNTAX      Unsigned32
         MAX-ACCESS  read-only
         STATUS      current
         DESCRIPTION
               "Number of APs to which the wireless system is
                currently sending de-authentication messages
                to mitigate against rogue APs."
         ::= { wsGlobalStatus 28 }

    wsRogueAPMitigationLimit    OBJECT-TYPE
         SYNTAX      Unsigned32
         MAX-ACCESS  read-only
         STATUS      current
         DESCRIPTION
               "Maximum number of APs for which the system
                can send de-authentication frames."
         ::= { wsGlobalStatus 29 }

     wsRogueAPAcknowledgeAll OBJECT-TYPE
         SYNTAX      INTEGER {
                     no-action(0),
                     acknowledge(1)
                  }
         MAX-ACCESS  read-only
         STATUS      current
         DESCRIPTION
                     "This is a command that allows the administrator
                      to clear out all rogue AP states in the RF Scan database"
         ::= { wsGlobalStatus 30 }
--
-- Global Config Push ends
--

   wsTotalDetectedClients  OBJECT-TYPE
         SYNTAX      Unsigned32
         MAX-ACCESS  read-only
         STATUS      current
         DESCRIPTION
               "Total number of detected clients across
               all APs managed by the controller."
         ::= { wsGlobalStatus 31 }

   wsMaximumDetectedClients  OBJECT-TYPE
         SYNTAX      Unsigned32
         MAX-ACCESS  read-only
         STATUS      current
         DESCRIPTION
               "Maximum number of clients that can be maintained
                by the detected clients database."
         ::= { wsGlobalStatus 32 }

  wsMaximumDetectedClientPreAuthenticationHistoryEntries OBJECT-TYPE
         SYNTAX      Unsigned32
         MAX-ACCESS  read-only
         STATUS      current
         DESCRIPTION
               "Maximum number of pre-authentication history entries that
               can be recorded for all the detected clients present in
               the detected client database."
     ::= { wsGlobalStatus 33 }

  wsTotalDetectedClientPreAuthenticationHistoryEntries OBJECT-TYPE
         SYNTAX      Unsigned32
         MAX-ACCESS  read-only
         STATUS      current
         DESCRIPTION
               "Total number of pre-authentication history entries
               accumulated for all the detected clients present in the
               detected client database."
     ::= { wsGlobalStatus 34 }

  wsMaximumDetectedClientRoamHistoryEntries OBJECT-TYPE
         SYNTAX      Unsigned32
         MAX-ACCESS  read-only
         STATUS      current
         DESCRIPTION
               "Maximum number of roam history entries that
               can be recorded for all the detected clients present in
               the detected client database."
     ::= { wsGlobalStatus 35 }

  wsTotalDetectedClientRoamHistoryEntries OBJECT-TYPE
         SYNTAX      Unsigned32
         MAX-ACCESS  read-only
         STATUS      current
         DESCRIPTION
               "Total number of roam history entries accumulated for all
               the detected clients present in the detected client database."
     ::= { wsGlobalStatus 36 }

  wsRegenerateX509CertificateAction OBJECT-TYPE
        SYNTAX              INTEGER {
                              none(1),
                              start(2)
                            }
        MAX-ACCESS          not-accessible
        STATUS              current
        DESCRIPTION
        "This action object is used to:
                - start - Start the certificate regeneration on the controller.
                - Read on this object will always return none."
         DEFVAL      { none }
        ::= { wsGlobalStatus 37 }

  wsRegenerateX509CertificateStatus  OBJECT-TYPE
        SYNTAX              INTEGER {
                              not-in-progress(1),
                              started(2),
                              in-progress(3)
                            }
        MAX-ACCESS          not-accessible
        STATUS              current
        DESCRIPTION
          "Status of regenerate X.509 certificates."
        DEFVAL              { not-in-progress }
        ::= { wsGlobalStatus 38 }

 wsNetworkMutualAuthenticationStatus  OBJECT-TYPE
        SYNTAX              INTEGER {
                              not-started(1),
                              exchange-start(2),
                              in-progress(3),
                              provisioning-in-progress(4),
                              exchange-in-progress(5),
                              provisioning-complete(6),
                              exchange-complete(7),
                              complete-without-errors(8),
                              complete-with-errors-refer-to-event-log-for-details(9)
                            }
        MAX-ACCESS          not-accessible
        STATUS              current
        DESCRIPTION
          "Status of the mutual authentication enable/disable command.
          When status is Complete With Errors then the administrator
          may need to provision some controllers or APs separately."
        DEFVAL              { not-started }
        ::= { wsGlobalStatus 39 }

   wsTotalProvisioningAPs  OBJECT-TYPE
         SYNTAX      Unsigned32
         MAX-ACCESS  not-accessible
         STATUS      current
         DESCRIPTION
               "Total number of APs present in
               the AP Provisioning database."
         ::= { wsGlobalStatus 40 }

   wsMaximumProvisioningAPs  OBJECT-TYPE
         SYNTAX      Unsigned32
         MAX-ACCESS  not-accessible
         STATUS      current
         DESCRIPTION
               "Maximum number of APs that can be
                maintained in the AP Provisioning
                database."
         ::= { wsGlobalStatus 41 }

--
--  wsGlobalStatistics
--
   wsGlobalStatistics                        OBJECT IDENTIFIER ::= { wsGlobalConfig 13 }

    wsTotalWLANBytesTransmitted    OBJECT-TYPE
         SYNTAX      Counter64
         MAX-ACCESS  read-only
         STATUS      current
         DESCRIPTION
              "Total bytes transmitted across all APs managed by
               this controller."
         ::= { wsGlobalStatistics 1 }

    wsTotalWLANBytesRecvd    OBJECT-TYPE
         SYNTAX      Counter64
         MAX-ACCESS  read-only
         STATUS      current
         DESCRIPTION
              "Total bytes received across all APs managed by
               by this controller."
         ::= { wsGlobalStatistics 2 }

    wsTotalWLANPktsTransmitted    OBJECT-TYPE
         SYNTAX      Counter64
         MAX-ACCESS  read-only
         STATUS      current
         DESCRIPTION
              "Total packets transmitted across all APs managed by
               this controller."
         ::= { wsGlobalStatistics 3 }

    wsTotalWLANPktsRecvd    OBJECT-TYPE
         SYNTAX      Counter64
         MAX-ACCESS  read-only
         STATUS      current
         DESCRIPTION
              "Total packets received across all APs managed by
               this controller."
         ::= { wsGlobalStatistics 4 }

    wsAllStatisticsReset    OBJECT-TYPE
         SYNTAX      INTEGER {
                        enable(1),
                        disable(2)
                     }
         MAX-ACCESS  read-write
         STATUS      current
         DESCRIPTION
                  "When we set this object to enable, all statistics maintained by
                   controller will be cleared. Read on this object will always
                   return disable."
         ::= { wsGlobalStatistics 5 }

     wsAllStatisticsResetStatus    OBJECT-TYPE
         SYNTAX      INTEGER {
                        not-started(0),
                        requested(1),
                        in-progress(2),
                        success(3),
                        partial-success(4),
                        failure(5)
                     }
         MAX-ACCESS  read-only
         STATUS      current
         DESCRIPTION
                  "This object indicates the current status of controller statistics
                   reset request. Default value is not started."
         ::= { wsGlobalStatistics 6 }

    wsTotalWLANBytesTransmitDropped    OBJECT-TYPE
         SYNTAX      Counter64
         MAX-ACCESS  read-only
         STATUS      current
         DESCRIPTION
              "Total bytes dropped in the transmit direction across all APs
               managed by this controller.  This is due to client QoS actions
               affecting the wireless down (outbound) direction from AP to client."
         ::= { wsGlobalStatistics 7 }

    wsTotalWLANBytesRecvDropped    OBJECT-TYPE
         SYNTAX      Counter64
         MAX-ACCESS  read-only
         STATUS      current
         DESCRIPTION
              "Total bytes dropped in the receive direction across all APs
               managed by this controller.  This is due to client QoS actions
               affecting the wireless up (inbound) direction from AP to client."
         ::= { wsGlobalStatistics 8 }

    wsTotalWLANPktsTransmitDropped    OBJECT-TYPE
         SYNTAX      Counter64
         MAX-ACCESS  read-only
         STATUS      current
         DESCRIPTION
              "Total packets dropped in the transmit direction across all APs
               managed by this controller.  This is due to client QoS actions
               affecting the wireless down (outbound) direction from AP to client."
         ::= { wsGlobalStatistics 9 }

    wsTotalWLANPktsRecvDropped    OBJECT-TYPE
         SYNTAX      Counter64
         MAX-ACCESS  read-only
         STATUS      current
         DESCRIPTION
              "Total packets dropped in the receive direction across all APs
               managed by this controller.  This is due to client QoS actions
               affecting the wireless up (inbound) direction from AP to client."
         ::= { wsGlobalStatistics 10 }

   wsTotalWLANDistTunnelPktsTransmitted    OBJECT-TYPE
         SYNTAX      Counter64
         MAX-ACCESS  read-only
         STATUS      current
         DESCRIPTION
              "Total number of packets transmitted by all APs using
               distributed tunnels."
         ::= { wsGlobalStatistics 11 }

   wsTotalWLANDistTunnelRoamedClients    OBJECT-TYPE
         SYNTAX      Unsigned32
         MAX-ACCESS  read-only
         STATUS      current
         DESCRIPTION
              "Number of clients in all APs currently in roaming state using
               distributed tunnels."
         ::= { wsGlobalStatistics 12 }

   wsTotalWLANDistTunnelClientDenials    OBJECT-TYPE
         SYNTAX      Unsigned32
         MAX-ACCESS  read-only
         STATUS      current
         DESCRIPTION
              "Number of client tunnel setups denied for all APs."
         ::= { wsGlobalStatistics 13 }

--
-- Global Peer Configuration Push
--
   wsPeerConfiguration                OBJECT IDENTIFIER ::= { wsGlobalConfig 14 }

-- Object not supported in SMB builds
wsPeerConfigurationGlobal       OBJECT-TYPE
         SYNTAX      INTEGER {
                       enable(1),
                       disable(2)
                     }
         MAX-ACCESS  read-only
         STATUS      current
         DESCRIPTION
                     "Flag to enable/disable the functionality  to send global
                      configuration parameters to a peer controller on a
                      configuration push."
         DEFVAL      { enable }
         ::= { wsPeerConfiguration 1 }

-- Object not supported in SMB builds
wsPeerConfigurationDiscovery    OBJECT-TYPE
         SYNTAX      INTEGER {
                       enable(1),
                       disable(2)
                     }
         MAX-ACCESS  read-only
         STATUS      current
         DESCRIPTION
                     "Flag to enable/disable the functionality  to send
                      discovery configuration parameters to a peer controller on
                      a configuration push."
         DEFVAL      { disable }
         ::= { wsPeerConfiguration 2 }

-- Object not supported in SMB builds
wsPeerConfigurationAPDatabase    OBJECT-TYPE
         SYNTAX      INTEGER {
                       enable(1),
                       disable(2)
                     }
         MAX-ACCESS  read-only
         STATUS      current
         DESCRIPTION
                     "Flag to enable/disable the functionality  to send
                      valid AP Database to a peer controller on a configuration
                      push."
         DEFVAL      { enable }
         ::= { wsPeerConfiguration 3 }

-- Object not supported in SMB builds
wsPeerConfigurationChannelPower    OBJECT-TYPE
         SYNTAX      INTEGER {
                       enable(1),
                       disable(2)
                     }
         MAX-ACCESS  read-only
         STATUS      current
         DESCRIPTION
                     "Flag to enable/disable the functionality  to send
                      Channel and Power configuration to a peer controller on
                      a configuration push."
         DEFVAL      { enable }
         ::= { wsPeerConfiguration 4 }


-- Object not supported in SMB builds
wsPeerConfigurationAPProfiles    OBJECT-TYPE
         SYNTAX      INTEGER {
                       enable(1),
                       disable(2)
                     }
         MAX-ACCESS  read-only
         STATUS      current
         DESCRIPTION
                     "Flag to enable/disable the functionality  to send
                      all AP profiles and networks to a peer controller on a
                      configuration push."
         DEFVAL      { enable }
         ::= { wsPeerConfiguration 5 }

-- Object not supported in SMB builds
wsPeerConfigurationKnownClients       OBJECT-TYPE
         SYNTAX      INTEGER {
                       enable(1),
                       disable(2)
                     }
         MAX-ACCESS  read-only
         STATUS      current
         DESCRIPTION
                     "Flag to enable/disable the functionality to send configured
                      known client entries to a peer controller on a configuration push."
         DEFVAL      { enable }
         ::= { wsPeerConfiguration 6 }

-- Object not supported in SMB builds
wsPeerConfigurationCaptivePortal    OBJECT-TYPE
         SYNTAX      INTEGER {
                       enable(1),
                       disable(2)
                     }
         MAX-ACCESS  read-only
         STATUS      current
         DESCRIPTION
                     "Flag to enable/disable the functionality  to send
                      all Captive Portal configuration to a peer controller on a
                      configuration push."
         DEFVAL      { enable }
         ::= { wsPeerConfiguration 7 }

-- Object not supported in SMB builds
wsPeerConfigurationRadiusClient    OBJECT-TYPE
         SYNTAX      INTEGER {
                       enable(1),
                       disable(2)
                     }
         MAX-ACCESS  read-only
         STATUS      current
         DESCRIPTION
                     "Flag to enable/disable the functionality  to send
                      RADIUS Client configuration parameters to a peer controller
                      on a configuration push."
         DEFVAL      { enable }
         ::= { wsPeerConfiguration 8 }

-- Object not supported in SMB builds
wsPeerConfigurationQosAcl    OBJECT-TYPE
         SYNTAX      INTEGER {
                       enable(1),
                       disable(2)
                     }
         MAX-ACCESS  read-only
         STATUS      current
         DESCRIPTION
                     "Flag to enable/disable the functionality  to send
                      all QoS ACL configuration to a peer controller on a
                      configuration push."
         DEFVAL      { enable }
         ::= { wsPeerConfiguration 9 }

-- Object not supported in SMB builds
wsPeerConfigurationQosDiffServ    OBJECT-TYPE
         SYNTAX      INTEGER {
                       enable(1),
                       disable(2)
                     }
         MAX-ACCESS  read-only
         STATUS      current
         DESCRIPTION
                     "Flag to enable/disable the functionality  to send
                      all QoS DiffServ configuration to a peer controller on a
                      configuration push."
         DEFVAL      { enable }
         ::= { wsPeerConfiguration 10 }

-- Object not supported in SMB builds
wsPeerConfigurationWdsGroup       OBJECT-TYPE
         SYNTAX      INTEGER {
                       enable(1),
                       disable(2)
                     }
         MAX-ACCESS  read-only
         STATUS      current
         DESCRIPTION
                     "Flag to enable/disable the functionality to send configured
                      wds groups to a peer controller on a configuration push."
         DEFVAL      { enable }
         ::= { wsPeerConfiguration 11 }

-- Object not supported in SMB builds
wsPeerConfigurationDeviceLocation       OBJECT-TYPE
         SYNTAX      INTEGER {
                       enable(1),
                       disable(2)
                     }
         MAX-ACCESS  read-only
         STATUS      current
         DESCRIPTION
                     "Flag to enable/disable the functionality to send configured
                      device location parameters to a peer controller on a configuration push."
         DEFVAL      { enable }
         ::= { wsPeerConfiguration 12 }



wsClusterPriority    OBJECT-TYPE
         SYNTAX     Unsigned32(0..255)
         MAX-ACCESS  read-only
         STATUS      current
         DESCRIPTION
                  "Preference level of the controller to become the Cluster
                   Controller of the Peer Group.A priority of 0 means that the controller can not become cluster controller."
         DEFVAL      { 0 }
         ::= { wsGlobalConfig 16 }

wsAPClientQosMode    OBJECT-TYPE
         SYNTAX     INTEGER {
                         enable(1),
                         disable(2)
                    }
         MAX-ACCESS  not-accessible
         STATUS      current
         DESCRIPTION
                     "Flag to globally enable/disable AP quality-of-service
                      operation for wireless clients."
         DEFVAL      { disable }
         ::= { wsGlobalConfig 17 }

wsAPAutoUpgradeMode    OBJECT-TYPE
         SYNTAX      INTEGER {
                     enable(1),
                     disable(2)
                     }
         MAX-ACCESS  not-accessible
         STATUS      current
         DESCRIPTION
                     "Flag to enable/disable AP auto upgrade mode. This object is
                      configurable only if the wireless controller supports both
                      'Integrated' and 'Independent' AP image download modes.
                      If the controller supports only 'Integrated' mode, the default is Enable."
         DEFVAL      { disable }
         ::= { wsGlobalConfig 18 }

wsDistTunnelIdleTimeout    OBJECT-TYPE
         SYNTAX     Unsigned32(30..3600)
         MAX-ACCESS  read-only
         STATUS      current
         DESCRIPTION
                  "Time of inactivity in seconds to wait before terminating a
                   tunnel client."
         DEFVAL      { 120 }
         ::= { wsGlobalConfig 19 }


wsDistTunnelMaxTimeout    OBJECT-TYPE
         SYNTAX     Unsigned32(30..86400)
         MAX-ACCESS  read-only
         STATUS      current
         DESCRIPTION
                  "Time in seconds to wait before terminating a tunnel client."
         DEFVAL      { 7200 }
         ::= { wsGlobalConfig 20 }


wsDistTunnelMaxMcastRepl    OBJECT-TYPE
         SYNTAX     Unsigned32(1..1024)
         MAX-ACCESS  read-only
         STATUS      current
         DESCRIPTION
                  "Maximum number of multicast replications that can be performed
                   by the AP."
         DEFVAL      { 128 }
         ::= { wsGlobalConfig 21 }


wsDistTunnelMaxClients    OBJECT-TYPE
         SYNTAX     Unsigned32(1..8000)
         MAX-ACCESS  read-only
         STATUS      current
         DESCRIPTION
                  "Maximum number of clients that can use tunneled through a
                   Home AP."
         DEFVAL      { 128 }
         ::= { wsGlobalConfig 22 }

wsMACAuthenticationMode OBJECT-TYPE
        SYNTAX       INTEGER {
                     whitelist(1),
                     blacklist(2)
                  }
        MAX-ACCESS   read-only
        STATUS       current
        DESCRIPTION
                "This object indicates whether MAC addresses in the Known Client
                database are granted or denied access if they are in the list,
                but dont have a specific action."
        DEFVAL      { whitelist }
        ::= { wsGlobalConfig 23 }

----
--    wsKnownClientTable
----
  wsKnownClientTable OBJECT-TYPE
     SYNTAX       SEQUENCE OF WsKnownClientEntry
     MAX-ACCESS   not-accessible
     STATUS       current
     DESCRIPTION
        "This table contains entries of the known clients."
     ::= { wsGlobalConfig 24 }

  wsKnownClientEntry OBJECT-TYPE
     SYNTAX       WsKnownClientEntry
     MAX-ACCESS   not-accessible
     STATUS       current
     DESCRIPTION
          "The entry contains parameters of a known client."
     INDEX    { wsKnownClientMacAddress }
     ::= { wsKnownClientTable 1 }

  WsKnownClientEntry ::=
     SEQUENCE {
        wsKnownClientMacAddress         MacAddress,
        wsKnownClientAuthAction         INTEGER,
        wsKnownClientName               DisplayString,
        wsKnownClientRowStatus          RowStatus
     }

  wsKnownClientMacAddress OBJECT-TYPE
     SYNTAX       MacAddress
     MAX-ACCESS   read-only
     STATUS       current
     DESCRIPTION
        "MAC address of the known client."
     ::= { wsKnownClientEntry 1 }

  wsKnownClientAuthAction OBJECT-TYPE
     SYNTAX      INTEGER {
                        global(1),
                        grant(2),
                        deny(3)
                }
     MAX-ACCESS   read-only
     STATUS       current
     DESCRIPTION
       "This object indicates whether to grant, deny, or use global action
       for client authentication."
     DEFVAL      { global }
         ::= { wsKnownClientEntry 2 }

  wsKnownClientName OBJECT-TYPE
     SYNTAX       DisplayString(SIZE(0..32))
     MAX-ACCESS   read-only
     STATUS       current
     DESCRIPTION
        "Descriptive name of the known client."
     ::= { wsKnownClientEntry 3 }

  wsKnownClientRowStatus OBJECT-TYPE
     SYNTAX       RowStatus
     MAX-ACCESS   read-only
     STATUS       current
     DESCRIPTION
        "This object is used to create or delete entries in this
         table."
     ::= { wsKnownClientEntry 4 }

--  wsWidsSecurity
--
   wsWidsSecurity                        OBJECT IDENTIFIER ::= { wsGlobalConfig 25 }

    wsWidsApSecurity                     OBJECT IDENTIFIER ::= { wsWidsSecurity 1 }

    rogueAdminConfig                    OBJECT-TYPE
         SYNTAX     INTEGER {
                         enable(1)
                    }
         MAX-ACCESS  read-only
         STATUS      current
         DESCRIPTION
                     "Report the AP as rogue in the RF Scan if the local
                      database indicates that the AP is rogue.  Can not be disabled."
         DEFVAL      { enable }
         ::= { wsWidsApSecurity 1 }

    rogueUnknownApManagedSsid           OBJECT-TYPE
         SYNTAX     INTEGER {
                         enable(1),
                         disable(2)
                    }
         MAX-ACCESS  read-only
         STATUS      current
         DESCRIPTION
                     "Enable rogue reporting for unknown AP's detected
                      with a managed SSID."
         DEFVAL      { enable }
         ::= { wsWidsApSecurity 2 }

    rogueFakeManagedApManagedSsid       OBJECT-TYPE
         SYNTAX     INTEGER {
                         enable(1),
                         disable(2)
                    }
         MAX-ACCESS  read-only
         STATUS      current
         DESCRIPTION
                     "Enable rogue reporting for fake managed AP's
                      detected with a managed SSID."
         DEFVAL      { enable }
         ::= { wsWidsApSecurity 3 }

    rogueManagedApNoSsid                OBJECT-TYPE
         SYNTAX     INTEGER {
                         enable(1),
                         disable(2)
                    }
         MAX-ACCESS  read-only
         STATUS      current
         DESCRIPTION
                     "Enable rogue reporting of all APs detected with no SSID."
         DEFVAL      { enable }
         ::= { wsWidsApSecurity 4 }

    rogueManagedApInvalidChannel        OBJECT-TYPE
         SYNTAX     INTEGER {
                         enable(1),
                         disable(2)
                    }
         MAX-ACCESS  read-only
         STATUS      current
         DESCRIPTION
                     "Enable rogue reporting of fake managed AP's detected
                      with an invalid channel."
         DEFVAL      { enable }
         ::= { wsWidsApSecurity 5 }

    rogueManagedSsidInvalidSecurity     OBJECT-TYPE
         SYNTAX     INTEGER {
                         enable(1),
                         disable(2)
                    }
         MAX-ACCESS  read-only
         STATUS      current
         DESCRIPTION
                     "Enable rogue reporting of AP's detected with managed SSID's
                      and an invalid security configuration."
         DEFVAL      { enable }
         ::= { wsWidsApSecurity 6 }

    rogueManagedApInvalidSsid           OBJECT-TYPE
         SYNTAX     INTEGER {
                         enable(1),
                         disable(2)
                    }
         MAX-ACCESS  read-only
         STATUS      current
         DESCRIPTION
                     "Enable rogue reporting of managed AP's with an invalid SSID."
         DEFVAL      { enable }
         ::= { wsWidsApSecurity 7 }

    rogueApIllegalChannel               OBJECT-TYPE
         SYNTAX     INTEGER {
                         enable(1),
                         disable(2)
                    }
         MAX-ACCESS  read-only
         STATUS      current
         DESCRIPTION
                     "Enable rogue reporting of AP's operating on an illegal channel."
         DEFVAL      { enable }
         ::= { wsWidsApSecurity 8 }

    rogueStandaloneApInvalidConfig      OBJECT-TYPE
         SYNTAX     INTEGER {
                         enable(1),
                         disable(2)
                    }
         MAX-ACCESS  read-only
         STATUS      current
         DESCRIPTION
                     "Enable rogue reporting of standalone AP's operating with an
                      unexpected configuration."
         DEFVAL      { enable }
         ::= { wsWidsApSecurity 9 }

    rogueUnexpectedWdsDevice            OBJECT-TYPE
         SYNTAX     INTEGER {
                         enable(1),
                         disable(2)
                    }
         MAX-ACCESS  read-only
         STATUS      current
         DESCRIPTION
                     "Enable rogue reporting of unexpected WDS devices."
         DEFVAL      { enable }
         ::= { wsWidsApSecurity 10 }

    rogueUnmanagedApWiredNetwork        OBJECT-TYPE
         SYNTAX     INTEGER {
                         enable(1),
                         disable(2)
                    }
         MAX-ACCESS  read-only
         STATUS      current
         DESCRIPTION
                     "Enable rogue reporting of unmanaged AP's on a wired network."
         DEFVAL      { enable }
         ::= { wsWidsApSecurity 11 }

    wiredNetworkDetectionInterval       OBJECT-TYPE
         SYNTAX       Integer32(0..3600)
         MAX-ACCESS   read-only
         STATUS       current
         DESCRIPTION
                      "Minimum number of seconds that the AP waits before starting
                       a new wired network detection cycle.  A value of 0 disables
                       wired network detection."
         DEFVAL       { 60 }
         ::= { wsWidsApSecurity 12 }

    rogueDetectedTrapInterval           OBJECT-TYPE
         SYNTAX       Integer32(0|60..3600)
         MAX-ACCESS   read-only
         STATUS       current
         DESCRIPTION
                      "The interval in seconds between transmissions of the trap telling
                      the administrator that Rogues are present in the RF Scan database.
                      A configured value of 0 disables the trap from being sent. ."
         DEFVAL       { 300 }
         ::= { wsWidsApSecurity 13 }

    apDeauthenticationAttack            OBJECT-TYPE
         SYNTAX     INTEGER {
                         enable(1),
                         disable(2)
                    }
         MAX-ACCESS  read-only
         STATUS      current
         DESCRIPTION
                     "Enable the AP de-authentication attack."
         DEFVAL      { disable }
         ::= { wsWidsApSecurity 14 }

--**************************************************************************************
-- wsWidsApSecurity Ends
--**************************************************************************************

--**************************************************************************************
-- wsWidsClientSecurity Begin
--**************************************************************************************

    wsWidsClientSecurity                     OBJECT IDENTIFIER ::= { wsWidsSecurity 2 }

    rogueDetectedTrapIntvl              OBJECT-TYPE
         SYNTAX       Integer32(0|60..3600)
         MAX-ACCESS   read-only
         STATUS       current
         DESCRIPTION
                      "The interval in seconds between transmissions of the trap telling
                      the administrator that Rogues are present in the Rogue Clients are
                      present in the Detected Clients Database. A configured value of 0
                      disables the trap from being sent."
         DEFVAL       { 300 }
         ::= { wsWidsClientSecurity 1 }


    knownClientDatabaseTest            OBJECT-TYPE
         SYNTAX     INTEGER {
                         enable(1),
                         disable(2)
                    }
         MAX-ACCESS  read-only
         STATUS      current
         DESCRIPTION
                     "Report the client as rogue if it fails the Known Client Database Test."
         DEFVAL      { disable }
         ::= { wsWidsClientSecurity 2 }

    authReqTransmitRate                OBJECT-TYPE
         SYNTAX     INTEGER {
                         enable(1),
                         disable(2)
                    }
         MAX-ACCESS  read-only
         STATUS      current
         DESCRIPTION
                     "Report the client as rogue if it exceeds configured rate for
                      transmitting 802.11 authentication requests."
         DEFVAL      { enable }
         ::= { wsWidsClientSecurity 3 }

    probeReqTransmitRate                OBJECT-TYPE
         SYNTAX     INTEGER {
                         enable(1),
                         disable(2)
                    }
         MAX-ACCESS  read-only
         STATUS      current
         DESCRIPTION
                     "Report the client as rogue if it exceeds configured rate for
                      transmitting probe requests."
         DEFVAL      { enable }
         ::= { wsWidsClientSecurity 4 }

    deauthReqTransmitRate                OBJECT-TYPE
         SYNTAX     INTEGER {
                         enable(1),
                         disable(2)
                    }
         MAX-ACCESS  read-only
         STATUS      current
         DESCRIPTION
                     "Report the client as rogue if it exceeds configured rate for
                      transmitting 802.11 deauthentication requests."
         DEFVAL      { enable }
         ::= { wsWidsClientSecurity 5 }

    maxFailingAuthentication              OBJECT-TYPE
         SYNTAX     INTEGER {
                         enable(1),
                         disable(2)
                    }
         MAX-ACCESS  read-only
         STATUS      current
         DESCRIPTION
                     "Report the client as rogue if it exceeds maximum number of
                      failing authentications."
         DEFVAL      { enable }
         ::= { wsWidsClientSecurity 6 }

    authWithUnknownAP                     OBJECT-TYPE
         SYNTAX     INTEGER {
                         enable(1),
                         disable(2)
                    }
         MAX-ACCESS  read-only
         STATUS      current
         DESCRIPTION
                     "Report the client as rogue if it is authenticated with an
                      unknown AP."
         DEFVAL      { disable }
         ::= { wsWidsClientSecurity 7 }

    clientThreatMitigation                OBJECT-TYPE
         SYNTAX     INTEGER {
                         enable(1),
                         disable(2)
                    }
         MAX-ACCESS  read-only
         STATUS      current
         DESCRIPTION
                     "Transmission of de-authentication messages to known clients
                      associated with unknown APs. The Known Client test must
                      also be enabled in order for the mitigation to take place."
         DEFVAL      { disable }
         ::= { wsWidsClientSecurity 8 }

    deauthThresholdInterval               OBJECT-TYPE
         SYNTAX       Integer32(1..3600)
         MAX-ACCESS   read-only
         STATUS       current
         DESCRIPTION
                      "Number of seconds for counting the de-authentication messages."
         DEFVAL       { 60 }
         ::= { wsWidsClientSecurity 9 }

    deauthThresholdValue                 OBJECT-TYPE
         SYNTAX       Integer32(1..99999)
         MAX-ACCESS   read-only
         STATUS       current
         DESCRIPTION
                      "If controller receives more than specified de-auth messages
                      during the threshold interval the test triggers
                      the client to be reported as rogue."
         DEFVAL       { 10 }
         ::= { wsWidsClientSecurity 10 }

    authThresholdInterval                 OBJECT-TYPE
         SYNTAX       Integer32(1..3600)
         MAX-ACCESS   read-only
         STATUS       current
         DESCRIPTION
                      "Number of seconds for counting the authentication messages."
         DEFVAL       { 60 }
         ::= { wsWidsClientSecurity 11 }

    authThresholdValue                   OBJECT-TYPE
         SYNTAX       Integer32(1..99999)
         MAX-ACCESS   read-only
         STATUS       current
         DESCRIPTION
                      "If controller receives more than specified auth messages
                      during the threshold interval the test triggers
                      the client to be reported as rogue."
         DEFVAL       { 10 }
         ::= { wsWidsClientSecurity 12 }

    probeThresholdInterval               OBJECT-TYPE
         SYNTAX       Integer32(1..3600)
         MAX-ACCESS   read-only
         STATUS       current
         DESCRIPTION
                      "Number of seconds for counting the probe messages."
         DEFVAL       { 60 }
         ::= { wsWidsClientSecurity 13 }

    probeThresholdValue                  OBJECT-TYPE
         SYNTAX       Integer32(1..99999)
         MAX-ACCESS   read-only
         STATUS       current
         DESCRIPTION
                      "If controller receives more than specified probe messages
                      during the threshold interval the test triggers
                      the client to be reported as rogue."
         DEFVAL       { 120 }
         ::= { wsWidsClientSecurity 14 }

    authFailureThreshold                   OBJECT-TYPE
         SYNTAX       Integer32(1..99999)
         MAX-ACCESS   read-only
         STATUS       current
         DESCRIPTION
                      "The number of 802.1X authentication failures that triggers
                      the client to be reported as rogue."
         DEFVAL       { 50 }
         ::= { wsWidsClientSecurity 15 }

    knownClientDatabaseLocation              OBJECT-TYPE
         SYNTAX     INTEGER {
                         local(1),
                         radius(2)
                    }

         MAX-ACCESS   read-only
         STATUS       current
         DESCRIPTION
                      "The location of Known Client Database. If the value is local
                      then Known Client Database is located in the local controller.
                      Otherwise the database is located in the RADIUS Server."
         DEFVAL      { local }
         ::= { wsWidsClientSecurity 16 }

    knownClientDatabaseRadiusServerName OBJECT-TYPE
       SYNTAX       DisplayString (SIZE(1..32))
       MAX-ACCESS   read-only
       STATUS       current
       DESCRIPTION
                    "Name of the RADIUS server used for Known Client database
                     This is used when knownClientDatabaseLocation is set to
                     'radius'."
      DEFVAL        { "Default-RADIUS-Server" }
       ::= { wsWidsClientSecurity 17 }

    knownClientDatabaseRadiusServerStatus OBJECT-TYPE
       SYNTAX       INTEGER {
                    not-configured(1),
                    configured(2)
                    }
       MAX-ACCESS   read-only
       STATUS       current
       DESCRIPTION
                    "Indicates whether the specified named RADIUS Authentication
                     server is configured in the RADIUS Client configuration."
       DEFVAL       { not-configured }
        ::= { wsWidsClientSecurity 18 }

     notInOUIDatabase            OBJECT-TYPE
         SYNTAX     INTEGER {
                         enable(1),
                         disable(2)
                    }
         MAX-ACCESS  not-accessible
         STATUS      current
         DESCRIPTION
                     "Report the client as rogue if it's OUI is not present in the OUI
                      Database."
         DEFVAL      { disable }
         ::= { wsWidsClientSecurity 19 }


--
--  wsRadiusConfiguration
--
    wsGlobalRadiusConfiguration                OBJECT IDENTIFIER ::= { wsGlobalConfig 26 }

    wsRadiusConfiguration                      OBJECT IDENTIFIER ::= { wsGlobalRadiusConfiguration 1 }


    wsAuthRadiusServerName OBJECT-TYPE
       SYNTAX       DisplayString (SIZE(1..32))
       MAX-ACCESS   read-only
       STATUS       current
       DESCRIPTION
                    "Name of the RADIUS server used for AP authentications as
                     well as client authentications when a network-level RADIUS
                     server is not defined."
      DEFVAL        { "Default-RADIUS-Server" }
       ::= { wsRadiusConfiguration 1 }

    wsAuthRadiusServerConfiguredStatus OBJECT-TYPE
       SYNTAX       INTEGER {
                    not-configured(1),
                    configured(2)
                    }
       MAX-ACCESS   read-only
       STATUS       current
       DESCRIPTION
                    "Indicates whether the specified named RADIUS Authentication
                     server is configured in the RADIUS Client configuration."
       DEFVAL       { not-configured }
       ::= { wsRadiusConfiguration 2 }

    wsAcctRadiusServerName OBJECT-TYPE
       SYNTAX       DisplayString (SIZE(1..32))
       MAX-ACCESS   read-only
       STATUS       current
       DESCRIPTION
                    "Name of the RADIUS server used for reporting wireless
                    client associations and disassociations when a
                    network-level RADIUS accounting server is not defined."
       DEFVAL       { "Default-RADIUS-Server" }
       ::= { wsRadiusConfiguration 3 }

   wsAcctRadiusServerConfiguredStatus OBJECT-TYPE
       SYNTAX       INTEGER {
                    not-configured(1),
                    configured(2)
                    }
       MAX-ACCESS   read-only
       STATUS       current
       DESCRIPTION
                    "Indicates whether the specified named RADIUS Accounting
                     server is configured in the RADIUS Client configuration."
       DEFVAL       { not-configured }
       ::= { wsRadiusConfiguration 4 }

    wsRadiusAcctMode OBJECT-TYPE
       SYNTAX     INTEGER {
                         enable(1),
                         disable(2)
                    }

       MAX-ACCESS   read-only
       STATUS       current
       DESCRIPTION
                    "Flag to indicate whether or not RADIUS accounting is
                    enabled for wireless clients."
       DEFVAL       { disable }
       ::= { wsRadiusConfiguration 5 }

--**************************************************************************************
-- wsRadiusConfiguration Ends
--**************************************************************************************

    wsAutoIPAssignMode    OBJECT-TYPE
         SYNTAX      INTEGER {
                       enable(1),
                       disable(2)
                     }
         MAX-ACCESS  read-only
         STATUS      current
         DESCRIPTION
                     "Flag indicating whether the Wireless feature should
                     automatically assign an IP address from one of the active
                     interfaces or whether the IP address is manually assigned."
         DEFVAL      { enable }
         ::= { wsGlobalConfig 29 }

    wsSwitchStaticIPAddress OBJECT-TYPE
         SYNTAX       IpAddress
         MAX-ACCESS   read-only
         STATUS       current
         DESCRIPTION
               "Statically assigned IPv4 address for the Wireless feature.
               If Auto IP Assignment is true then this setting is ignored."
               ::= { wsGlobalConfig 30 }


--**************************************************************************************
-- wsWidsSecurity Ends
--**************************************************************************************

--**************************************************************************************
-- wsGlobalTspecConfiguration Begin
--**************************************************************************************

    wsGlobalTspecConfiguration                 OBJECT IDENTIFIER ::= { wsGlobalConfig 31 }
--
--    global tspec configuration
--
  wsTspecViolationReportInterval    OBJECT-TYPE
       SYNTAX     Unsigned32(0..900)
       MAX-ACCESS  not-accessible
       STATUS      current
       DESCRIPTION
                "Specifies the time period at which wireless
                 clients detected as using admission-controlled
                 resources without proper TSPEC authorization are
                 reported via the system logging and SNMP trap
                 mechanisms.

                 If a violating client disassociates before the next
                 report interval, it is reported upon disassociation.

                 This object is specified in seconds, with a default
                 value of 300 (5 minutes).  Setting this object value
                 to 0 disables TSPEC violation reporting."
       DEFVAL      { 300 }
       ::= { wsGlobalTspecConfiguration 1 }

--**************************************************************************************
-- wsGlobalTspecConfiguration Ends
--**************************************************************************************

--
--  wsSwitchStatusTable
--
   wsSwitchStatusTable OBJECT-TYPE
          SYNTAX       SEQUENCE OF WsSwitchStatusEntry
          MAX-ACCESS   not-accessible
          STATUS       current
          DESCRIPTION
                "This table contain access point and client status parameters
                of peer controllers of wireless controller."
                ::= { wsGlobalConfig 27 }

   wsSwitchStatusEntry OBJECT-TYPE
          SYNTAX       WsSwitchStatusEntry
          MAX-ACCESS   not-accessible
          STATUS       current
          DESCRIPTION
                "Each entry describes the access point and client status
                parameters of each peer of wireless controller."
          INDEX    { wsSwitchIPAddress }
          ::= { wsSwitchStatusTable 1 }

   WsSwitchStatusEntry ::=
     SEQUENCE {
         wsSwitchIPAddress                   IpAddress,
         wsSwitchClusterPriority             Unsigned32,
         wsSwitchAPImageDownloadMode         DisplayString,
         wsSwitchTotalAPs                    Unsigned32,
         wsSwitchManagedAPs                  Unsigned32,
         wsSwitchDiscoveredAPs               Unsigned32,
         wsSwitchConnectionFailedAPs         Unsigned32,
         wsSwitchMaximumManagedAPs           Unsigned32,
         wsSwitchTotalClients                Unsigned32,
         wsSwitchAuthenticatedClients        Unsigned32,
         wsSwitchWLANUtilization             Unsigned32,
         wsSwitchDistTunnelClients           Unsigned32
     }

   wsSwitchIPAddress OBJECT-TYPE
         SYNTAX       IpAddress
         MAX-ACCESS   read-only
         STATUS       current
         DESCRIPTION
               "This object represents wireless controller IP address.
               When wireless mode is in disabled state,
               return entry will be none."
               ::= { wsSwitchStatusEntry 1 }

   wsSwitchClusterPriority    OBJECT-TYPE
         SYNTAX     Unsigned32(0..255)
         MAX-ACCESS  read-only
         STATUS      current
         DESCRIPTION
               "Preference level of the controller to become the Cluster
               Controller of the Peer Group."
               ::= { wsSwitchStatusEntry 2}

   wsSwitchAPImageDownloadMode    OBJECT-TYPE
         SYNTAX      DisplayString(SIZE(0..32))
         MAX-ACCESS  not-accessible
         STATUS      current
         DESCRIPTION
               "The AP image download mode supported by the wireless controller.

               The displayed mode can be one of the following:
               Integrated - The controller supports Integrated mode. In this mode, the AP code is located on the controller,
                            and the controller automatically updates the code on APs it manages.
               Independent - The controller supports Independent mode. In this mode, the AP code is on a TFTP server,
                             and the download is triggered from the cluster controller.
               Integrated, Independent - The controller supports both modes.

               Note that this field displays the mode only if wireless controllers that support
               Independent and Integrated AP Image Download modes co-exist in the network."
         ::= { wsSwitchStatusEntry 3}

   wsSwitchTotalAPs  OBJECT-TYPE
         SYNTAX      Unsigned32(0..48)
         MAX-ACCESS  read-only
         STATUS      current
         DESCRIPTION
               "Sum of all the WS managed APs, connection failed APs, and
               discovered APs in the database of specified controller."
         ::= { wsSwitchStatusEntry 4 }

   wsSwitchManagedAPs  OBJECT-TYPE
         SYNTAX      Unsigned32(0..48)
         MAX-ACCESS  read-only
         STATUS      current
         DESCRIPTION
               "Total number of WS managed APs currently
               authenticated, configured and have an active connection
               with the specifed controller."
         ::= { wsSwitchStatusEntry 5 }

   wsSwitchDiscoveredAPs    OBJECT-TYPE
         SYNTAX      Unsigned32(0..48)
         MAX-ACCESS  read-only
         STATUS      current
         DESCRIPTION
               "Number of APs that are connected to the specified controller,
               but have not been completely configured."
         ::= { wsSwitchStatusEntry 6 }

   wsSwitchConnectionFailedAPs  OBJECT-TYPE
         SYNTAX      Unsigned32(0..48)
         MAX-ACCESS  read-only
         STATUS      current
         DESCRIPTION
               "Number of APs that were previously authenticated and managed,
               but currently do not have connection with the specified controller."
         ::= { wsSwitchStatusEntry 7 }

   wsSwitchMaximumManagedAPs    OBJECT-TYPE
         SYNTAX      Unsigned32
         MAX-ACCESS  read-only
         STATUS      current
         DESCRIPTION
               "Maximum number of APs that the specified controller can manage."
         ::= { wsSwitchStatusEntry 8 }

   wsSwitchTotalClients  OBJECT-TYPE
         SYNTAX      Unsigned32(0..8192)
         MAX-ACCESS  read-only
         STATUS      current
         DESCRIPTION
               "Total number of clients in the database that include clients
               with an associated, authenticated and disassociated status."
         ::= { wsSwitchStatusEntry 9 }

   wsSwitchAuthenticatedClients  OBJECT-TYPE
         SYNTAX      Unsigned32(0..8192)
         MAX-ACCESS  read-only
         STATUS      current
         DESCRIPTION
               "Total number of authenticated clients across
               all APs managed by the specified controller."
         ::= { wsSwitchStatusEntry 10 }

   wsSwitchWLANUtilization    OBJECT-TYPE
         SYNTAX      Unsigned32(0..100)
         MAX-ACCESS  read-only
         STATUS      current
         DESCRIPTION
               "Total network utilization across all APs managed by
               the specifed controller."
         ::= { wsSwitchStatusEntry 11 }

   wsSwitchDistTunnelClients  OBJECT-TYPE
         SYNTAX      Unsigned32
         MAX-ACCESS  read-only
         STATUS      current
         DESCRIPTION
               "Number of clients that are currently sending and
                receiving packets via distributed tunnels."
         ::= { wsSwitchStatusEntry 12 }

--
--  wsSwitchStatisticsTable
--
   wsSwitchStatisticsTable OBJECT-TYPE
         SYNTAX       SEQUENCE OF WsSwitchStatisticsEntry
         MAX-ACCESS   not-accessible
         STATUS       current
         DESCRIPTION
              "This table contain WLAN statistics for every controller in the
              peer group. Only Cluster Controller can hold the entries for peer
              controllers. The controller which is not a Cluster Controller only keep
              statistics local to it."
              ::= { wsGlobalConfig 28 }

   wsSwitchStatisticsEntry OBJECT-TYPE
        SYNTAX       WsSwitchStatisticsEntry
        MAX-ACCESS   not-accessible
        STATUS       current
        DESCRIPTION
              "Each entry describe WLAN statistics of specified controller in the
              wireless system."
        INDEX    { wsSwitchIPAddress }
        ::= { wsSwitchStatisticsTable 1 }

   WsSwitchStatisticsEntry ::=
     SEQUENCE {
         wsSwitchWLANBytesTransmitted       Counter64,
         wsSwitchWLANBytesReceived          Counter64,
         wsSwitchWLANPktsTransmitted        Counter64,
         wsSwitchWLANPktsReceived           Counter64,
         wsSwitchWLANBytesTransmitDropped   Counter64,
         wsSwitchWLANBytesRecvDropped       Counter64,
         wsSwitchWLANPktsTransmitDropped    Counter64,
         wsSwitchWLANPktsRecvDropped        Counter64
     }

   wsSwitchWLANBytesTransmitted    OBJECT-TYPE
         SYNTAX      Counter64
         MAX-ACCESS  read-only
         STATUS      current
         DESCRIPTION
              "Total bytes transmitted across all APs managed by
               the specified  controller."
         ::= { wsSwitchStatisticsEntry 1 }

   wsSwitchWLANBytesReceived    OBJECT-TYPE
         SYNTAX      Counter64
         MAX-ACCESS  read-only
         STATUS      current
         DESCRIPTION
              "Total bytes received across all APs managed by
               the specified controller."
         ::= { wsSwitchStatisticsEntry 2 }

   wsSwitchWLANPktsTransmitted    OBJECT-TYPE
         SYNTAX      Counter64
         MAX-ACCESS  read-only
         STATUS      current
         DESCRIPTION
              "Total packets transmitted across all APs managed by
               the specified controller."
         ::= { wsSwitchStatisticsEntry 3 }

   wsSwitchWLANPktsReceived    OBJECT-TYPE
         SYNTAX      Counter64
         MAX-ACCESS  read-only
         STATUS      current
         DESCRIPTION
              "Total packets received across all APs managed by
               the specified controller."
         ::= { wsSwitchStatisticsEntry 4 }

   wsSwitchWLANBytesTransmitDropped    OBJECT-TYPE
         SYNTAX      Counter64
         MAX-ACCESS  read-only
         STATUS      current
         DESCRIPTION
              "Total bytes dropped in the transmit direction across all APs
               managed by the specified controller.  This is due to client QoS actions
               affecting the wireless down (outbound) direction from AP to client."
         ::= { wsSwitchStatisticsEntry 5 }

   wsSwitchWLANBytesRecvDropped    OBJECT-TYPE
         SYNTAX      Counter64
         MAX-ACCESS  read-only
         STATUS      current
         DESCRIPTION
              "Total bytes dropped in the receive direction across all APs
               managed the specified controller.  This is due to client QoS actions
               affecting the wireless up (inbound) direction from AP to client."
         ::= { wsSwitchStatisticsEntry 6 }

   wsSwitchWLANPktsTransmitDropped    OBJECT-TYPE
         SYNTAX      Counter64
         MAX-ACCESS  read-only
         STATUS      current
         DESCRIPTION
              "Total packets dropped in the transmit direction across all APs
               managed by the specified controller.  This is due to client QoS actions
               affecting the wireless down (outbound) direction from AP to client."
         ::= { wsSwitchStatisticsEntry 7 }

   wsSwitchWLANPktsRecvDropped    OBJECT-TYPE
         SYNTAX      Counter64
         MAX-ACCESS  read-only
         STATUS      current
         DESCRIPTION
              "Total packets dropped in the receive direction across all APs
               managed by the specified controller.  This is due to client QoS actions
               affecting the wireless up (inbound) direction from AP to client."
         ::= { wsSwitchStatisticsEntry 8 }

    networkMutualAuthMode   OBJECT-TYPE
        SYNTAX              INTEGER {
                              enable(1),
                              disable(2)
                            }
        MAX-ACCESS          not-accessible
        STATUS              current
        DESCRIPTION
          "Flag to enable/disable mutual authentication of the Wireless
           controllers and Access Points in the network."
        DEFVAL              { disable }
        ::= { wsGlobalConfig 32}

    unmanagedAPReprovisioning   OBJECT-TYPE
        SYNTAX              INTEGER {
                              enable(1),
                              disable(2)
                            }
        MAX-ACCESS          not-accessible
        STATUS              current
        DESCRIPTION
          "Flag to enable/disable reprovisioning of APs when in unmanaged mode."
        DEFVAL              { enable }
        ::= { wsGlobalConfig 33 }

    apProvisionDbAgeTime    OBJECT-TYPE
        SYNTAX              Unsigned32(0..240)
        MAX-ACCESS          not-accessible
        STATUS              current
        DESCRIPTION
          "Time in hours to wait without hearing any updates for the APs before
           removing them from the provisioning database.A value of 0 in input range means that the entry never ages out."
        DEFVAL              { 72 }
        ::= { wsGlobalConfig 34 }

    switchProvisioning  OBJECT-TYPE
        SYNTAX              INTEGER {
                              enable(1),
                              disable(2)
                            }
        MAX-ACCESS          not-accessible
        STATUS              current
        DESCRIPTION
          "Flag to enable/disable controller provisioning."
        DEFVAL              { enable }
        ::= { wsGlobalConfig 35 }

    wsIpBasePort    OBJECT-TYPE
         SYNTAX      Unsigned32(0..65000)
         MAX-ACCESS  read-only
         STATUS     current
         DESCRIPTION
                  "Base IP port."
         DEFVAL      { 57775 }
         ::= { wsGlobalConfig 36 }

    devLocMeasurementSys   OBJECT-TYPE
         SYNTAX                INTEGER {
                                 metric(1),
                                 english(2)
                               }
         MAX-ACCESS            read-only
         STATUS                current
         DESCRIPTION
          "Measurement system in english/metric."
         DEFVAL                        { metric }
         ::= { wsGlobalConfig 37 }

    devLocRfScanLocMode     OBJECT-TYPE
        SYNTAX                 INTEGER {
                                  enable(1),
                                  disable(2)
                               }
        MAX-ACCESS             read-only
        STATUS                 current
        DESCRIPTION
          "Flag to enable/disable RF Scan location Mode."
        DEFVAL              { enable }
        ::= { wsGlobalConfig 38 }

     devLocRfScanLocInterval    OBJECT-TYPE
        SYNTAX                     Unsigned32(30..3600)
        MAX-ACCESS                 read-only
        STATUS                     current
        DESCRIPTION
          "Number of seconds between iterations of triangulation
           table device location protocol."
        DEFVAL              { 60 }
        ::= { wsGlobalConfig 39 }



--**************************************************************************************
-- wsGlobalGroup Ends
--**************************************************************************************

--**************************************************************************************
-- discovery
--**************************************************************************************
    wsIPPollMode    OBJECT-TYPE
         SYNTAX     INTEGER {
                         enable(1),
                         disable(2)
                    }
         MAX-ACCESS  read-only
         STATUS      current
         DESCRIPTION
                     "Flag to enable/disable IP based discovery of APs and
                      peer controllers."
         DEFVAL      { enable }
         ::= { discovery 1 }

    wsL2DiscoveryMode    OBJECT-TYPE
         SYNTAX     INTEGER {
                         enable(1),
                         disable(2)
                    }
         MAX-ACCESS  read-only
         STATUS      current
         DESCRIPTION
                     "Flag to enable/disable L2 discovery of APs and
                      peer controllers."
         DEFVAL      { enable }
         ::= { discovery 2 }

--
--  wsIPPollListTable
--
 wsIPPollListTable OBJECT-TYPE
     SYNTAX       SEQUENCE OF WsIPPollListEntry
     MAX-ACCESS   not-accessible
     STATUS       current
     DESCRIPTION
          "This table contains IP addresses to poll on
           the network."
     ::= { discovery 3 }

 wsIPPollListEntry OBJECT-TYPE
     SYNTAX       WsIPPollListEntry
     MAX-ACCESS   not-accessible
     STATUS       current
     DESCRIPTION
          "An IP address list that can be configured globally on
           the wireless controller to define which IP addresses to poll
           in order to discover new APs and peer controllers. This list
           is used when discovery via IP Polling is enabled."
     INDEX    { wsPollIpAddress }
     ::= { wsIPPollListTable 1 }

 WsIPPollListEntry ::=
     SEQUENCE {
         wsPollIpAddress    IpAddress,
         wsPollIPStatus     INTEGER,
         wsIPPollRowStatus  RowStatus
 }

 wsPollIpAddress OBJECT-TYPE
     SYNTAX       IpAddress
     MAX-ACCESS   read-only
     STATUS       current
     DESCRIPTION
        "IP address of an AP or controller to poll."
     ::= { wsIPPollListEntry 1 }

 wsPollIPStatus OBJECT-TYPE
     SYNTAX       INTEGER {
                     not-polled(1),
                     polled(2),
                     discovered(3),
                     discovered-failed(4)
                  }
     MAX-ACCESS   read-only
     STATUS       current
     DESCRIPTION
        "Indicates whether or not the controller reached this IP address."
      DEFVAL      { not-polled }
      ::= { wsIPPollListEntry 2 }

 wsIPPollRowStatus OBJECT-TYPE
     SYNTAX       RowStatus
     MAX-ACCESS   read-only
     STATUS       current
     DESCRIPTION
        "This object is used to create and delete entries
         in the table."
     ::= { wsIPPollListEntry 3 }

--
--  wsL2DiscoveryVlanListTable
--
 wsL2DiscoveryVlanListTable OBJECT-TYPE
     SYNTAX       SEQUENCE OF WsL2DiscoveryVlanListEntry
     MAX-ACCESS   not-accessible
     STATUS       current
     DESCRIPTION
         "This table contains the list of VLANs on which to send L2 discovery
          multicast packets."
     ::= { discovery 4 }

 wsL2DiscoveryVlanListEntry OBJECT-TYPE
     SYNTAX       WsL2DiscoveryVlanListEntry
     MAX-ACCESS   not-accessible
     STATUS       current
     DESCRIPTION
          "A list of VLANs on which to send L2 discovery multicast
           frames when L2 broadcast discovery mode is enabled.
           The entries in this table are limited to sixteen.
           By default there will be one entry in this table with
           wsL2DiscoveryVlanId equal to one. This entry can neither
           be created nor deleted."
     INDEX    { wsL2DiscoveryVlanId }
     ::= { wsL2DiscoveryVlanListTable 1 }

 WsL2DiscoveryVlanListEntry ::=
     SEQUENCE {
         wsL2DiscoveryVlanId        Integer32,
         wsL2DiscoveryVlanRowStatus RowStatus
 }

 wsL2DiscoveryVlanId OBJECT-TYPE
     SYNTAX       Integer32(1..4094)
     MAX-ACCESS   read-only
     STATUS       current
     DESCRIPTION
        "VLAN Id on which controller will send L2 discovery multicast
         frames."
     ::= { wsL2DiscoveryVlanListEntry 1 }

 wsL2DiscoveryVlanRowStatus OBJECT-TYPE
     SYNTAX       RowStatus
     MAX-ACCESS   read-only
     STATUS       current
     DESCRIPTION
        "This variable is used to create and delete entries
         in the table."
     ::= { wsL2DiscoveryVlanListEntry 2 }

--
--  wsIPPollListCounters
--
  wsIPPollListMaxNumOfEntries  OBJECT-TYPE
          SYNTAX      Unsigned32(0..256)
          MAX-ACCESS  read-only
          STATUS      current
          DESCRIPTION
               "Maximum number of IP discovery entries
                allowed to be configured."
         ::= { discovery 5 }

  wsIPPollListNumOfConfigEntries OBJECT-TYPE
        SYNTAX      Unsigned32(0..256)
        MAX-ACCESS  read-only
        STATUS      current
        DESCRIPTION
               "Total number of entries configured
                IP discovery entries."
         ::= { discovery 6 }

  wsIPPollListNumOfPolledEntries OBJECT-TYPE
         SYNTAX       Unsigned32(0..256)
         MAX-ACCESS  read-only
         STATUS      current
         DESCRIPTION
               "Total number of polled entries in
                the IP discovery list."
         ::= { discovery 7 }

  wsIPPollListNumOfNotPolledEntries OBJECT-TYPE
         SYNTAX       Unsigned32(0..256)
         MAX-ACCESS  read-only
         STATUS      current
         DESCRIPTION
               "Total number of not-polled entries in
                the IP discovery list."
         ::= { discovery 8 }

  wsIPPollListNumOfDiscoveredEntries OBJECT-TYPE
         SYNTAX        Unsigned32(0..256)
         MAX-ACCESS  read-only
         STATUS      current
         DESCRIPTION
               "Total number of discovered entries in
                the IP discovery list."
         ::= { discovery 9 }

  wsIPPollListNumOfDiscoveredFailedEntries OBJECT-TYPE
         SYNTAX       Unsigned32(0..256)
         MAX-ACCESS  read-only
         STATUS      current
         DESCRIPTION
               "Total number of discovered-failed entries in
                the IP discovery list."
         ::= { discovery 10 }

--**************************************************************************************
-- l2centTunnel
--**************************************************************************************
--
--  wsL2CentTnnlVlanListTable
--
 wsL2CentTnnlVlanListTable OBJECT-TYPE
     SYNTAX       SEQUENCE OF WsL2CentTnnlVlanListEntry
     MAX-ACCESS   not-accessible
     STATUS       current
     DESCRIPTION
         "This table contains the list of layer 2 tunneled VLANs."
     ::= { l2centTunnel 1 }

 wsL2CentTnnlVlanListEntry OBJECT-TYPE
     SYNTAX       WsL2CentTnnlVlanListEntry
     MAX-ACCESS   not-accessible
     STATUS       current
     DESCRIPTION
          "A list of VLANs on which all frames are tunneled.
           The entries in this table are limited to 64."
     INDEX    { wsL2CentTnnlVlanId }
     ::= { wsL2CentTnnlVlanListTable 1 }

 WsL2CentTnnlVlanListEntry ::=
     SEQUENCE {
         wsL2CentTnnlVlanId        Integer32,
         wsL2CentTnnlVlanRowStatus RowStatus
 }

 wsL2CentTnnlVlanId OBJECT-TYPE
     SYNTAX       Integer32(1..4094)
     MAX-ACCESS   not-accessible
     STATUS       current
     DESCRIPTION
        "VLAN ID on which all frames are tunneled."
     ::= { wsL2CentTnnlVlanListEntry 1 }

 wsL2CentTnnlVlanRowStatus OBJECT-TYPE
     SYNTAX       RowStatus
     MAX-ACCESS   read-only
     STATUS       current
     DESCRIPTION
        "This variable is used to create and delete entries
         in the table."
     ::= { wsL2CentTnnlVlanListEntry 2 }

--**************************************************************************************
-- wsOuiDatabase
--**************************************************************************************
--
--  wsOuiTable
--
 wsOuiTable OBJECT-TYPE
     SYNTAX       SEQUENCE OF WsOuiEntry
     MAX-ACCESS   not-accessible
     STATUS       current
     DESCRIPTION
         "This table contains the list of OUIs that have been configured by
          the administrator. The entries in this table are limited to 64."
     ::= { wsOuiDatabase 1 }

 wsOuiEntry OBJECT-TYPE
     SYNTAX       WsOuiEntry
     MAX-ACCESS   not-accessible
     STATUS       current
     DESCRIPTION
          "A list of OUIs. Each entry contains OUI and descriptive name of the
           wireless device manufacturer. The administrator can enter up to 64
           user-defined OUIs."
     INDEX    { wsOuiValue }
     ::= { wsOuiTable 1 }

 WsOuiEntry ::=
     SEQUENCE {
         wsOuiValue           WsOui,
         wsOuiDescription     DisplayString,
         wsOuiRowStatus       RowStatus
 }

 wsOuiValue OBJECT-TYPE
     SYNTAX      WsOui
     MAX-ACCESS  read-only
     STATUS      current
     DESCRIPTION "The OUI value for the AP or the client. Least significant bit of
                  the first byte must be zero."
     ::= { wsOuiEntry 1 }

 wsOuiDescription OBJECT-TYPE
     SYNTAX      DisplayString
     MAX-ACCESS  read-only
     STATUS      current
     DESCRIPTION "The descriptive name for the manufacturer of AP or wireless client adapter."
     ::= { wsOuiEntry 2 }

 wsOuiRowStatus OBJECT-TYPE
     SYNTAX       RowStatus
     MAX-ACCESS   read-only
     STATUS       current
     DESCRIPTION
        "This variable is used to create and delete entries
         in the table."
     ::= { wsOuiEntry 3 }



--**************************************************************************************
-- apProfile
--**************************************************************************************
--
--    wsApProfileTable
--
 wsAPProfileTable OBJECT-TYPE
     SYNTAX       SEQUENCE OF WsAPProfileEntry
     MAX-ACCESS   not-accessible
     STATUS       current
     DESCRIPTION
        "The following parameters can be configured within an AP configuration
         profile. A profile is used to replicate a single AP configuration across
         multiple managed APs. Modification or deletion is not allowed if the
         profile is assigned to one or more managed APs except
         wsCopyAPProfileToProfileId."
     ::= { apProfile 1 }

 wsAPProfileEntry OBJECT-TYPE
     SYNTAX       WsAPProfileEntry
     MAX-ACCESS   not-accessible
     STATUS       current
     DESCRIPTION
         "Each entry has parameters that can be configured within an AP configuration
          profile. A profile is used to replicate a single AP configuration across
          multiple managed APs, and is indexed by an integer Id."
     INDEX    { wsAPProfileId }
     ::= { wsAPProfileTable 1 }

 WsAPProfileEntry ::=
     SEQUENCE {
         wsAPProfileId                       Integer32,
         wsAPProfileName                     DisplayString,
         wsAPProfileState                    INTEGER,
         wsAPProfileRowStatus                RowStatus,
         wsCopyAPProfileToProfileId          Integer32,
         wsAPProfileApply                    INTEGER,
         wsAPHardwareTypeID                  Integer32,
         wsAPWiredDetectionVlanId            Integer32,
         wsAPProfileDisconnAPFwdingMode      INTEGER,
         wsAPProfileDisconnAPMgmtMode        INTEGER,
         wsAPProfileAeroScoutSupportMode     INTEGER
 }

 wsAPProfileId OBJECT-TYPE
     SYNTAX       Integer32(1..16)
     MAX-ACCESS   read-only
     STATUS       current
     DESCRIPTION
         "Unique AP Profile Id for each entry."
     ::= { wsAPProfileEntry 1 }

 wsAPProfileName OBJECT-TYPE
     SYNTAX       DisplayString(SIZE(0..32))
     MAX-ACCESS   read-only
     STATUS       current
     DESCRIPTION
        "AP configuration profile name."
     ::= { wsAPProfileEntry 2 }

 wsAPProfileState OBJECT-TYPE
     SYNTAX       INTEGER
                  {
                     none(0),
                     configured(1),
                     requested(2),
                     in-progress(3),
                     associated(4)
                  }
     MAX-ACCESS   read-only
     STATUS       current
     DESCRIPTION
        "Indicates current state of AP Profile."
     ::= { wsAPProfileEntry 3 }

 wsAPProfileRowStatus  OBJECT-TYPE
     SYNTAX       RowStatus
     MAX-ACCESS   read-only
     STATUS       current
     DESCRIPTION
        "This object is used to create or delete entries in
         the table."
     ::= { wsAPProfileEntry 8 }

 wsCopyAPProfileToProfileId OBJECT-TYPE
     SYNTAX       Integer32(0..16)
     MAX-ACCESS   read-only
     STATUS       current
     DESCRIPTION
        "This object copies the AP profile configuration to the specified
         valid AP Profile Id. If specified Profile Id is already
         assigned to one or more managed APs, the operation is
         not allowed. Read on this object will always return
         zero."
     ::= { wsAPProfileEntry 9 }

 wsAPProfileApply  OBJECT-TYPE
     SYNTAX       INTEGER {
                      none(1),
                      apply(2)
                  }
     MAX-ACCESS   read-only
     STATUS       current
     DESCRIPTION
        "This object is used to apply the AP profile configuration.
         Read on this object will always return none."
     ::= { wsAPProfileEntry 10 }

 wsAPHardwareTypeID OBJECT-TYPE
     SYNTAX       Integer32(0..6)
     MAX-ACCESS   not-accessible
     STATUS       current
     DESCRIPTION
         "AP Hardware type ID associated with each entry."
     ::= { wsAPProfileEntry 11 }

 wsAPWiredDetectionVlanId OBJECT-TYPE
     SYNTAX       Integer32(0..4094)
     MAX-ACCESS   read-only
     STATUS       current
     DESCRIPTION
        "VLAN ID that is used to send packets on the wire that enable the
         system to discover rogue APs attached to the wired network."
     ::= { wsAPProfileEntry 12 }

 wsAPProfileDisconnAPFwdingMode OBJECT-TYPE
     SYNTAX       INTEGER {
                    enable(1),
                    disable(2)
                  }
     MAX-ACCESS   read-only
     STATUS       current
     DESCRIPTION
        "Flag to enable/disable Disconnected AP Data Forwarding Mode."
     DEFVAL  { disable }
     ::= { wsAPProfileEntry 13 }

 wsAPProfileDisconnAPMgmtMode OBJECT-TYPE
     SYNTAX       INTEGER {
                    enable(1),
                    disable(2)
                  }
     MAX-ACCESS   read-only
     STATUS       current
     DESCRIPTION
        "Flag to enable/disable Disconnected AP Management Mode."
     DEFVAL  { enable }
     ::= { wsAPProfileEntry 14 }

wsAPProfileAeroScoutSupportMode OBJECT-TYPE
     SYNTAX       INTEGER {
                    enable(1),
                    disable(2)
                  }
     MAX-ACCESS   not-accessible
     STATUS       current
     DESCRIPTION
        "Flag to enable/disable AE Protocol Support Mode."
     DEFVAL  { disable }
     ::= { wsAPProfileEntry 15 }


--
--    wsAPProfileRadioTable
--
 wsAPProfileRadioTable OBJECT-TYPE
     SYNTAX       SEQUENCE OF WsAPProfileRadioEntry
     MAX-ACCESS   not-accessible
     STATUS       current
     DESCRIPTION
        "This table contains parameters that can be configured with
         in an AP Profile per radio interface."
     ::= { apProfile 3 }

 wsAPProfileRadioEntry OBJECT-TYPE
     SYNTAX       WsAPProfileRadioEntry
     MAX-ACCESS   not-accessible
     STATUS       current
     DESCRIPTION
         "Each entry in this table represents parameters
          that can be configured with in an AP profile per radio
          interface. Two entries in this table will get created
          automatically for each AP profile being created in
          wsAPProfileTable. Whenever AP profile entry is deleted,
          corresponding radio profile entries will get deleted
          automatically."
     INDEX    { wsAPProfileId, wsAPRadioInterface }
     ::= { wsAPProfileRadioTable 1 }

 WsAPProfileRadioEntry ::=
     SEQUENCE {
         wsAPRadioInterface               Integer32,
         wsAPRadioAdminMode               INTEGER,
         wsAPRadioFrequency               INTEGER,
         wsAPRadioOtherChannelsScanMode    INTEGER,
         wsAPRadioOtherChannelsScanInterval   Integer32,
         wsAPRadioSentryScanMode          INTEGER,
         wsAPRadioSentryScanChannel       INTEGER,
         wsAPRadioScanDuration            Integer32,
         wsAPRadioRateLimitMode           INTEGER,
         wsAPRadioRateLimit               Integer32,
         wsAPRadioRateLimitBurst          Integer32,
         wsAPRadioBeaconInterval          Integer32,
         wsAPRadioDTIMPeriod              Integer32,
         wsAPRadioFragmentationThreshold  Integer32,
         wsAPRadioRTSThreshold            Integer32,
         wsAPRadioShortRetryLimit         Integer32,
         wsAPRadioLongRetryLimit          Integer32,
         wsAPRadioMaxTransmitLifetime     Unsigned32,
         wsAPRadioMaxReceiveLifetime      Unsigned32,
         wsAPRadioMaxClients              Integer32,
         wsAPRadioAutoPowerMode           INTEGER,
         wsAPRadioTxPower                 Integer32,
         wsAPRadioWMMMode                 INTEGER,
         wsAPRadioLoadBalancingMode       INTEGER,
         wsAPRadioUtilization             Integer32,
         wsAPRadioAutoChannelMode         INTEGER,
         wsAPRadioStationIsolationMode    INTEGER,
         wsAPRadioChannelBandwidth        INTEGER,
         wsAPRadioPrimaryChannel          INTEGER,
         wsAPRadioProtectionMode          INTEGER,
         wsAPRadioShortGuardInterval      INTEGER,
         wsAPRadioSTBCMode                INTEGER,
         wsAPRadioMulticastTxRate         Integer32,
         wsAPRadioAPSDMode                INTEGER,
         wsAPRadioNoAckMode               INTEGER,
         wsAPRadioResourceMeasEnabled     INTEGER,
         wsAPRadioQOSEDCATemplate         INTEGER,
         wsAPRadioMinTxPower                 Integer32
--         wsAPRadioAntennaDivMode          INTEGER,
--         wsAPRadioAntennaSel              INTEGER
 }

 wsAPRadioInterface OBJECT-TYPE
     SYNTAX       Integer32(1..2)
     MAX-ACCESS   read-only
     STATUS       current
     DESCRIPTION
        "AP physical radio interface number."
     ::= { wsAPProfileRadioEntry 1 }

 wsAPRadioAdminMode OBJECT-TYPE
     SYNTAX       INTEGER {
                     on(1),
                     off(2)
                  }
     MAX-ACCESS   read-only
     STATUS       current
     DESCRIPTION
        "Flag to indicate whether the radio is operational."
     DEFVAL      { on }
     ::= { wsAPProfileRadioEntry 2 }

 wsAPRadioFrequency OBJECT-TYPE
     SYNTAX       INTEGER {
                   ieee802dot11a(1),
                   ieee802dot11bg(2),
                   ieee802dot11an(3),
                   ieee802dot11bgn(4),
                   fiveGHzIeee802dot11n(5),
                   twoDotFourGHzIeee802dot11n(6),
                   fiveGHzIeee802dot11anac(7),
                   fiveGHzIeee802dot11nac(8)
                 }
     MAX-ACCESS   read-only
     STATUS       current
     DESCRIPTION
        "Indicates which physical layer technology to use on radio.
         Default value for radio 1 is 'ieee802dot11bgn' and default value
         for radio 2 is 'ieee802dot11an'."
     ::= { wsAPProfileRadioEntry 3 }

 wsAPRadioOtherChannelsScanMode OBJECT-TYPE
     SYNTAX       INTEGER {
                    enable(1),
                    disable(2)
                  }
     MAX-ACCESS   read-only
     STATUS       current
     DESCRIPTION
        "When Sentry mode is disabled this flag controls whether the radio moves away from
        the operating channel while doing scans. When this mode is disabled the radio scans
        only on the operating channel. When sentry mode is enabled on the radio this parameter
        is ignored."
     DEFVAL      { disable }
     ::= { wsAPProfileRadioEntry 4 }

 wsAPRadioOtherChannelsScanInterval OBJECT-TYPE
     SYNTAX       Integer32(30..120)
     MAX-ACCESS   read-only
     STATUS       current
     DESCRIPTION
        "If scan mode is enable, indicates how often the radio
         leaves its operational channel."
     DEFVAL    { 60 }
     ::= { wsAPProfileRadioEntry 5 }

 wsAPRadioSentryScanMode OBJECT-TYPE
     SYNTAX       INTEGER {
                    enable(1),
                    disable(2)
                  }
     MAX-ACCESS   read-only
     STATUS       current
     DESCRIPTION
        "When Sentry mode is enabled the radio doesn't do any data forwarding, but only periodically
        scan channels for rogues. The length of time spent on each channels controlled by the
        'scan duration' time."
     DEFVAL      { disable }
     ::= { wsAPProfileRadioEntry 6 }

 wsAPRadioSentryScanChannel OBJECT-TYPE
     SYNTAX      INTEGER {
                   ieee802dot11an(1),
                   ieee802dot11bORgn(2),
                   all(3)
                 }
     MAX-ACCESS   read-only
     STATUS       current
     DESCRIPTION
        "If scanning is enabled, this object indicates on which frequencies to
         scan."
     DEFVAL    { all }
     ::= { wsAPProfileRadioEntry 7 }

 wsAPRadioScanDuration OBJECT-TYPE
     SYNTAX       Integer32(10..2000)
     MAX-ACCESS   read-only
     STATUS       current
     DESCRIPTION
        "Indicates how long the radio can scan before returning to its operational
         channel. The default value is 10ms."
     ::= { wsAPProfileRadioEntry 8 }

 wsAPRadioRateLimitMode OBJECT-TYPE
     SYNTAX       INTEGER {
                    enable(1),
                    disable(2)
                  }
     MAX-ACCESS   read-only
     STATUS       current
     DESCRIPTION
        "This object enables/disables rate limit for broadcast and multicast
         traffic transmitted across the network."
     DEFVAL   { disable }
     ::= { wsAPProfileRadioEntry 9 }

 wsAPRadioRateLimit OBJECT-TYPE
     SYNTAX       Integer32(1..50)
     MAX-ACCESS   read-only
     STATUS       current
     DESCRIPTION
        "Allowed rate limit for broadcast/multicast traffic
         transmitted across the network. Broadcast/multicast
         traffic below this limit is transmitted normally."
     DEFVAL      { 50 }
     ::= { wsAPProfileRadioEntry 10 }

 wsAPRadioRateLimitBurst OBJECT-TYPE
     SYNTAX       Integer32(1..75)
     MAX-ACCESS   read-only
     STATUS       current
     DESCRIPTION
        "Broadcast/multicast traffic can occur in bursts up to
         this value before all traffic is considered to exceed
         the limit."
     DEFVAL     { 75 }
     ::= { wsAPProfileRadioEntry 11 }

 wsAPRadioBeaconInterval OBJECT-TYPE
     SYNTAX       Integer32(20..2000)
     MAX-ACCESS   read-only
     STATUS       current
     DESCRIPTION
        "Interval at which the AP transmit beacon frames."
     DEFVAL    { 100 }
     ::= { wsAPProfileRadioEntry 12 }

 wsAPRadioDTIMPeriod OBJECT-TYPE
     SYNTAX       Integer32(1..255)
     MAX-ACCESS   read-only
     STATUS       current
     DESCRIPTION
        "Indicates the number of beacons between Delivery Traffic
         Indication MAP(DTIM). DTIM indicates buffered broadcast/multicast
         traffic on an AP."
     DEFVAL   { 10 }
     ::= { wsAPProfileRadioEntry 13 }

 wsAPRadioFragmentationThreshold OBJECT-TYPE
     SYNTAX       Integer32(256..2346)
     MAX-ACCESS   read-only
     STATUS       current
     DESCRIPTION
        "This object limits the size of packets transmitted over the network.
         Only even values are allowed in the defined range."
     DEFVAL   { 2346 }
     ::= { wsAPProfileRadioEntry 14 }

 wsAPRadioRTSThreshold OBJECT-TYPE
     SYNTAX       Integer32(0..2347)
     MAX-ACCESS   read-only
     STATUS       current
     DESCRIPTION
        "This object indicates the number of octets in an
        MAC Protocol Data Unit(MPDU), below which an
        request to send(RTS)/clear to send(CTS) handshake
        shall not be performed."
     DEFVAL   { 2347 }
     ::= { wsAPProfileRadioEntry 15 }

 wsAPRadioShortRetryLimit OBJECT-TYPE
     SYNTAX       Integer32(1..255)
     MAX-ACCESS   read-only
     STATUS       current
     DESCRIPTION
        "This object indicates the maximum number of transmission attempts on
         frame sizes less than or equal to the RTS threshold.
         Set action for this object will be supported in next release."
     DEFVAL    { 7 }
     ::= { wsAPProfileRadioEntry 16 }

 wsAPRadioLongRetryLimit OBJECT-TYPE
     SYNTAX       Integer32(1..255)
     MAX-ACCESS   read-only
     STATUS       current
     DESCRIPTION
        "This object indicates the maximum number of transmission attempts
         on frame sizes greater than the RTS threshold. Set action
         for this object will be supported in next release."
     DEFVAL    { 4 }
     ::= { wsAPProfileRadioEntry 17 }

 wsAPRadioMaxTransmitLifetime OBJECT-TYPE
     SYNTAX       Unsigned32
     MAX-ACCESS   read-only
     STATUS       current
     DESCRIPTION
        "This object indicates the elapsed time after the initial
         transmission of MAC Service Data Unit(MSDU), after
         which further attempts to transmit the MSDU shall be
         terminated. Set action for this object will be supported
         in next release."
     DEFVAL     { 512 }
     ::= { wsAPProfileRadioEntry 18 }

 wsAPRadioMaxReceiveLifetime OBJECT-TYPE
     SYNTAX       Unsigned32
     MAX-ACCESS   read-only
     STATUS       current
     DESCRIPTION
        "This object indicates the elapsed time after the initial
        reception of a fragmented MAC Management Protocol Data Unit(MMPDU)
         or MSDU, after which further attempts to reassemble
         the MMPDU or MSDU shall be terminated. Set action for
         this object will be supported in next release."
     DEFVAL     { 512 }
     ::= { wsAPProfileRadioEntry 19 }

 wsAPRadioMaxClients OBJECT-TYPE
     SYNTAX       Integer32(0..200)
     MAX-ACCESS   read-only
     STATUS       current
     DESCRIPTION
        "Maximum number of client stations that can simultaneously
         get associated on this interface."
     DEFVAL { 200 }
     ::= { wsAPProfileRadioEntry 20 }

 wsAPRadioAutoPowerMode OBJECT-TYPE
     SYNTAX       INTEGER {
                    enable(1),
                    disable(2)
                  }
     MAX-ACCESS   read-only
     STATUS       current
     DESCRIPTION
        "Flag to indicate power is automatically adjusted by
         the controller."
     DEFVAL     { enable }
     ::= { wsAPProfileRadioEntry 21 }

 wsAPRadioTxPower OBJECT-TYPE
     SYNTAX       Integer32(1..100)
     MAX-ACCESS   read-only
     STATUS       current
     DESCRIPTION
        "If auto power mode is disabled, this object indicates a fixed
         power setting for the radio."
     DEFVAL  { 100 }
     ::= { wsAPProfileRadioEntry 22 }

 wsAPRadioWMMMode OBJECT-TYPE
     SYNTAX       INTEGER {
                    enable(1),
                    disable(2)
                  }
     MAX-ACCESS   read-only
     STATUS       current
     DESCRIPTION
        "Flag to enable/disable Wi-Fi MultiMedia Mode. When enabled,
         QOS settings affect both downstream traffic to the sation
         and upstream traffic to the AP. When disabled, QOS only applies
         to downstream traffic."
     DEFVAL   { enable }
     ::= { wsAPProfileRadioEntry 23 }

 wsAPRadioLoadBalancingMode OBJECT-TYPE
     SYNTAX       INTEGER {
                    enable(1),
                    disable(2)
                  }
     MAX-ACCESS   read-only
     STATUS       current
     DESCRIPTION
        "Flag to indicate that AP will load balance users on
         this radio."
     DEFVAL   { disable }
     ::= { wsAPProfileRadioEntry 24 }

 wsAPRadioUtilization OBJECT-TYPE
     SYNTAX       Integer32(1..100)
     MAX-ACCESS   read-only
     STATUS       current
     DESCRIPTION
        "If load balancing is enabled, percentage of network utilization
         allowed on the radio before clients are denied. This value is
         displayed in percentage."
      DEFVAL   { 60 }
     ::= { wsAPProfileRadioEntry 25 }

 wsAPRadioAutoChannelMode OBJECT-TYPE
     SYNTAX       INTEGER {
                    enable(1),
                    disable(2)
                  }
     MAX-ACCESS   read-only
     STATUS       current
     DESCRIPTION
       "Flag to indicate whether initial AP radio channel assignment
        can be automatically adjusted by controller due to changes in
        radio performance."
      DEFVAL   { enable }
     ::= { wsAPProfileRadioEntry 26 }


wsAPRadioStationIsolationMode OBJECT-TYPE
     SYNTAX       INTEGER {
                    enable(1),
                    disable(2)
                  }
     MAX-ACCESS   read-only
     STATUS       current
     DESCRIPTION
        "Flag to indicate whether Station Isolation is enabled on the Radio."
     DEFVAL     { disable }
     ::= { wsAPProfileRadioEntry 27 }

  wsAPRadioChannelBandwidth OBJECT-TYPE
     SYNTAX       INTEGER {
                    twentyMHz(1),
                    fortyMHz(2),
                    eightyMHz(3)
                  }
     MAX-ACCESS   read-only
     STATUS       current
     DESCRIPTION
        "Bandwidth used in the channel."
     DEFVAL     { fortyMHz }
     ::= { wsAPProfileRadioEntry 28 }

  wsAPRadioPrimaryChannel OBJECT-TYPE
     SYNTAX       INTEGER {
                    upper(1),
                    lower(2)
                  }
     MAX-ACCESS   read-only
     STATUS       current
     DESCRIPTION
        "Specify relative location of Primary Channel in the 40 MHz channel."
     DEFVAL     { lower }
     ::= { wsAPProfileRadioEntry 29 }

  wsAPRadioProtectionMode OBJECT-TYPE
     SYNTAX       INTEGER {
                    auto(1),
                    off(2)
                  }
     MAX-ACCESS   read-only
     STATUS       current
     DESCRIPTION
        "Turn on/off Protection mechanisms."
     DEFVAL     { auto }
     ::= { wsAPProfileRadioEntry 30 }

  wsAPRadioShortGuardInterval OBJECT-TYPE
     SYNTAX       INTEGER {
                    disable(1),
                    enable(2)
                  }
     MAX-ACCESS   read-only
     STATUS       current
     DESCRIPTION
        "Dead time, in nanoseconds, between OFDM symbols which prevents
         Inter-Symbol and Inter-Carrier Interference (ISI, ICI).
         The short guard interval, when enabled, is 400ns and the standard
         guard interval, when disabled, is 800ns."
     DEFVAL     { disable }
     ::= { wsAPProfileRadioEntry 31 }

  wsAPRadioSTBCMode OBJECT-TYPE
     SYNTAX       INTEGER {
                    disable(0),
                    enable(1)
                  }
     MAX-ACCESS   not-accessible
     STATUS       current
     DESCRIPTION
        "The Space Time Block Code (STBC) Mode enables the AP to send the
         same data stream on multiple antennas at the same time. This is
         different from MIMO where the data stream is divided between
         two antennas."
     DEFVAL     { enable }
     ::= { wsAPProfileRadioEntry 32 }

  wsAPRadioMulticastTxRate OBJECT-TYPE
     SYNTAX       Integer32(0|2..127)
     MAX-ACCESS   read-only
     STATUS       current
     DESCRIPTION
       "Indicates the data rate AP will send multicast
        data to its client stations represented by a count from
        2 - 127, corresponding to data rates in multiples of
        500 kbit/s from 1 Mbit/s to 63.5 Mbit/s. 0 represents
        automatic rate selection.
        For Example :
        Supported Data Rate          Mbps
            2                          1
            4                          2
            11                         5.5
            12                         6
            18                         9 and so on."

     DEFVAL     { 0 }
     ::= { wsAPProfileRadioEntry 33 }

  wsAPRadioAPSDMode OBJECT-TYPE
     SYNTAX       INTEGER {
                    enable(1),
                    disable(2)
                  }
     MAX-ACCESS   read-only
     STATUS       current
     DESCRIPTION
        "Automatic Power Save Delivery Mode."
     DEFVAL     { enable }
     ::= { wsAPProfileRadioEntry 34 }

  wsAPRadioNoAckMode OBJECT-TYPE
     SYNTAX       INTEGER {
                    enable(1),
                    disable(2)
                  }
     MAX-ACCESS   read-only
     STATUS       current
     DESCRIPTION
        "Don't send acknowledgement to correctly received frames."
     DEFVAL     { disable }
     ::= { wsAPProfileRadioEntry 35 }


  wsAPRadioResourceMeasEnabled OBJECT-TYPE
     SYNTAX       INTEGER {
                    enable(1),
                    disable(2)
                  }
     MAX-ACCESS   not-accessible
     STATUS       current
     DESCRIPTION
        "Flag to enable/disable Radio Resource Management (RRM) as
         defined in the IEEE 802.11k specification. RRM allows wireless
         clients to request adjustments and report conditions regarding
         channel load and neighbor detection."
     DEFVAL     { enable }
     ::= { wsAPProfileRadioEntry 36 }

  wsAPRadioQOSEDCATemplate OBJECT-TYPE
     SYNTAX       INTEGER {
                    custom(0),
                    factory-default(1),
                    voice(2)
                  }
     MAX-ACCESS   not-accessible
     STATUS       current
     DESCRIPTION
        "This object indicates the QOS template choice in effect for the profile and radio."
     ::= { wsAPProfileRadioEntry 37 }

  wsAPRadioMinTxPower OBJECT-TYPE
     SYNTAX       Integer32(1..100)
     MAX-ACCESS   read-only
     STATUS       current
     DESCRIPTION
        "Minimum Transmit Power that can be set by APA on the radio.
         Default Value is 20% for 2.4Ghz Radio and 100% for 5Ghz radio."
     ::= { wsAPProfileRadioEntry 38 }


-- wsAPRadioAntennaDivMode OBJECT-TYPE
--     SYNTAX       INTEGER {
--                   enable(1),
--                    disable(2)
--                  }
--     MAX-ACCESS   not-accessible
--     STATUS       current
--     DESCRIPTION
--        "Enable/Disable Antenna Diversity."
--     DEFVAL     { disable }
--     ::= { wsAPProfileRadioEntry 36 }

--  wsAPRadioAntennaSel OBJECT-TYPE
--     SYNTAX       INTEGER {
--                     left-right (1),
--                     left-middle (2),
--                     middle-right (3)
--                  }
--     MAX-ACCESS   not-accessible
--     STATUS       current
--     DESCRIPTION
--        "Select 2 out of 3 antenna's in antenaa diversity off mode"
--     DEFVAL     { left-right }
--     ::= { wsAPProfileRadioEntry 37 }

--
--   wsAPProfileRadioSupportedRatesTable
--
 wsAPProfileRadioSupportedRatesTable OBJECT-TYPE
     SYNTAX       SEQUENCE OF WsAPProfileRadioSupportedRatesEntry
     MAX-ACCESS   not-accessible
     STATUS       current
     DESCRIPTION
       "This table represents the supported data rates by AP Profile."
     ::= { apProfile 4 }

 wsAPProfileRadioSupportedRatesEntry OBJECT-TYPE
     SYNTAX       WsAPProfileRadioSupportedRatesEntry
     MAX-ACCESS   not-accessible
     STATUS       current
     DESCRIPTION
       "Each entry in this table represents supported data rate."
     INDEX    { wsAPProfileId,wsAPRadioInterface, wsSupportedDataRate }
     ::= { wsAPProfileRadioSupportedRatesTable 1 }

 WsAPProfileRadioSupportedRatesEntry ::=
     SEQUENCE {
         wsSupportedDataRate                     Integer32,
         wsAPProfileRadioSupportedDataMode       INTEGER
 }

 wsSupportedDataRate OBJECT-TYPE
     SYNTAX       Integer32(2..127)
     MAX-ACCESS   read-only
     STATUS       current
     DESCRIPTION
       "Indicates the data rate, AP will actually support
        in setting up communications with client stations
        represented by a count from 2 - 127, corresponding
        to data rates in multiples of 500 kbit/s from 1 Mbit/s
        to 63.5 Mbit/s.
        Supported Data Rate          Mbps
            2                          1
            4                          2
            11                         5.5
            12                         6
            18                         9 and so on. "
     ::= { wsAPProfileRadioSupportedRatesEntry 1 }

 wsAPProfileRadioSupportedDataMode OBJECT-TYPE
     SYNTAX       INTEGER {
                    supported(1),
                    not-supported(2)
                  }
     MAX-ACCESS   read-only
     STATUS       current
     DESCRIPTION
        "Displays supported data rate by an AP Profile.
        Supported rates by an AP Profile depends on
        physical mode of the radio."
     ::= { wsAPProfileRadioSupportedRatesEntry 2 }
--
--   wsAPProfileRadioBasicRatesTable
--
 wsAPProfileRadioBasicRatesTable OBJECT-TYPE
     SYNTAX       SEQUENCE OF WsAPProfileRadioBasicRatesEntry
     MAX-ACCESS   not-accessible
     STATUS       current
     DESCRIPTION
       "This table represents the basic data rates advertised
        by an AP Profile.Stations connecting to this AP must
        support this set of data rates."
     ::= { apProfile 5 }

 wsAPProfileRadioBasicRatesEntry OBJECT-TYPE
     SYNTAX       WsAPProfileRadioBasicRatesEntry
     MAX-ACCESS   not-accessible
     STATUS       current
     DESCRIPTION
       "Each entry in this table represents basic data rate."
     INDEX    { wsAPProfileId,wsAPRadioInterface, wsBasicDataRate }
     ::= { wsAPProfileRadioBasicRatesTable 1 }

 WsAPProfileRadioBasicRatesEntry ::=
     SEQUENCE {
         wsBasicDataRate                 Integer32,
         wsAPProfileRadioBasicDataMode   INTEGER
 }

 wsBasicDataRate OBJECT-TYPE
     SYNTAX       Integer32(2..127)
     MAX-ACCESS   read-only
     STATUS       current
     DESCRIPTION
       "Indicates the basic data rate, AP will actually advertise
        to its client stations represented by a count from
        2 - 127, corresponding to data rates in multiples of
        500 kbit/s from 1 Mbit/s to 63.5 Mbit/s.
        For Example :
        Supported Data Rate          Mbps
            2                          1
            4                          2
            11                         5.5
            12                         6
            18                         9 and so on. "

     ::= { wsAPProfileRadioBasicRatesEntry 1 }

 wsAPProfileRadioBasicDataMode OBJECT-TYPE
     SYNTAX       INTEGER {
                    basic(1),
                    not-basic(2)
                  }
     MAX-ACCESS   read-only
     STATUS       current
     DESCRIPTION
        "Displays basic data rate advertised by an AP Profile.
        Basic rate depends on physical mode of the radio."
     ::= { wsAPProfileRadioBasicRatesEntry 2 }







--
--    wsAPProfileVAPTable
--
 wsAPProfileVAPTable OBJECT-TYPE
     SYNTAX       SEQUENCE OF WsAPProfileVAPEntry
     MAX-ACCESS   not-accessible
     STATUS       current
     DESCRIPTION
        "This table is about VAP profile configuration. When
         AP profile entry is created, corresponding eight VAP
         entries will get created for each radio. When AP Profile
         entry is get deleted, corresponding VAP entries will be
         deleted automatically."
     ::= { apProfile 6 }

 wsAPProfileVAPEntry OBJECT-TYPE
     SYNTAX       WsAPProfileVAPEntry
     MAX-ACCESS   not-accessible
     STATUS       current
     DESCRIPTION
         "Each entry in this table represents VAP profile."
     INDEX    { wsAPProfileId,wsAPRadioInterface, wsVAPId }

     ::= { wsAPProfileVAPTable 1 }

 WsAPProfileVAPEntry ::=
     SEQUENCE {
         wsVAPId                                Integer32,
         wsVAPMode                              INTEGER,
         wsVAPNetworkId                         Integer32
     }

 wsVAPId OBJECT-TYPE
     SYNTAX       Integer32(0..7)
     MAX-ACCESS   read-only
     STATUS       current
     DESCRIPTION
        "Index of the VAP with respect to the radio
         interface."
     ::= { wsAPProfileVAPEntry 1 }

 wsVAPMode OBJECT-TYPE
     SYNTAX       INTEGER {
                    enable(1),
                    disable(2)
                  }
     MAX-ACCESS   read-only
     STATUS       current
     DESCRIPTION
        "Flag to enable/disable VAP. VAP0 can not be disabled.
         In order to disable VAP0, radio must be turned off."
     DEFVAL  { enable }
     ::= { wsAPProfileVAPEntry 2 }

 wsVAPNetworkId OBJECT-TYPE
     SYNTAX       Integer32(1..32)
     MAX-ACCESS   read-only
     STATUS       current
     DESCRIPTION
        "Network configuration assigned to the VAP. By default,
         VAP 0 to 7 are assigned to Network Ids 1 to 8 in order."
     ::= { wsAPProfileVAPEntry 3 }


--
--    wsAPProfileQOSTable
--
 wsAPProfileQOSTable OBJECT-TYPE
     SYNTAX       SEQUENCE OF WsAPProfileQOSEntry
     MAX-ACCESS   not-accessible
     STATUS       current
     DESCRIPTION
        "This table displays QOS configuration. Enhanced
        Distributed Channel Access(EDCA) parameters of an AP
        affect downstream traffic from AP to the client station.
        Station EDCA parameters affect upstream traffic from the
        client station to an AP. Creation of AP Profile creates
        corresponding four qos profiles with default
        values for each radio. Deletion of AP Profile deletes the
        corresponding QOS entries in this table."
     ::= { apProfile 7 }

 wsAPProfileQOSEntry OBJECT-TYPE
     SYNTAX       WsAPProfileQOSEntry
     MAX-ACCESS   not-accessible
     STATUS       current
     DESCRIPTION
         "Each entry in this table represents QOS profile."
     INDEX    { wsAPProfileId,wsAPRadioInterface, wsQOSQueueId }
     ::= { wsAPProfileQOSTable 1 }

 WsAPProfileQOSEntry ::=
     SEQUENCE {
         wsQOSQueueId                       INTEGER,
         wsAPEDCAAIFS                       Integer32,
         wsAPEDCAMinContentionWindow        INTEGER,
         wsAPEDCAMaxContentionWindow        INTEGER,
         wsAPEDCAMaxBurst                   Integer32,
         wsStationEDCAAIFS                  Integer32,
         wsStationEDCAMinContentionWindow   INTEGER,
         wsStationEDCAMaxContentionWindow   INTEGER,
         wsStationEDCATXOPLimit             Integer32
 }

 wsQOSQueueId OBJECT-TYPE
     SYNTAX       INTEGER {
                    voice(0),
                    video(1),
                    besteffort(2),
                    background(3)
                  }
     MAX-ACCESS   read-only
     STATUS       current
     DESCRIPTION
        "This object indicates QOS Queue Id."
     ::= { wsAPProfileQOSEntry 1 }

 wsAPEDCAAIFS OBJECT-TYPE
     SYNTAX       Integer32(1..255)
     MAX-ACCESS   read-only
     STATUS       current
     DESCRIPTION
        "Specifies the wait time for data frames.
         The default values for each QOS Id is
         mentioned below:
             voice(0) - 1 msec
             video(1) - 1 msec
             besteffort(2) - 3 msec
             background(3) - 7 msec"
     ::= { wsAPProfileQOSEntry 2 }

 wsAPEDCAMinContentionWindow OBJECT-TYPE
     SYNTAX       INTEGER {
                     one(1),
                     three(3),
                     seven(7),
                     fifteen(15),
                     thirty-one(31),
                     sixty-three(63),
                     onetwenty-seven(127),
                     twofifty-five(255),
                     fivehundred-eleven(511),
                     onethousand-twentythree(1023)
                  }
     MAX-ACCESS   read-only
     STATUS       current
     DESCRIPTION
        "Specifies the upper limit of a range from
         which the initial random backoff wait time is
         determined.
         The default values for each QOS Id is
         mentioned below:
             voice(0) - 3 msec
             video(1) - 7 msec
             besteffort(2) - 15 msec
             background(3) - 15 msec"
     ::= { wsAPProfileQOSEntry 3 }

 wsAPEDCAMaxContentionWindow OBJECT-TYPE
     SYNTAX       INTEGER {
                     one(1),
                     three(3),
                     seven(7),
                     fifteen(15),
                     thirty-one(31),
                     sixty-three(63),
                     onetwenty-seven(127),
                     twofifty-five(255),
                     fivehundred-eleven(511),
                     onethousand-twentythree(1023)
                  }
     MAX-ACCESS   read-only
     STATUS       current
     DESCRIPTION
        "Specifies the upper limit for the doubling of the
         random backoff value, doubling continues until
         either the data frame is sent or this value is
         reached.
         The default values for each QOS Id is
         mentioned below:
             voice(0) - 7 msec
             video(1) - 15 msec
             besteffort(2) - 63 msec
             background(3) - 1023 msec"
     ::= { wsAPProfileQOSEntry 4 }

 wsAPEDCAMaxBurst OBJECT-TYPE
     SYNTAX       Integer32(0..999900)
     MAX-ACCESS   read-only
     STATUS       current
     DESCRIPTION
        "Specifies the maximum burst length allowed for
         packet bursts on the wireless network.
         The default values for each QOS Id is
         mentioned below:
             voice(0) - 1500 micro sec
             video(1) - 3000 micro sec
             besteffort(2) - 0 micro sec
             background(3) - 0 micro sec"
     ::= { wsAPProfileQOSEntry 5 }

 wsStationEDCAAIFS OBJECT-TYPE
     SYNTAX       Integer32(1..255)
     MAX-ACCESS   read-only
     STATUS       current
     DESCRIPTION
        "Specifies the wait time for data frames.
         The default values for each QOS Id is
         mentioned below:
             voice(0) - 2 msec
             video(1) - 2 msec
             besteffort(2) - 3 msec
             background(3) - 7 msec"
     ::= { wsAPProfileQOSEntry 6 }

 wsStationEDCAMinContentionWindow OBJECT-TYPE
     SYNTAX       INTEGER {
                     one(1),
                     three(3),
                     seven(7),
                     fifteen(15),
                     thirty-one(31),
                     sixty-three(63),
                     onetwenty-seven(127),
                     twofifty-five(255),
                     fivehundred-eleven(511),
                     onethousand-twentythree(1023)
                  }
     MAX-ACCESS   read-only
     STATUS       current
     DESCRIPTION
        "Specifies the upper limit of a range from
         which the initial random backoff wait time is
         determined for station.
         The default values for each QOS Id is
         mentioned below:
             voice(0) - 3 msec
             video(1) - 7 msec
             besteffort(2) - 15 msec
             background(3) - 15 msec"
     ::= { wsAPProfileQOSEntry 7 }

 wsStationEDCAMaxContentionWindow OBJECT-TYPE
     SYNTAX       INTEGER {
                     one(1),
                     three(3),
                     seven(7),
                     fifteen(15),
                     thirty-one(31),
                     sixty-three(63),
                     onetwenty-seven(127),
                     twofifty-five(255),
                     fivehundred-eleven(511),
                     onethousand-twentythree(1023)
                  }
     MAX-ACCESS   read-only
     STATUS       current
     DESCRIPTION
        "Specifies the upper limit for the doubling of the
         random backoff value, doubling continues until
         either the data frame is sent or this value is
         reached.
         The default values for each QOS Id is
         mentioned below:
             voice(0) - 7 msec
             video(1) - 15 msec
             besteffort(2) - 63 msec
             background(3) - 1023 msec"
     ::= { wsAPProfileQOSEntry 8 }

 wsStationEDCATXOPLimit OBJECT-TYPE
     SYNTAX       Integer32(0..65535)
     MAX-ACCESS   read-only
     STATUS       current
     DESCRIPTION
       "Specifies an interval of the time when a Wireless
        Multimedia Extensions(WME) client station has the
        right to initiate transmissions on to the wireless medium.
        The default values for each QOS Id is
        mentioned below:
             voice(0) - 47 msec
             video(1) - 94 msec
             besteffort(2) - 0 msec
             background(3) - 0 msec"
     ::= { wsAPProfileQOSEntry 9 }


--
--    wsNetworkTable
--
 wsNetworkTable OBJECT-TYPE
     SYNTAX       SEQUENCE OF WsNetworkEntry
     MAX-ACCESS   not-accessible
     STATUS       current
     DESCRIPTION
        "The following parameters can be configured for each
        network. A network may be assigned to one or more VAPs
        within an AP configuration profile. The first eight
        networks are created with default values, and cannot be deleted."
      ::= { apProfile 8 }

 wsNetworkEntry OBJECT-TYPE
     SYNTAX       WsNetworkEntry
     MAX-ACCESS   not-accessible
     STATUS       current
     DESCRIPTION
         "Each entry in this table is associated with a unique network Id."
     INDEX    { wsNetworkId }
     ::= { wsNetworkTable 1 }

 WsNetworkEntry ::=
     SEQUENCE {
         wsNetworkId                            Integer32,
         wsNetworkIdRowStatus                   RowStatus,
         wsNetworkSSID                              DisplayString,
         wsNetworkDefaultVLANId                     Integer32,
         wsNetworkHideSSIDMode                      INTEGER,
         wsNetworkDenyBcastMode                     INTEGER,
         wsNetworkMACAuthenticationMode             INTEGER,
         wsNetworkRadiusAccountingMode              INTEGER,
         wsNetworkSecurityMode                      INTEGER,
         wsNetworkWPAVersionsSupported              INTEGER,
         wsNetworkWPACipherSuites                   INTEGER,
         wsNetworkWPAKeyType                        INTEGER,
         wsNetworkWPAKey                            DisplayString,
         wsNetworkWPA2PreAuthenticationMode         INTEGER,
         wsNetworkWPA2PreAuthenticationLimit        Integer32,
         wsNetworkWPA2RoambackKeyCacheHoldtime      Integer32,
         wsNetworkStaticWEPAuthenticationMode       INTEGER,
         wsNetworkUseWEPTransferKeyIndex            Integer32,
         wsNetworkWEPKeyType                        INTEGER,
         wsNetworkWEPKeyLength                      INTEGER,
         wsNetworkWEPKey1                           DisplayString,
         wsNetworkWEPKey2                           DisplayString,
         wsNetworkWEPKey3                           DisplayString,
         wsNetworkWEPKey4                           DisplayString,
         wsClearNetworkEntry                        INTEGER,
         wsNetworkRedirectMode                      INTEGER,       -- deprecated
         wsNetworkRedirectURL                       DisplayString, -- deprecated
         wsIfNumber                                 Integer32,
         wsNetworkAuthRadiusServerName              DisplayString,
         wsNetworkAuthRadiusServerConfiguredStatus  INTEGER,
         wsNetworkAcctRadiusServerName              DisplayString,
         wsNetworkAcctRadiusServerConfiguredStatus  INTEGER,
         wsUseNetworkRadiusConfig             INTEGER,
         wsNetworkDistTunnelMode                    INTEGER,
         wsNetworkBcastKeyRefreshRate               Unsigned32,
         wsNetworkSessionKeyRefreshRate             Unsigned32,
         wsNetworkARPSuppressionMode                INTEGER,
         wsNetworkBandSteerMode                     INTEGER
     }

  wsNetworkId OBJECT-TYPE
     SYNTAX       Integer32(1..32)
     MAX-ACCESS   read-only
     STATUS       current
     DESCRIPTION
        "Network Id used to uniquely identify the network."
     ::= { wsNetworkEntry 1 }

  wsNetworkIdRowStatus OBJECT-TYPE
     SYNTAX       RowStatus
     MAX-ACCESS   read-only
     STATUS       current
     DESCRIPTION
        "Add Network ID to the network configuration table.
        The first 16 network configurations are created by default,
        they are applied to VAP-0 through VAP-15 in order on each
        radio when a new AP configuration profile is created
        (one default network configuration exists per VAP ID)."
     ::= { wsNetworkEntry 2 }

  wsNetworkSSID OBJECT-TYPE
     SYNTAX       DisplayString(SIZE(1..32))
     MAX-ACCESS   read-only
     STATUS       current
     DESCRIPTION
        "This object indicates Service Set ID specific to this Network.
        The first network is configured with a default SSID 'Guest Network',
        the rest of the networks have default SSIDs assigned based on the Network Id."
     DEFVAL    { "Guest Network" }
     ::= { wsNetworkEntry 3 }

 wsNetworkDefaultVLANId OBJECT-TYPE
     SYNTAX       Integer32(1..4094)
     MAX-ACCESS   read-only
     STATUS       current
     DESCRIPTION
        "Default VLAN Id assigned to the Network. The default VLAN
        is used if RADIUS based authentication is not configured for
        the network or the RADIUS server does not return a VLAN for
        a specific client."
     DEFVAL  { 1 }
     ::= { wsNetworkEntry 4 }

 wsNetworkHideSSIDMode OBJECT-TYPE
     SYNTAX        INTEGER {
                      enable(1),
                      disable(2)
                   }
     MAX-ACCESS   read-only
     STATUS       current
     DESCRIPTION
        "Flag to enable/disable inclusion of SSID in
         AP beacons."
     DEFVAL    { disable }
     ::= { wsNetworkEntry 5 }

 wsNetworkDenyBcastMode OBJECT-TYPE
     SYNTAX        INTEGER {
                      enable(1),
                      disable(2)
                   }
     MAX-ACCESS   read-only
     STATUS       current
     DESCRIPTION
       "If client broadcasts probe requests to all available
        SSIDs this option controls whether or not the system
        will respond to the probe request. The 'disable' mode
        means that the system responds."
     DEFVAL    { disable }
     ::= { wsNetworkEntry 6 }


 wsNetworkMACAuthenticationMode OBJECT-TYPE
     SYNTAX       INTEGER {
                     local(1),
                     radius(2),
                     disable(3)
                  }
     MAX-ACCESS   read-only
     STATUS       current
     DESCRIPTION
       "This object indicates mode to disable, or enable and specify lookup method for
        authentication via client MAC address."
     DEFVAL      { disable }
     ::= { wsNetworkEntry 10 }

  wsNetworkRadiusAccountingMode OBJECT-TYPE
     SYNTAX       INTEGER {
                    enable(1),
                    disable(2)
                  }
     MAX-ACCESS   read-only
     STATUS       current
     DESCRIPTION
        "Flag to enable/disable RADIUS accounting authentication
         for users on this network."
     DEFVAL      { disable }
     ::= { wsNetworkEntry 14 }

 wsNetworkSecurityMode OBJECT-TYPE
     SYNTAX       INTEGER {
                    none(1),
                    wepStatic(2),
                    wep802dot1x(3),
                    wpaPersonal(4),
                    wpaEnterprise(5)
                  }
     MAX-ACCESS   read-only
     STATUS       current
     DESCRIPTION
        "Specifies authentication and encryption mode on
         this network."
     DEFVAL   { none }
     ::= { wsNetworkEntry 15 }

 wsNetworkWPAVersionsSupported OBJECT-TYPE
     SYNTAX       INTEGER {
                    wpa(1),
                    wpa2(2),
                    both(3)
                  }
     MAX-ACCESS   read-only
     STATUS       current
     DESCRIPTION
         "If Wi-Fi Protected Access(WPA) encryption mode is enabled,
          this object indicates the versions of WPA allowed by
          clients on this network."
     DEFVAL      { both }
     ::= { wsNetworkEntry 16 }

 wsNetworkWPACipherSuites OBJECT-TYPE
     SYNTAX       INTEGER {
                     tkip(1),
                     ccmp(2),
                     both(3)
                  }
     MAX-ACCESS   read-only
     STATUS       current
     DESCRIPTION
       "If WPA encryption mode is enabled, this object indicates which
        encryption solutions to use for WPA clients."
     DEFVAL      { tkip }
     ::= { wsNetworkEntry 17 }

 wsNetworkWPAKeyType OBJECT-TYPE
     SYNTAX       INTEGER {
                    ascii(1)
                  }
     MAX-ACCESS   read-only
     STATUS       current
     DESCRIPTION
       "If WPA-SharedKey security mode is enabled, this object specifies
        the type of the WPA key configured. Only ascii key type
        is supported for this release."
     DEFVAL    { ascii }
     ::= { wsNetworkEntry 18 }

 wsNetworkWPAKey OBJECT-TYPE
     SYNTAX       DisplayString(SIZE(8..63))
     MAX-ACCESS   read-only
     STATUS       current
     DESCRIPTION
       "If WPA-SharedKey security mode is enabled, this object specifies
        the pre-shared secret for WPA clients.
        For ASCII - 8-63 characters."
        ::= { wsNetworkEntry 19 }

 wsNetworkWPA2PreAuthenticationMode OBJECT-TYPE
     SYNTAX       INTEGER {
                    enable(1),
                    disable(2)
                  }
     MAX-ACCESS   read-only
     STATUS       current
     DESCRIPTION
       "If WPA2 encryption is enabled, flag to enable/disable
        pre-authentication support for roaming WPA2 clients."
     DEFVAL     { enable }
     ::= { wsNetworkEntry 20 }

 wsNetworkWPA2PreAuthenticationLimit OBJECT-TYPE
     SYNTAX       Integer32(0..192)
     MAX-ACCESS   read-only
     STATUS       current
     DESCRIPTION
       "If WPA2 pre-authentication is enabled, this object specifies a
        limit on the number of APs within the peer group
        to which one client is allowed to be pre-authenticate."
     DEFVAL    { 0 }
     ::= { wsNetworkEntry 21 }
 wsNetworkWPA2RoambackKeyCacheHoldtime OBJECT-TYPE
     SYNTAX       Integer32(1..1440)
     MAX-ACCESS   read-only
     STATUS       current
     DESCRIPTION
       "Length of time in minutes a PMK will be cached by an AP after the client
        using this PMK has roamed away from this AP. Length of time
        a PMK will be cached by an AP after the PMK has been received
        from the WS. After this time has expired, the AP deletes the
        PMK entry from the security database."
     DEFVAL    { 10 }
     ::= { wsNetworkEntry 23 }

 wsNetworkStaticWEPAuthenticationMode     OBJECT-TYPE
     SYNTAX             INTEGER
                        {
                           openSystem(1),
                           sharedKey(2),
                           both(3)
                        }
     MAX-ACCESS         read-only
     STATUS             current
     DESCRIPTION
        "Indicates security configuration for static WEP."
        DEFVAL  { openSystem }
        ::= { wsNetworkEntry 24 }

 wsNetworkUseWEPTransferKeyIndex OBJECT-TYPE
     SYNTAX       Integer32(1..4)
     MAX-ACCESS   read-only
     STATUS       current
     DESCRIPTION
       "If wsNetSecurityMode is wepSharedKey, this object indicates
        which Wired Equivalent Privacy(WEP) algorithm network
        will use for encryption."
     DEFVAL    { 1 }
     ::= { wsNetworkEntry 25 }


 wsNetworkWEPKeyType OBJECT-TYPE
     SYNTAX       INTEGER {
                    ascii(1),
                    hex(2)
                  }
     MAX-ACCESS   read-only
     STATUS       current
     DESCRIPTION
       "If WEP-SharedKey security mode is enabled, this object specifies
        the type WEP key configured."
     DEFVAL    { hex }
     ::= { wsNetworkEntry 26 }

 wsNetworkWEPKeyLength OBJECT-TYPE
     SYNTAX       INTEGER {
                    sixty-four(64),
                    one-twentyeight(128)
                  }
     MAX-ACCESS   read-only
     STATUS       current
     DESCRIPTION
       "If WEP-SharedKey security mode is enabled, this object specifies
        number of bits for the WEP key."
     DEFVAL    { one-twentyeight }
     ::= { wsNetworkEntry 27 }

 wsNetworkWEPKey1 OBJECT-TYPE
     SYNTAX       DisplayString(SIZE(0|5..32))
     MAX-ACCESS   read-only
     STATUS       current
     DESCRIPTION
       "If WEP-SharedKey security mode is enabled, this object specifies
        the key for WEP clients.
        Minimum characters required for key based on key
        type/length are:
        For ASCII/64  -    5 characters
            ASCII/128 -    13 characters
            HEX/64     -    10 characters
            HEX/128    -    26 characters"
     ::= { wsNetworkEntry 28 }

 wsNetworkWEPKey2 OBJECT-TYPE
     SYNTAX       DisplayString(SIZE(0|5..32))
     MAX-ACCESS   read-only
     STATUS       current
     DESCRIPTION
       "If WEP-SharedKey security mode is enabled, this object specifies
        the key for WEP clients.
        Minimum characters required for key based on key
        type/length are:
        For ASCII/64  -    5 characters
            ASCII/128 -    13 characters
            HEX/64     -    10 characters
            HEX/128    -    26 characters"
     ::= { wsNetworkEntry 29 }

 wsNetworkWEPKey3 OBJECT-TYPE
     SYNTAX       DisplayString(SIZE(0|5..32))
     MAX-ACCESS   read-only
     STATUS       current
     DESCRIPTION
       "If WEP-SharedKey security mode is enabled, specifies
        the key for WEP clients.
        Minimum characters required for key based on key
        type/length are:
        For ASCII/64  -    5 characters
            ASCII/128 -    13 characters
            HEX/64     -    10 characters
            HEX/128    -    26 characters"
     ::= { wsNetworkEntry 30 }

 wsNetworkWEPKey4 OBJECT-TYPE
     SYNTAX       DisplayString(SIZE(0|5..32))
     MAX-ACCESS   read-only
     STATUS       current
     DESCRIPTION
       "If WEP-SharedKey security mode is enabled, this object specifies
        the key for WEP clients.
        Minimum characters required for key based on key
        type/length are:
        For ASCII/64  -    5 characters
            ASCII/128 -    13 characters
            HEX/64     -    10 characters
            HEX/128    -    26 characters"
     ::= { wsNetworkEntry 31 }


  wsClearNetworkEntry  OBJECT-TYPE
     SYNTAX       INTEGER {
                    enable(1),
                    disable(2)
                  }
     MAX-ACCESS   read-only
     STATUS       current
     DESCRIPTION
        "This is an action object. Setting this object to
         enable will set Network Id configuration to default
         configuration. Read on this object will always return disable."
      DEFVAL    { disable }
     ::= { wsNetworkEntry 33 }

 wsNetworkRedirectMode OBJECT-TYPE
     SYNTAX       INTEGER {
                    none(1),
                    http(2)
                  }
     MAX-ACCESS   not-accessible
     STATUS       deprecated
     DESCRIPTION
        "Specifies the redirect mode on
         this network."
     DEFVAL   { none }
     ::= { wsNetworkEntry 34 }

  wsNetworkRedirectURL OBJECT-TYPE
     SYNTAX       DisplayString(SIZE(0..127))
     MAX-ACCESS   not-accessible
     STATUS       deprecated
     DESCRIPTION
        "This object indicates HTTP Redirect URL on the Network Id."
     DEFVAL    { "" }
     ::= { wsNetworkEntry 35 }

  wsIfNumber  OBJECT-TYPE
    SYNTAX      Integer32
    MAX-ACCESS  read-only
    STATUS      current
    DESCRIPTION
            "A unique value to identify the wireless network interface."
    ::= { wsNetworkEntry 36 }

  wsNetworkAuthRadiusServerName OBJECT-TYPE
    SYNTAX       DisplayString (SIZE(1..32))
    MAX-ACCESS   read-only
    STATUS       current
    DESCRIPTION
                 "The name of the RADIUS server used for client
                 authentications."
    DEFVAL       { "Default-RADIUS-Server" }
    ::= { wsNetworkEntry 37 }

  wsNetworkAuthRadiusServerConfiguredStatus OBJECT-TYPE
    SYNTAX       INTEGER {
                    not-configured(1),
                    configured(2)
                 }
    MAX-ACCESS   read-only
    STATUS       current
    DESCRIPTION
                 "Indicates whether the specified named RADIUS Authentication
                  server is configured in the RADIUS Client configuration."
    DEFVAL       { not-configured }
    ::= { wsNetworkEntry 38 }

  wsNetworkAcctRadiusServerName OBJECT-TYPE
    SYNTAX       DisplayString (SIZE(1..32))
    MAX-ACCESS   read-only
    STATUS       current
    DESCRIPTION
                 "The name of the RADIUS server used for reporting wireless
                  client associations and disassociations."
    DEFVAL       { "Default-RADIUS-Server" }
    ::= { wsNetworkEntry 39 }

  wsNetworkAcctRadiusServerConfiguredStatus OBJECT-TYPE
    SYNTAX       INTEGER {
                    not-configured(1),
                    configured(2)
                 }
    MAX-ACCESS   read-only
    STATUS       current
    DESCRIPTION
                 "Indicates whether the specified named RADIUS Accounting
                 server is configured in the RADIUS Client configuration."
    DEFVAL       { not-configured }
    ::= { wsNetworkEntry 40 }

  wsUseNetworkRadiusConfig OBJECT-TYPE
    SYNTAX       INTEGER {
                 enable(1),
                 disable(2)
                 }
    MAX-ACCESS   read-only
    STATUS       current
    DESCRIPTION
                  "This flag controls whether the VAP uses the network RADIUS
                  configuration or global RADIUS configuration. When enabled,
                  network RADIUS configuration shall be used."
    DEFVAL       { enable }
    ::= { wsNetworkEntry 41 }

     wsNetworkDistTunnelMode OBJECT-TYPE
     SYNTAX       INTEGER {
                      enable(1),
                      disable(2)
                   }
     MAX-ACCESS   read-only
     STATUS       current
     DESCRIPTION
        "Flag to enable/disable Distributed Tunneling for this
         Network."
     DEFVAL   { disable }
     ::= { wsNetworkEntry 42 }

     wsNetworkBcastKeyRefreshRate OBJECT-TYPE
     SYNTAX       Unsigned32(0..86400)
     MAX-ACCESS   read-only
     STATUS       current
     DESCRIPTION
        "The 802.1x broadcastkey refresh rate command specifies the interval after
         which the broadcast keys are changed."
     DEFVAL   { 300 }
     ::= { wsNetworkEntry 43 }

     wsNetworkSessionKeyRefreshRate OBJECT-TYPE
     SYNTAX       Unsigned32
     MAX-ACCESS   read-only
     STATUS       current
     DESCRIPTION
        "The 802.1x SessionKey refresh rate command specifies the interval after
         which the Unicast session keys are changed. This is applicable only dynamic WEP and
         WPA Enterprise modes.Valid values are 0 and from 30-86400."
     DEFVAL   { 0 }
     ::= { wsNetworkEntry 44 }

   wsNetworkARPSuppressionMode OBJECT-TYPE
     SYNTAX       INTEGER {
                      enable(1),
                      disable(2)
                   }
     MAX-ACCESS   read-only
     STATUS       current
     DESCRIPTION
        "Flag to enable/disable Wireless ARP Suppression for this Network."
     DEFVAL   { disable }
     ::= { wsNetworkEntry 45 }

   wsNetworkBandSteerMode OBJECT-TYPE
        SYNTAX      INTEGER {
                    disable(0),
                    enable(1)
                    }
        MAX-ACCESS  read-write
        STATUS      current
        DESCRIPTION
            "Configure band steering on this VAP. To have band steering operationally enabled,
            the following conditions should be met:
            1.  SSIDs on both VAPs should match.
            2.  One radio should be in the 2.4-GHz band, and the other should be in the 5-GHz band."
     ::= { wsNetworkEntry 46 }
--
--    wsNetworkClientQosTable
--
 wsNetworkClientQosTable OBJECT-TYPE
     SYNTAX       SEQUENCE OF WsNetworkClientQosEntry
     MAX-ACCESS   not-accessible
     STATUS       current
     DESCRIPTION
        "The following parameters can be configured for each
         network. This table extends the wsNetworkTable definition."
      ::= { apProfile 9 }

 wsNetworkClientQosEntry OBJECT-TYPE
     SYNTAX       WsNetworkClientQosEntry
     MAX-ACCESS   not-accessible
     STATUS       current
     DESCRIPTION
         "Each entry in this table is associated with a unique network ID,
          and defines its default client QoS parameters for a managed AP.
          These parameters are used for any wireless client on the designated
          network that does not have its own comparable parameter(s) defined
          via RADIUS when using 802.1X authentication."
     AUGMENTS { wsNetworkEntry }
     ::= { wsNetworkClientQosTable 1 }

 WsNetworkClientQosEntry ::=
     SEQUENCE {
         wsNetworkClientQosBandwidthLimitDown         Unsigned32,
         wsNetworkClientQosBandwidthLimitUp           Unsigned32,
         wsNetworkClientQosAccessControlDownType      INTEGER,
         wsNetworkClientQosAccessControlDownName      DisplayString,
         wsNetworkClientQosAccessControlUpType        INTEGER,
         wsNetworkClientQosAccessControlUpName        DisplayString,
         wsNetworkClientQosDiffservPolicyDownType     INTEGER,
         wsNetworkClientQosDiffservPolicyDownName     DisplayString,
         wsNetworkClientQosDiffservPolicyUpType       INTEGER,
         wsNetworkClientQosDiffservPolicyUpName       DisplayString,
         wsNetworkClientQosMode                       INTEGER
     }

 wsNetworkClientQosBandwidthLimitDown OBJECT-TYPE
      SYNTAX      Unsigned32
      MAX-ACCESS  not-accessible
      STATUS      current
      DESCRIPTION
               "Maximum bandwidth rate allowed for the wireless down (outbound)
                direction from AP to client for this network, thus controlling
                the maximum receive rate from the AP for a wireless client.  This
                parameter is specified in bits-per-second (bps).

                This object may be set to any value in the range 0-4294967295.
                Any configured non-zero value is rounded down to the
                nearest 64000 bps by the AP, but no lower than 64000.  Setting
                this object value to 0 disables bandwidth limiting in this
                direction."
      DEFVAL   { 0 }
      ::= { wsNetworkClientQosEntry 1 }

 wsNetworkClientQosBandwidthLimitUp OBJECT-TYPE
      SYNTAX      Unsigned32
      MAX-ACCESS  not-accessible
      STATUS      current
      DESCRIPTION
               "Maximum bandwidth rate allowed for the wireless up (inbound)
                direction from client to AP for this network, thus controlling
                the maximum send rate to the AP for a wireless client.  This
                parameter is specified in bits-per-second (bps).

                This object may be set to any value in the range 0-4294967295.
                Any configured non-zero value is rounded down to the
                nearest 64000 bps by the AP, but no lower than 64000.  Setting
                this object value to 0 disables bandwidth limiting in this
                direction."
      DEFVAL   { 0 }
      ::= { wsNetworkClientQosEntry 2 }

 wsNetworkClientQosAccessControlDownType OBJECT-TYPE
     SYNTAX       INTEGER {
                    none(1),
                    ip(2),
                    mac(3),
                    ipv6(4)
                  }
     MAX-ACCESS   not-accessible
     STATUS       current
     DESCRIPTION
        "Access list type used for the wireless down (outbound) direction from
         AP to client for this network.  Setting this object usually requires
         that the wsNetworkClientQosAccessControlDownName object also be set at
         the same time (see the 'Object set restrictions' in that object's
         description for more information)."
     DEFVAL   { none }
     ::= { wsNetworkClientQosEntry 3 }

 wsNetworkClientQosAccessControlDownName OBJECT-TYPE
     SYNTAX       DisplayString(SIZE(1..31))
     MAX-ACCESS   not-accessible
     STATUS       current
     DESCRIPTION
       "Name of the access list to use in accordance with the
        wsNetworkClientQosAccessControlDownType as follows:

        none(1) - This object is not used and must not be set.

        ip(2)   - This specifies an IP access list number in the range
                  1-199, entered as a character string rather than an integer,
                  or an alphanumeric string from 1-31 characters, beginning
                  with a letter.  This must be a valid IP access list,
                  as defined by the aclTable in the FASTPATH-QOS-ACL-MIB.
        mac(3)  - This is an alphanumeric string from 1-31 characters, beginning
                  with a letter.  This must be a valid MAC access list name,
                  as defined by the aclMacName object in the FASTPATH-QOS-ACL-MIB.
        ipv6(4) - This is an alphanumeric string from 1-31 characters, beginning
                  with a letter.  This must be a valid IPV6 access list name,
                  as defined by the aclIpv6Name object in the FASTPATH-QOS-ACL-MIB.

        Note that numbered IP access lists are specified here using a character
        string notation instead of an integer value.

        Object set restrictions:
        ------------------------
        1. When setting wsNetworkClientQosAccessControlDownType to none(0), this object
           must not be set.
        2. When setting wsNetworkClientQosAccessControlDownType to any value other than
           none(0), both the wsNetworkClientQosAccessControlDownType and this object
           must be set at the same time (i.e. use multiple variable bindings).
        3. This object may be set by itself in accordance with the existing
           wsNetworkClientQosAccessControlDownType value, provided the type value
           is anything other than none(0)."
        ::= { wsNetworkClientQosEntry 4 }

 wsNetworkClientQosAccessControlUpType OBJECT-TYPE
     SYNTAX       INTEGER {
                    none(1),
                    ip(2),
                    mac(3),
                    ipv6(4)
                  }
     MAX-ACCESS   not-accessible
     STATUS       current
     DESCRIPTION
        "Access list type used for the wireless up (inbound) direction from
         client to AP for this network.  Setting this object usually requires
         that the wsNetworkClientQosAccessControlUpName object also be set at
         the same time (see the 'Object set restrictions' in that object's
         description for more information)."
     DEFVAL   { none }
     ::= { wsNetworkClientQosEntry 5 }

 wsNetworkClientQosAccessControlUpName OBJECT-TYPE
     SYNTAX       DisplayString(SIZE(1..31))
     MAX-ACCESS   not-accessible
     STATUS       current
     DESCRIPTION
       "Name of the access list to use in accordance with the
        wsNetworkClientQosAccessControlUpType as follows:

        none(1) - This object is not used and must not be set.

        ip(2)   - This specifies an IP access list number in the range
                  1-199, entered as a character string rather than an integer,
                  or an alphanumeric string from 1-31 characters, beginning
                  with a letter.  This must be a valid IP access list,
                  as defined by the aclTable in the FASTPATH-QOS-ACL-MIB.
        mac(3)  - This is an alphanumeric string from 1-31 characters, beginning
                  with a letter.  This must be a valid MAC access list name,
                  as defined by the aclMacName object in the FASTPATH-QOS-ACL-MIB.
        ipv6(4) - This is an alphanumeric string from 1-31 characters, beginning
                  with a letter.  This must be a valid IPV6 access list name,
                  as defined by the aclIpv6Name object in the FASTPATH-QOS-ACL-MIB.

        Note that numbered IP access lists are specified here using a character
        string notation instead of an integer value.

        Object set restrictions:
        ------------------------
        1. When setting wsNetworkClientQosAccessControlUpType to none(0), this object
           must not be set.
        2. When setting wsNetworkClientQosAccessControlUpType to any value other than
           none(0), both the wsNetworkClientQosAccessControlUpType and this object
           must be set at the same time (i.e. use multiple variable bindings).
        3. This object may be set by itself in accordance with the existing
           wsNetworkClientQosAccessControlUpType value, provided the type value
           is anything other than none(0)."
        ::= { wsNetworkClientQosEntry 6 }

 wsNetworkClientQosDiffservPolicyDownType OBJECT-TYPE
     SYNTAX       INTEGER {
                    none(1),
                    in(2)
                  }
     MAX-ACCESS   not-accessible
     STATUS       current
     DESCRIPTION
        "DiffServ policy type used for the wireless down (outbound) direction from
         AP to client for this network.  Setting this object usually requires
         that the wsNetworkClientQosDiffservPolicyDownName object also be set at
         the same time (see the 'Object set restrictions' in that object's
         description for more information).

         Only DiffServ policy defintions of type 'in' are supported for wireless
         client QoS operation."
     DEFVAL   { none }
     ::= { wsNetworkClientQosEntry 7 }

 wsNetworkClientQosDiffservPolicyDownName OBJECT-TYPE
     SYNTAX       DisplayString(SIZE(1..31))
     MAX-ACCESS   not-accessible
     STATUS       current
     DESCRIPTION
       "Name of the DiffServ policy to use in accordance with the
        wsNetworkClientQosDiffservPolicyDownType as follows:

        none(1) - This object is not used and must not be set.

        in(2)   - This is an alphanumeric string from 1-31 characters, beginning
                  with a letter.  This must be a valid DiffServ policy name,
                  as defined by the agentDiffServPolicyName object in the
                  FASTPATH-QOS-DIFFSERV-PRIVATE-MIB.

        Note that only DiffServ policy defintions of type 'in' are supported for
        wireless client QoS operation.

        Object set restrictions:
        ------------------------
        1. When setting wsNetworkClientQosDiffservPolicyDownType to none(0), this object
           must not be set.
        2. When setting wsNetworkClientQosDiffservPolicyDownType to any value other than
           none(0), both the wsNetworkClientQosDiffservPolicyDownType and this object
           must be set at the same time (i.e. use multiple variable bindings).
        3. This object may be set by itself in accordance with the existing
           wsNetworkClientQosDiffservPolicyDownType value, provided the type value
           is anything other than none(0)."
        ::= { wsNetworkClientQosEntry 8 }

 wsNetworkClientQosDiffservPolicyUpType OBJECT-TYPE
     SYNTAX       INTEGER {
                    none(1),
                    in(2)
                  }
     MAX-ACCESS   not-accessible
     STATUS       current
     DESCRIPTION
        "DiffServ policy type used for the wireless up (inbound) direction from
         client to AP for this network.  Setting this object usually requires
         that the wsNetworkClientQosDiffservPolicyUpName object also be set at
         the same time (see the 'Object set restrictions' in that object's
         description for more information).

         Only DiffServ policy defintions of type 'in' are supported for wireless
         client QoS operation."
     DEFVAL   { none }
     ::= { wsNetworkClientQosEntry 9 }

 wsNetworkClientQosDiffservPolicyUpName OBJECT-TYPE
     SYNTAX       DisplayString(SIZE(1..31))
     MAX-ACCESS   not-accessible
     STATUS       current
     DESCRIPTION
       "Name of the DiffServ policy to use in accordance with the
        wsNetworkClientQosDiffservPolicyUpType as follows:

        none(1) - This object is not used and must not be set.

        in(2)   - This is an alphanumeric string from 1-31 characters, beginning
                  with a letter.  This must be a valid DiffServ policy name,
                  as defined by the agentDiffServPolicyName object in the
                  FASTPATH-QOS-DIFFSERV-PRIVATE-MIB.

        Note that only DiffServ policy defintions of type 'in' are supported for
        wireless client QoS operation.

        Object set restrictions:
        ------------------------
        1. When setting wsNetworkClientQosDiffservPolicyUpType to none(0), this object
           must not be set.
        2. When setting wsNetworkClientQosDiffservPolicyUpType to any value other than
           none(0), both the wsNetworkClientQosDiffservPolicyUpType and this object
           must be set at the same time (i.e. use multiple variable bindings).
        3. This object may be set by itself in accordance with the existing
           wsNetworkClientQosDiffservPolicyUpType value, provided the type value
           is anything other than none(0)."
        ::= { wsNetworkClientQosEntry 10 }


 wsNetworkClientQosMode OBJECT-TYPE
     SYNTAX        INTEGER {
                      enable(1),
                      disable(2)
                   }
     MAX-ACCESS   not-accessible
     STATUS       current
     DESCRIPTION
        "Flag to enable/disable AP quality-of-service for wireless clients
         on this network."
     DEFVAL    { disable }
     ::= { wsNetworkClientQosEntry 11 }


--
--   wsAPProfileRadioSupportedChannelsTable
--
 wsAPProfileRadioSupportedChannelsTable OBJECT-TYPE
     SYNTAX       SEQUENCE OF WsAPProfileRadioSupportedChannelsEntry
     MAX-ACCESS   not-accessible
     STATUS       current
     DESCRIPTION
       "This table represents the supported channels by AP Profile."
     ::= { apProfile 10 }

 wsAPProfileRadioSupportedChannelsEntry OBJECT-TYPE
     SYNTAX       WsAPProfileRadioSupportedChannelsEntry
     MAX-ACCESS   not-accessible
     STATUS       current
     DESCRIPTION
       "Each entry in this table represents a supported channel."
     INDEX    { wsAPProfileId,wsAPRadioInterface,wsSupportedChannel  }
     ::= { wsAPProfileRadioSupportedChannelsTable 1 }

 WsAPProfileRadioSupportedChannelsEntry ::=
     SEQUENCE {
         wsSupportedChannel                     Integer32
 }

 wsSupportedChannel OBJECT-TYPE
     SYNTAX       Integer32(1..255)
     MAX-ACCESS   read-only
     STATUS       current
     DESCRIPTION
       "Indicates a channel currently supported by the radio
        for use with client connections.  The set of supported
        channel numbers is determined by country code, radio
        mode, and in the case of modes that are compatible with
        802.11n, primary channel selection and channel bandwidth
        settings."
     ::= { wsAPProfileRadioSupportedChannelsEntry 1 }



--
--   wsAPProfileRadioEligibleChannelsTable
--
 wsAPProfileRadioEligibleChannelsTable OBJECT-TYPE
     SYNTAX       SEQUENCE OF WsAPProfileRadioEligibleChannelsEntry
     MAX-ACCESS   not-accessible
     STATUS       current
     DESCRIPTION
       "This table represents the channels of an AP profile that are eligible for automatic channel selection."
     ::= { apProfile 11 }

 wsAPProfileRadioEligibleChannelsEntry OBJECT-TYPE
     SYNTAX       WsAPProfileRadioEligibleChannelsEntry
     MAX-ACCESS   not-accessible
     STATUS       current
     DESCRIPTION
       "Each entry in this table represents an eligible channel."
     INDEX    { wsAPProfileId, wsAPRadioInterface, wsEligibleChannel }
     ::= { wsAPProfileRadioEligibleChannelsTable 1 }

 WsAPProfileRadioEligibleChannelsEntry ::=
     SEQUENCE {
         wsEligibleChannel                     Integer32,
         wsEligibleChannelRowStatus            RowStatus
 }

 wsEligibleChannel OBJECT-TYPE
     SYNTAX       Integer32(1..255)
     MAX-ACCESS   read-only
     STATUS       current
     DESCRIPTION
       "Indicates a channel currently eligible for automatic channel
        selection by the radio for use with client connections.  The
        set of eligible channel numbers is a subset of the channels
        supported by the radio in its current configuration of country,
        mode, and in the case of modes that are compatible with
        802.11n, primary channel selection and channel bandwidth
        settings. For 80Mhz 4 channels form a set and setting one channel
        would unset all the remaining channels in the set. Deleting one channel
        would unset all the channels in the set."
     ::= { wsAPProfileRadioEligibleChannelsEntry 1 }


wsEligibleChannelRowStatus    OBJECT-TYPE
     SYNTAX       RowStatus
     MAX-ACCESS   read-only
     STATUS       current
     DESCRIPTION  "The eligible channel status.
                   Supported values:
                   active(1)       - valid instance
                   createAndGo(4)  - creates a new instance
                   destroy(6)      - removes an instance"
     ::= { wsAPProfileRadioEligibleChannelsEntry 2 }


--
--    wsAPProfileRadioTspecTable
--
 wsAPProfileRadioTspecTable OBJECT-TYPE
     SYNTAX       SEQUENCE OF WsAPProfileRadioTspecEntry
     MAX-ACCESS   not-accessible
     STATUS       current
     DESCRIPTION
        "This table contains TSPEC parameters that can be configured
         within an AP Profile per radio interface."
     ::= { apProfile 12 }

 wsAPProfileRadioTspecEntry OBJECT-TYPE
     SYNTAX       WsAPProfileRadioTspecEntry
     MAX-ACCESS   not-accessible
     STATUS       current
     DESCRIPTION
         "Each entry in this table represents TSPEC parameters
          that can be configured per radio interface within an
          AP profile. These entries augment the wsAPProfileRadioEntry
          definition for TSPEC configuration."
     AUGMENTS    { wsAPProfileRadioEntry }
     ::= { wsAPProfileRadioTspecTable 1 }

 WsAPProfileRadioTspecEntry ::=
     SEQUENCE {
         wsAPRadioTspecMode                    INTEGER,
         wsAPRadioTspecVoiceAcmMode            INTEGER,
         wsAPRadioTspecVideoAcmMode            INTEGER,
         wsAPRadioTspecVoiceAcmLimit           Unsigned32,
         wsAPRadioTspecVideoAcmLimit           Unsigned32,
         wsAPRadioTspecRoamReserveLimit        Unsigned32,
         wsAPRadioTspecApInactivityTimeout     Unsigned32,
         wsAPRadioTspecStaInactivityTimeout    Unsigned32,
         wsAPRadioTspecLegacyWmmQueueMapMode   INTEGER
 }

 wsAPRadioTspecMode OBJECT-TYPE
     SYNTAX       INTEGER {
                    enable(1),
                    disable(2)
                  }
     MAX-ACCESS   not-accessible
     STATUS       current
     DESCRIPTION
        "The overall TSPEC operational mode for this radio.
         This object must be set to enable(1) for any of the
         other TSPEC ACM configuration parameters defined in
         this table row to have an effect.  The default value
         for this object is disable(2)."
     DEFVAL      { disable }
     ::= { wsAPProfileRadioTspecEntry 1 }

 wsAPRadioTspecVoiceAcmMode OBJECT-TYPE
     SYNTAX       INTEGER {
                    enable(1),
                    disable(2)
                  }
     MAX-ACCESS   not-accessible
     STATUS       current
     DESCRIPTION
        "Regulates mandatory admission control for the voice
         access category (AC).  When set to enable(1), the
         voice AC may only be used by WMM-compliant client
         stations that have successfully established a TSPEC
         for this AC.

         Note that setting the wsAPRadioTspecLegacyWmmQueueMapMode
         object to enable(1) overrides the exclusive use of the
         voice AC by allowing legacy (i.e. non-WMM-compliant) client
         stations to use it as well."
     DEFVAL      { disable }
     ::= { wsAPProfileRadioTspecEntry 2 }

 wsAPRadioTspecVideoAcmMode OBJECT-TYPE
     SYNTAX       INTEGER {
                    enable(1),
                    disable(2)
                  }
     MAX-ACCESS   not-accessible
     STATUS       current
     DESCRIPTION
        "Regulates mandatory admission control for the video
         access category (AC).  When set to enable(1), the
         video AC may only be used by WMM-compliant client
         stations that have successfully established a TSPEC
         for this AC.

         Note that setting the wsAPRadioTspecLegacyWmmQueueMapMode
         object to enable(1) overrides the exclusive use of the
         video AC by allowing legacy (i.e. non-WMM-compliant) client
         stations to use it as well."
     DEFVAL      { disable }
     ::= { wsAPProfileRadioTspecEntry 3 }

 wsAPRadioTspecVoiceAcmLimit OBJECT-TYPE
     SYNTAX       Unsigned32(0|1..70)
     MAX-ACCESS   not-accessible
     STATUS       current
     DESCRIPTION
        "Defines the maximum amount of wireless bandwidth utilization to admit
         for the voice access category.  TSPEC requests that would cause
         this limit to be exceeded are rejected.

         Note that this value establishes an upper limit for wireless bandwidth
         to be admitted for this access category but does not guarantee that this
         limit can be reached.

         Setting this object value to 0 and the wsAPRadioTspecVoiceAcmMode object
         to enable(1) causes all TSPEC requests to be rejected by the AP for the
         voice access category.

         The sum of this value and the wsAPRadioTspecVideoAcmLimit object value
         is not allowed to exceed 70.

         This value is treated as a percentage."
      DEFVAL   { 20 }
     ::= { wsAPProfileRadioTspecEntry 4 }

 wsAPRadioTspecVideoAcmLimit OBJECT-TYPE
     SYNTAX       Unsigned32(0|1..70)
     MAX-ACCESS   not-accessible
     STATUS       current
     DESCRIPTION
        "Defines the maximum amount of wireless bandwidth utilization to admit
         for the video access category.  TSPEC requests that would cause
         this limit to be exceeded are rejected.

         Note that this value establishes an upper limit for wireless bandwidth
         to be admitted for this access category but does not guarantee that this
         limit can be reached.

         Setting this object value to 0 and the wsAPRadioTspecVideoAcmMode object
         to enable(1) causes all TSPEC requests to be rejected by the AP for the
         video access category.

         The sum of this value and the wsAPRadioTspecVoiceAcmLimit object value
         is not allowed to exceed 70.

         This value is treated as a percentage."
      DEFVAL   { 15 }
     ::= { wsAPProfileRadioTspecEntry 5 }

 wsAPRadioTspecRoamReserveLimit OBJECT-TYPE
     SYNTAX       Unsigned32(0|1..70)
     MAX-ACCESS   not-accessible
     STATUS       current
     DESCRIPTION
        "Defines the portion of the wsAPRadioTspecVoiceAcmLimit and
         wsAPRadioTspecVideoAcmLimit object values to hold in reserve
         for roaming clients only.

         If this value exceeds the current value in either of those two
         objects, respectively, then their entire ACM limit is used
         exclusively for roaming clients.

         Setting this object value to 0 causes none of the voice or video
         ACM limit values to be reserved for roaming clients - they compete
         equally with non-roaming clients for wireless network bandwidth.

         This value is treated as a percentage."
      DEFVAL   { 5 }
     ::= { wsAPProfileRadioTspecEntry 6 }

 wsAPRadioTspecApInactivityTimeout OBJECT-TYPE
     SYNTAX       Unsigned32(0|1..120)
     MAX-ACCESS   not-accessible
     STATUS       current
     DESCRIPTION
        "Specifies the amount of time that an active traffic stream (TS)
         in the downlink direction may be idle, from the perspective of
         the AP, before it is deleted by the AP.

         For a bidirectional TS, both the wsAPRadioTspecApInactivityTimeout
         and the wsAPRadioTspecStaInactivityTimeout must expire in order
         for the TS to be deleted by the AP due to inactivity.  If either
         of these timeouts is disabled, the AP will not delete a
         bidirectional TS due to inactivity.

         This value is specified in seconds.  Setting this object value
         to 0 disables this timeout."
      DEFVAL   { 30 }
     ::= { wsAPProfileRadioTspecEntry 7 }

 wsAPRadioTspecStaInactivityTimeout OBJECT-TYPE
     SYNTAX       Unsigned32(0|1..120)
     MAX-ACCESS   not-accessible
     STATUS       current
     DESCRIPTION
        "Specifies the amount of time that an active traffic stream (TS)
         in the uplink direction may be idle, from the perspective of
         the AP, before it is deleted by the AP.

         For a bidirectional TS, both the wsAPRadioTspecApInactivityTimeout
         and the wsAPRadioTspecStaInactivityTimeout must expire in order
         for the TS to be deleted by the AP due to inactivity.  If either
         of these timeouts is disabled, the AP will not delete a
         bidirectional TS due to inactivity.

         This value is specified in seconds.  Setting this object value
         to 0 disables this timeout."
      DEFVAL   { 30 }
     ::= { wsAPProfileRadioTspecEntry 8 }

 wsAPRadioTspecLegacyWmmQueueMapMode OBJECT-TYPE
     SYNTAX       INTEGER {
                    enable(1),
                    disable(2)
                  }
     MAX-ACCESS   not-accessible
     STATUS       current
     DESCRIPTION
        "When enabled, the AP allows intermixing of legacy traffic
         with Wi-Fi Multimedia (WMM) traffic on access category
         queues that are operating according to admission control
         mandatory (ACM) rules.

         This mode is intended for use with non Wi-Fi Multimedia Enabled
         (non-WME) clients and is disabled by default.  When this object
         is set to enable(1), both the voice and video access categories
         are accessible by wireless clients that do not have an admitted
         TSPEC, which can lead to underestimation of the available medium
         time by wireless TSPEC admission control. Use caution when enabling
         this mode and also consider using very small ACM limit values as well."
     DEFVAL      { disable }
     ::= { wsAPProfileRadioTspecEntry 9 }


--
--    wsAPProfileRadioMCSIndexTable
--

 wsAPProfileRadioMCSIndexTable OBJECT-TYPE
     SYNTAX       SEQUENCE OF WsAPProfileRadioMCSIndexEntry
     MAX-ACCESS   not-accessible
     STATUS       obsolete
     DESCRIPTION
        "This table contains MCS indices that can be configured
         within an AP Profile per radio interface."
     ::= { apProfile 13 }

 wsAPProfileRadioMCSIndexEntry OBJECT-TYPE
     SYNTAX       WsAPProfileRadioMCSIndexEntry
     MAX-ACCESS   not-accessible
     STATUS       obsolete
     DESCRIPTION
         "Each entry in this table represents an MCS index that can
          be configured per radio interface within an AP profile. "
     INDEX    { wsAPProfileId, wsAPRadioInterface, wsAPRadioMCSIndexValue }
     ::= { wsAPProfileRadioMCSIndexTable 1 }


 WsAPProfileRadioMCSIndexEntry ::=
     SEQUENCE {
         wsAPRadioMCSIndexValue         Unsigned32,
         wsAPRadioMCSIndexAvailable     INTEGER
 }

 wsAPRadioMCSIndexValue OBJECT-TYPE
     SYNTAX       Unsigned32(0..23)
     MAX-ACCESS   read-only
     STATUS       obsolete
     DESCRIPTION
       "Indicates an index value available for use with the Modulation
        and Coding Scheme (MCS) for 802.11n connections. Not all radios
        support index values from 16 to 23."
     ::= { wsAPProfileRadioMCSIndexEntry 1 }

 wsAPRadioMCSIndexAvailable OBJECT-TYPE
     SYNTAX       INTEGER {
                    disable(0),
                    enable(1)
                  }
     MAX-ACCESS   read-only
     STATUS       obsolete
     DESCRIPTION
       "Indicates that the associated index value has or has not been
        configured for use with the Modulation and Coding Scheme (MCS)
        for 802.11n connections."
     ::= { wsAPProfileRadioMCSIndexEntry 2 }



--**************************************************************************************
-- apCodeDownload
--**************************************************************************************
    wsAPCodeDownloadServerIP    OBJECT-TYPE
         SYNTAX      IpAddress
         MAX-ACCESS  read-only
         STATUS      current
         DESCRIPTION
                   "Indicates the server IP address to use for an
                    AP code download request."
         ::= { apCodeDownload 1 }
    wsAPImageTypeFileTable OBJECT-TYPE
         SYNTAX       SEQUENCE OF WsAPImageTypeFileEntry
         MAX-ACCESS   not-accessible
         STATUS       current
         DESCRIPTION
         "The AP image type capability table contain parameters that
         are configurable for each image type download."
         ::= { apCodeDownload 2 }

    wsAPImageTypeFileEntry OBJECT-TYPE
         SYNTAX       WsAPImageTypeFileEntry
         MAX-ACCESS   not-accessible
         STATUS       current
         DESCRIPTION
         "Each entry provides image type capability details for each AP image
         type supported by the WS."
         INDEX    { wsAPImageTypeID }
         ::= { wsAPImageTypeFileTable 1 }

    WsAPImageTypeFileEntry ::=
         SEQUENCE {
       wsAPImageFilePath                              DisplayString,
       wsAPImageFileName                              DisplayString
    }

    wsAPImageFilePath    OBJECT-TYPE
         SYNTAX      DisplayString (SIZE(0..96))
         MAX-ACCESS  read-only
         STATUS      current
         DESCRIPTION
                   "Indicates the file path on the server to use
                    for an AP code download request."
         ::= { wsAPImageTypeFileEntry 1 }

    wsAPImageFileName    OBJECT-TYPE
         SYNTAX      DisplayString (SIZE(0..32))
         MAX-ACCESS  read-only
         STATUS      current
         DESCRIPTION
                   "Indicates file on the server to use
                    for an AP code download request."
         ::= { wsAPImageTypeFileEntry 2 }

    wsAPCodeDownloadMACAddress    OBJECT-TYPE
         SYNTAX      MacAddress
         MAX-ACCESS  read-only
         STATUS      current
         DESCRIPTION
                   "Indicates an AP MAC address to use in a code download request for a single AP.
                    MAC address zero indicates the code download request is for all managed APs.
                    Setting this object initiates the code download.
                    A read on this object always returns zero."
         ::= { apCodeDownload 3 }

    wsAPCodeDownloadGroupSize    OBJECT-TYPE
         SYNTAX      Integer32(1..48)
         MAX-ACCESS  read-only
         STATUS      current
         DESCRIPTION
                   "Indicates the number of APs the wireless controller
                    will issue a code download request to at one time."
         DEFVAL  { 10 }
         ::= { apCodeDownload 4 }

    wsAPCodeDownloadImageType    OBJECT-TYPE
         SYNTAX      INTEGER {
                         tq3600(1),
                         image2(2),
                         image3(3),
                         tq2450(4),
                         tq4400(5),
                         tq4600(6),
                         tq3200(7),
                         tq3400(8),
                         all(9)
                     }
         MAX-ACCESS  read-only
         STATUS      current
         DESCRIPTION
             "Indicates which image to download to the AP(s). Configurable values are:
              - tq3600, if download is for APs with hardware that only require tq3600 code
              - image2, reserved future
              - image3, reserved future
              - tq2450, if download is for APs with hardware that only require tq2450 code
              - tq4400, if download is for APs with hardware that only require tq4400 code
              - tq4600, if download is for APs with hardware that only require tq4600 code
              - tq3200, if download is for APs with hardware that only require tq3200 code
              - tq3400, if download is for APs with hardware that only require tq3400 code
              - all, if download involves APs that require tq3600, tq2450, tq4400, tq4600, tq3200, and tq3400 code"
         ::= { apCodeDownload 5 }

    wsAPCodeDownloadStatus    OBJECT-TYPE
         SYNTAX      INTEGER {
                         not-started(1),
                         requested(2),
                         code-transfer-in-progress(3),
                         aborted(4),
                         nvram-update-in-progress(5),
                         success(6),
                         failure(7)
                     }
         MAX-ACCESS  read-only
         STATUS      current
         DESCRIPTION
             "This indicates the current status for an AP
              code download request. Default value is not started."
         ::= { apCodeDownload 6 }

    wsAPCodeDownloadTotalCount    OBJECT-TYPE
         SYNTAX      Integer32(1..48)
         MAX-ACCESS  read-only
         STATUS      current
         DESCRIPTION
             "Indicates the number of WS managed APs at the
              time a code download request is started.
              Value is 1 if a download request is for single AP."
         ::= { apCodeDownload 7 }

    wsAPCodeDownloadSuccessCount    OBJECT-TYPE
         SYNTAX      Integer32(0..48)
         MAX-ACCESS  read-only
         STATUS      current
         DESCRIPTION
             "Indicates the total number of APs that have
              successfully completed code download."
         ::= { apCodeDownload 8 }

    wsAPCodeDownloadFailureCount    OBJECT-TYPE
         SYNTAX      Integer32(0..48)
         MAX-ACCESS  read-only
         STATUS      current
         DESCRIPTION
             "Indicates the total number of APs that have
              failed to complete a code download."
         ::= { apCodeDownload 9 }

    wsAPCodeDownloadAbortCount    OBJECT-TYPE
         SYNTAX      Integer32(0..48)
         MAX-ACCESS  read-only
         STATUS      current
         DESCRIPTION
             "Indicates the total number of APs aborted from the code download."
         ::= { apCodeDownload 10 }

    wsAPCodeDownloadAbort    OBJECT-TYPE
         SYNTAX      INTEGER {
                        disable(0),
                        enable(1)
                     }
         MAX-ACCESS  read-only
         STATUS      current
         DESCRIPTION
                   "Abort the current code download on managed AP(s).

                   Supported values:
                   disable(0) - Code download is not to be aborted.
                   enable(1)  - Code download is to be aborted."
         ::= { apCodeDownload 11 }

--**************************************************************************************
-- rfManagement
--**************************************************************************************
--
--   wsChannelPlanTable
--
  wsChannelPlanTable OBJECT-TYPE
     SYNTAX       SEQUENCE OF WsChannelPlanEntry
     MAX-ACCESS   not-accessible
     STATUS       current
     DESCRIPTION
        "This table displays the channel plan parameters."
     ::= { rfManagement 1 }

    wsChannelPlanEntry OBJECT-TYPE
     SYNTAX       WsChannelPlanEntry
     MAX-ACCESS   not-accessible
     STATUS       current
     DESCRIPTION
        "Each entry in this table will indicate the channel
         plan parameters for specific radio frequency."
     INDEX { wsChannelPlan }
     ::= { wsChannelPlanTable 1 }

 WsChannelPlanEntry ::=
     SEQUENCE {
      wsChannelPlan                         INTEGER,
      wsChannelPlanMode                     INTEGER,
      wsChannelPlanInterval                 Integer32,
      wsChannelPlanTime                     Integer32,
      wsChannelPlanHistoryDepth             Integer32,
      wsChannelPlanOperatingStatus          INTEGER,
      wsChannelPlanLastIterationStatus      Integer32,
      wsChannelPlanManualAction             INTEGER,
      wsChannelPlanManualStatus             INTEGER,
      wsChannelPlanLastAlgorithmTime        DisplayString,
      wsChannelPlanChangeThreshold          Integer32,
      wsChannelPlanChangeThresholdAdj       Integer32,
      wsChannelPlanIgnoreUnamangedAPs       INTEGER,
      wsChannelPlanRunOnManagedApFailure    INTEGER,
      wsChannelPlanManagedAPFailureInterval Integer32,
      wsChannelPlanNumOfRadios              Integer32,
      wsChannelPlanNumOfRadiosAnalysed      Integer32,
      wsChannelPlanNumOfRadiosScanned       Integer32,
      wsChannelPlanNumOfRadiosChanged       Integer32,
      wsChannelPlanNumOfRadiosChangedToOrigChannel Integer32,
      wsChannelPlanEstimatedTimeOfCompletion  DisplayString,
      wsChannelPlanPercentageComplete         Integer32
 }

 wsChannelPlan  OBJECT-TYPE
     SYNTAX       INTEGER {
                   ieee802dot11an(1),
                   ieee802dot11bORgn(2)
                  }
     MAX-ACCESS   read-only
     STATUS       current
     DESCRIPTION
        "This object indicates the whether the channel plan
          is for ieee802dot11bORgn or ieee802dot11an."
     ::= {wsChannelPlanEntry  1 }

 wsChannelPlanMode  OBJECT-TYPE
     SYNTAX       INTEGER {
                         manual(1),
                         interval(2),
                         time(3)
                    }
     MAX-ACCESS   read-only
     STATUS       current
     DESCRIPTION
        "Indicates mode of computing and applying channel adjustments
        for managed AP radios operating in 2.4Ghz and 5Ghz band."
     DEFVAL    { manual }
     ::= {wsChannelPlanEntry  2 }

 wsChannelPlanInterval  OBJECT-TYPE
     SYNTAX       Integer32(10..1440)
     MAX-ACCESS   read-only
     STATUS       current
     DESCRIPTION
        "If channel plan mode is interval, this object indicates
         a regular interval in minutes at which to compute and apply a new
         channel adjustments."
     ::= {wsChannelPlanEntry  3 }

  wsChannelPlanTime    OBJECT-TYPE
      SYNTAX      Integer32(0..1440)
      MAX-ACCESS  read-only
      STATUS      current
      DESCRIPTION
          "If channel plan mode is time, this object indicates the next
           scheduled time in minutes at which to compute and apply a
           new channel adjustments. Zero minutes stands for mid-night."
      DEFVAL      { 0 }
      ::= { wsChannelPlanEntry 4 }

  wsChannelPlanHistoryDepth    OBJECT-TYPE
      SYNTAX     Integer32 (0..10)
      MAX-ACCESS  read-only
      STATUS      obsolete
      DESCRIPTION
         "Indicates the maximum number of previously applied channel
          algorithm iterations stored on the controller and used in the
          next channel adjustment computation."
      DEFVAL      { 5 }
      ::= { wsChannelPlanEntry 5 }

  wsChannelPlanOperatingStatus    OBJECT-TYPE
      SYNTAX      INTEGER {
                       active(1),
                       inActive(2)
                     }
      MAX-ACCESS  read-only
      STATUS      current
      DESCRIPTION
         "Indicates whether or not automatic channel adjustment
          is operating for managed AP radios operating in
          2.4Ghz and 5Ghz band."
       DEFVAL          { active }
      ::= { wsChannelPlanEntry 6 }

  wsChannelPlanLastIterationStatus    OBJECT-TYPE
      SYNTAX      Integer32(0..10)
      MAX-ACCESS  read-only
      STATUS      obsolete
      DESCRIPTION
         "Indicates the current iteration of channel plan
          adjustments for managed AP radio."
      ::= { wsChannelPlanEntry 7 }

 wsChannelPlanManualAction    OBJECT-TYPE
     SYNTAX      INTEGER {
                       none(1),
                       start(2),
                       abort(3),
                       clear(4)
                     }
     MAX-ACCESS  read-only
     STATUS      current
     DESCRIPTION
       "This action object is used to:
                - Run the Proposed Channel Adjustment alogorithm
                - Abort the channel plan.
                - Clear the calculated 2.4Ghz and 5Ghz channel plan.
        Read on this object will always return none."
     ::= { wsChannelPlanEntry 8 }

 wsChannelPlanManualStatus    OBJECT-TYPE
     SYNTAX      INTEGER {
                       none(1),
                       algorithm-in-progress(2),
                       algorithm-complete(3),
                       apply-in-process(4),
                       apply-complete(5)
                     }
    MAX-ACCESS  read-only
    STATUS      obsolete
    DESCRIPTION
       "Indicates the current state of a manual request
        to compute or apply proposed channel adjustments."
    ::= { wsChannelPlanEntry 9 }

 wsChannelPlanLastAlgorithmTime   OBJECT-TYPE
    SYNTAX     DisplayString
    MAX-ACCESS  read-only
    STATUS      current
    DESCRIPTION
       "The time since the last channel plan algorithm ran."
    ::= { wsChannelPlanEntry 10 }

 wsChannelPlanChangeThreshold    OBJECT-TYPE
    SYNTAX     Integer32 (-99..-1)
    MAX-ACCESS  read-only
    STATUS      current
    DESCRIPTION
      "The minimum signal strength (dBm) with which a neighbor must be detected
       on the current operational channel in order for the channel plan to consider
       moving away from the current channel."
    DEFVAL      { -82 }
    ::= { wsChannelPlanEntry  11 }

 wsChannelPlanChangeThresholdAdj  OBJECT-TYPE
    SYNTAX     Integer32 (0..5)
    MAX-ACCESS  read-only
    STATUS      current
    DESCRIPTION
       "The number of dBm by which to reduce the Channel Change Threshold for detected managed APs based on the Transmit Power of the detected managed APs."
    DEFVAL     {2}
    ::= {wsChannelPlanEntry 20 }

 wsChannelPlanIgnoreUnamangedAPs  OBJECT-TYPE
     SYNTAX       INTEGER {
                        enable(1),
                        disable(2)
                    }
     MAX-ACCESS   read-only
     STATUS       current
     DESCRIPTION
     "When enabled, the channel plan does not take into account the interfering unmanaged APs.
      Only managed APs are used for generating the channel plan."
     DEFVAL    { enable }
     ::= {wsChannelPlanEntry  12 }

  wsChannelPlanRunOnManagedApFailure  OBJECT-TYPE
     SYNTAX       INTEGER {
                        enable(1),
                        disable(2)
                    }
     MAX-ACCESS   read-only
     STATUS       current
     DESCRIPTION
     "When this administrative parameter is enabled, the controller runs ACA algorithm after it detects that a managed AP failed."
     DEFVAL    { disable }
     ::= {wsChannelPlanEntry  22 }

  wsChannelPlanManagedAPFailureInterval  OBJECT-TYPE
    SYNTAX     Integer32 (60..600)
    MAX-ACCESS  read-only
    STATUS      current
    DESCRIPTION
       "The number of seconds to wait before triggering the channel plan after a managed AP fails."
    DEFVAL     {300}
    ::= {wsChannelPlanEntry 21 }

 wsChannelPlanNumOfRadios  OBJECT-TYPE
     SYNTAX       Integer32
     MAX-ACCESS   read-only
     STATUS       current
     DESCRIPTION
         "Number of radios operating in the band.
          This includes the radios with static channel assignment."
     DEFVAL          { 0 }
     ::= {wsChannelPlanEntry  13 }

 wsChannelPlanNumOfRadiosAnalysed  OBJECT-TYPE
     SYNTAX       Integer32
     MAX-ACCESS   read-only
     STATUS       current
     DESCRIPTION
         "Indicates the number of AP radios analyzed by the channel algorithm.
          This includes APs that operate on static channels.This value is reset at
          the start of each channel plan cycle. "
     DEFVAL          { 0 }
     ::= {wsChannelPlanEntry  14 }

 wsChannelPlanNumOfRadiosScanned  OBJECT-TYPE
     SYNTAX       Integer32
     MAX-ACCESS   read-only
     STATUS       current
     DESCRIPTION
         "Indicates the number of AP radios for which a Channel Plan Request
          has been sent by the channel algorithm.This value is reset at
          the start of each channel plan cycle. "
     DEFVAL          { 0 }
     ::= {wsChannelPlanEntry  15 }

 wsChannelPlanNumOfRadiosChanged  OBJECT-TYPE
     SYNTAX       Integer32
     MAX-ACCESS   read-only
     STATUS       current
     DESCRIPTION
         "Indicates the number of AP radios whose operating channel changed.
          This includes APs whose channel is changed to the same channel as
          the original operating channel.This value is reset at
          the start of each channel plan cycle. "
     DEFVAL          { 0 }
     ::= {wsChannelPlanEntry  16 }

 wsChannelPlanNumOfRadiosChangedToOrigChannel  OBJECT-TYPE
     SYNTAX       Integer32
     MAX-ACCESS   read-only
     STATUS       current
     DESCRIPTION
         "Indicates the number of AP radios that scanned the candidate channels but
          ended on the same channel.This value is reset at
          the start of each channel plan cycle. "
     DEFVAL          { 0 }
     ::= {wsChannelPlanEntry  17 }

 wsChannelPlanEstimatedTimeOfCompletion   OBJECT-TYPE
    SYNTAX     DisplayString
    MAX-ACCESS  read-only
    STATUS      current
    DESCRIPTION
       "The time for the estimated time of completion of the current channel plan cycle.
        When the channel plan is inactive the time stamp is zeroed out."
    ::= { wsChannelPlanEntry 18 }

 wsChannelPlanPercentageComplete  OBJECT-TYPE
     SYNTAX       Integer32
     MAX-ACCESS   read-only
     STATUS       current
     DESCRIPTION
         "During the channel plan cycle this parameter is the percentage of the
         AP radios that have been analyzed. When the channel plan is inactive this value is 0."
     DEFVAL          { 0 }
     ::= {wsChannelPlanEntry  19 }

--
--   wsChannelPlanHistoryTable
--
  wsChannelPlanHistoryTable OBJECT-TYPE
     SYNTAX       SEQUENCE OF WsChannelPlanHistoryEntry
     MAX-ACCESS   not-accessible
     STATUS       obsolete
     DESCRIPTION
         "This table contains parameters related to
          channel plan algorithm history, each entry
          indicates a previously computed and applied
          channel adjustment for the specified iteration.
          The maximum number of channel adjustment
          iterations displayed is based on the 802.11b/g or 802.11a
          channel plan history depth."
     ::= { rfManagement 2 }

    wsChannelPlanHistoryEntry OBJECT-TYPE
     SYNTAX       WsChannelPlanHistoryEntry
     MAX-ACCESS   not-accessible
     STATUS       obsolete
     DESCRIPTION
         "Each entry in this table represents channel
          plan history for WS managed AP radio."
     INDEX    { wsChannelPlanHistory,
                wsChannelPlanAPMacAddress, wsChannelPlanAPRadioInterface }
     ::= { wsChannelPlanHistoryTable 1 }

 WsChannelPlanHistoryEntry ::=
     SEQUENCE {
      wsChannelPlanHistory                INTEGER,
      wsChannelPlanAPMacAddress           MacAddress,
      wsChannelPlanAPRadioInterface       Integer32,
      wsChannelPlanAPLocation             DisplayString,
      wsChannelPlanAPHistoryIteration     Integer32,
      wsChannelPlanAPChannel              Integer32
 }

 wsChannelPlanHistory  OBJECT-TYPE
     SYNTAX       INTEGER {
                   ieee802dot11an(1),
                   ieee802dot11bORgn(2)
                  }
     MAX-ACCESS   not-accessible
     STATUS       obsolete
     DESCRIPTION
        "This object indicates the whether the channel adjustment
          is for 2.4Ghz or 5Ghz band."
     ::= {wsChannelPlanHistoryEntry  1 }

 wsChannelPlanAPMacAddress  OBJECT-TYPE
     SYNTAX       MacAddress
     MAX-ACCESS   not-accessible
     STATUS       obsolete
     DESCRIPTION
        "The Ethernet address of the AP."
     ::= {wsChannelPlanHistoryEntry  2 }

 wsChannelPlanAPRadioInterface  OBJECT-TYPE
     SYNTAX       Integer32(1..2)
     MAX-ACCESS   not-accessible
     STATUS       obsolete
     DESCRIPTION
         "Indicates the radio interface for channel assignment."
     ::= {wsChannelPlanHistoryEntry  3 }

 wsChannelPlanAPLocation OBJECT-TYPE
     SYNTAX       DisplayString(SIZE(0..32))
     MAX-ACCESS   read-only
     STATUS       obsolete
     DESCRIPTION
        "A descriptive name of the AP, usually represented by its location."
     ::= {wsChannelPlanHistoryEntry  4}

 wsChannelPlanAPHistoryIteration  OBJECT-TYPE
     SYNTAX       Integer32(1..10)
     MAX-ACCESS   read-only
     STATUS       obsolete
     DESCRIPTION
         "This field indicates the iteration of the channel
          plan algorithm for this channel adjustment,
          the maximum history depth is configurable.
          This history prevents the same APs from being
          changed time after time."
     ::= {wsChannelPlanHistoryEntry  5 }

 wsChannelPlanAPChannel  OBJECT-TYPE
     SYNTAX       Integer32(1|6|11)
     MAX-ACCESS   read-only
     STATUS       obsolete
     DESCRIPTION
         "Indicates the previously applied channel for this
          radio."
     ::= {wsChannelPlanHistoryEntry  6 }

--
--   wsChannelPlanManualProposedAdjustmentTable
--
  wsChannelPlanManualProposedAdjustmentTable OBJECT-TYPE
     SYNTAX       SEQUENCE OF WsChannelPlanManualProposedAdjustmentEntry
     MAX-ACCESS   not-accessible
     STATUS       obsolete
     DESCRIPTION
         "This table contains parameters related to
          proposed channel plan adjustment. These parameters
          are applicable only when channel plan mode
          is manual."
     ::= { rfManagement 3 }

    wsChannelPlanManualProposedAdjustmentEntry OBJECT-TYPE
     SYNTAX       WsChannelPlanManualProposedAdjustmentEntry
     MAX-ACCESS   not-accessible
     STATUS       obsolete
     DESCRIPTION
         "Each entry in this table represents proposed
          channel plan adjustment."
     INDEX    { wsChannelPlanManual, wsChannelPlanManualMacAddress,
                wsChannelPlanManualAPRadioInterface }
     ::= { wsChannelPlanManualProposedAdjustmentTable 1 }

 WsChannelPlanManualProposedAdjustmentEntry ::=
     SEQUENCE {
      wsChannelPlanManual                     INTEGER,
      wsChannelPlanManualMacAddress           MacAddress,
      wsChannelPlanManualAPRadioInterface     Integer32,
      wsChannelPlanManualCurrentChannel       Integer32,
      wsChannelPlanManualNewChannel           Integer32
 }

 wsChannelPlanManual  OBJECT-TYPE
     SYNTAX       INTEGER {
                   ieee802dot11an(1),
                   ieee802dot11bORgn(2)
                  }
     MAX-ACCESS   not-accessible
     STATUS       obsolete
     DESCRIPTION
        "This object indicates the whether the channel plan
          is for 2.4Ghz or 5Ghz band."
     ::= {wsChannelPlanManualProposedAdjustmentEntry  1 }

 wsChannelPlanManualMacAddress  OBJECT-TYPE
     SYNTAX       MacAddress
     MAX-ACCESS   not-accessible
     STATUS       obsolete
     DESCRIPTION
        "The Ethernet address of the AP."
     ::= {wsChannelPlanManualProposedAdjustmentEntry  2 }

 wsChannelPlanManualAPRadioInterface  OBJECT-TYPE
     SYNTAX       Integer32(1..2)
     MAX-ACCESS   not-accessible
     STATUS       obsolete
     DESCRIPTION
         "Indicates the radio interface for channel assignment."
     ::= {wsChannelPlanManualProposedAdjustmentEntry  3 }

 wsChannelPlanManualCurrentChannel  OBJECT-TYPE
     SYNTAX       Integer32(1..13|36|40|44|48|52|56|60|64)
     MAX-ACCESS   read-only
     STATUS       obsolete
     DESCRIPTION
         "Indicates the current operating channel for this
          radio."
     ::= {wsChannelPlanManualProposedAdjustmentEntry  4 }

 wsChannelPlanManualNewChannel  OBJECT-TYPE
     SYNTAX       Integer32(1..13|36|40|44|48|52|56|60|64)
     MAX-ACCESS   read-only
     STATUS       obsolete
     DESCRIPTION
         "Indicates new channel assignment for this
          radio."
     ::= {wsChannelPlanManualProposedAdjustmentEntry  5 }

 wsPowerAdjustmentMode    OBJECT-TYPE
    SYNTAX     INTEGER {
                   manual(1),
                   interval(2)
               }
    MAX-ACCESS  read-only
    STATUS      current
    DESCRIPTION
       "Flag to set automatic power adjustment for
        all managed AP radios. If power adjustment mode is interval,
        periodically calculate the power adjustments and apply them.
        However, if power adjustment is manual, calculation and
        assignment of power adjustments initiated and controlled by
        the administrator user interface commands."
    DEFVAL      { manual }
    ::= { rfManagement 4 }

 wsPowerAdjustmentStrength    OBJECT-TYPE
    SYNTAX     Integer32 (-99..-1)
    MAX-ACCESS  read-only
    STATUS      current
    DESCRIPTION
      "Power Plan signal strength threshold in dBm."
    DEFVAL      { -85 }
    ::= { rfManagement 5 }

 wsPowerManualProposedAdjustmentAction    OBJECT-TYPE
    SYNTAX      INTEGER {
                       none(1),
                       start(2),
                       apply(3),
                       clear(4)
                     }
    MAX-ACCESS  read-only
    STATUS      current
    DESCRIPTION
       "This action object is used to:
             - Run the Proposed Power Adjustment alogorithm
             - Apply the same to network.
             - Clear the calculated power plan.
        Read on this object will always return none."
   ::= { rfManagement 6 }

 wsManualPowerAdjustmentStatus    OBJECT-TYPE
    SYNTAX      INTEGER {
                       none(1),
                       algorithm-in-progress(2),
                       algorithm-complete(3),
                       apply-in-process(4),
                       apply-complete(5)
                     }
    MAX-ACCESS  read-only
    STATUS      obsolete
    DESCRIPTION
      "Indicates the current state of a manual request
       to compute or apply proposed power adjustments."
    ::= { rfManagement 7 }

--
--   wsPowerManualProposedAdjustmentTable
--
 wsPowerManualProposedAdjustmentTable OBJECT-TYPE
     SYNTAX       SEQUENCE OF WsPowerManualProposedAdjustmentEntry
     MAX-ACCESS   not-accessible
     STATUS       obsolete
     DESCRIPTION
        "This table represents the proposed power adjustment
         status parameters. These parameters are displayed
         only when power adjustment mode is set to manual.
         The administrator manually apply all of the proposed
         power adjustments displayed."
     ::= { rfManagement 8 }

    wsPowerManualProposedAdjustmentEntry OBJECT-TYPE
     SYNTAX       WsPowerManualProposedAdjustmentEntry
     MAX-ACCESS   not-accessible
     STATUS       obsolete
     DESCRIPTION
        "Each entry in this table represents the proposed
         power adjustment status parameters."
     INDEX    { wsPowerManualProposedAdjustmentAPMacAddress,
                wsPowerManualProposedAdjustmentAPRadioInterface }
     ::= { wsPowerManualProposedAdjustmentTable 1 }

 WsPowerManualProposedAdjustmentEntry ::=
     SEQUENCE {
      wsPowerManualProposedAdjustmentAPMacAddress                 MacAddress,
      wsPowerManualProposedAdjustmentAPRadioInterface             Integer32,
      wsPowerManualProposedAdjustmentAPCurrentTxPower             Integer32,
      wsPowerManualProposedAdjustmentAPNewTxPower                 Integer32
 }

 wsPowerManualProposedAdjustmentAPMacAddress  OBJECT-TYPE
     SYNTAX       MacAddress
     MAX-ACCESS   not-accessible
     STATUS       obsolete
     DESCRIPTION
        "The Ethernet address of the AP."
     ::= {wsPowerManualProposedAdjustmentEntry  1 }

 wsPowerManualProposedAdjustmentAPRadioInterface  OBJECT-TYPE
     SYNTAX       Integer32(1..2)
     MAX-ACCESS   not-accessible
     STATUS       obsolete
     DESCRIPTION
        "Indicates the radio interface for power assignment."
     ::= {wsPowerManualProposedAdjustmentEntry  2 }

 wsPowerManualProposedAdjustmentAPCurrentTxPower  OBJECT-TYPE
     SYNTAX       Integer32(1..100)
     MAX-ACCESS   read-only
     STATUS       obsolete
     DESCRIPTION
        "Indicates the current operating power for this radio
         from the last power plan computation.
         Even after the new power plan is applied, this object displays the
         old value as opposed to the actual power currently set into the radio."
     ::= {wsPowerManualProposedAdjustmentEntry  3 }

 wsPowerManualProposedAdjustmentAPNewTxPower  OBJECT-TYPE
     SYNTAX       Integer32(1..100)
     MAX-ACCESS   read-only
     STATUS       obsolete
     DESCRIPTION
        "Indicates the new proposed power assignment for this
         radio."
     ::= {wsPowerManualProposedAdjustmentEntry  4 }
--
--   wsPowerPlanGlobalStatus
--
 wsPowerPlanOperatingStatus  OBJECT-TYPE
     SYNTAX       INTEGER {
                       inactive(0),
                       gatheringNbrData(1),
                       changingPower(2),
                       powerPlanComplete(3)
                  }
     MAX-ACCESS   read-only
     STATUS       current
     DESCRIPTION
         "The Operational Status of the Power Plan Algorithm. "
     DEFVAL { inactive }
     ::= {rfManagement  9 }

 wsPowerPlanAvgNumInterferingAPs  OBJECT-TYPE
     SYNTAX       Integer32(0..999)
     MAX-ACCESS   read-only
     STATUS       current
     DESCRIPTION
         "The average number of managed radios detected by every operational mode radio in the cluster."
     DEFVAL { 0 }
     ::= {rfManagement  10 }

 wsPowerPlanAvgNumInterferingVAPs  OBJECT-TYPE
     SYNTAX       Integer32(0..999)
     MAX-ACCESS   read-only
     STATUS       current
     DESCRIPTION
         "The average number of managed virtual APs detected by every operational mode radio in the cluster."
     DEFVAL { 0 }
     ::= {rfManagement  11 }

 wsPowerPlanAPNumOpRadios  OBJECT-TYPE
     SYNTAX       Integer32
     MAX-ACCESS   read-only
     STATUS       current
     DESCRIPTION
         "The number of operational mode radios in the cluster. The sentry and disabled radios are not counted."
     DEFVAL { 0 }
     ::= {rfManagement 12 }

 wsPowerPlanAPNumPwrCycles  OBJECT-TYPE
     SYNTAX       Integer32
     MAX-ACCESS   read-only
     STATUS       current
     DESCRIPTION
         "Number of power plan cycles executed by the controller."
     DEFVAL { 0 }
     ::= {rfManagement 13 }

 wsPowerPlanGlobalNumPwrChanges  OBJECT-TYPE
     SYNTAX       Integer32
     MAX-ACCESS   read-only
     STATUS       current
     DESCRIPTION
         "Number of transmit power changes done by the power plan algorithm for all radios in the cluster."
     DEFVAL { 0 }
     ::= {rfManagement 14 }

 wsPowerPlanGlobalNumPwrInc  OBJECT-TYPE
     SYNTAX       Integer32
     MAX-ACCESS   read-only
     STATUS       current
     DESCRIPTION
         "Number of transmit power increases done by the power plan algorithm for all radios in the cluster."
     DEFVAL { 0 }
     ::= {rfManagement  15 }

 wsPowerPlanGlobalNumPwrDec  OBJECT-TYPE
     SYNTAX       Integer32
     MAX-ACCESS   read-only
     STATUS       current
     DESCRIPTION
         "Number of transmit power reductions done by the power plan algorithm for all radios in the cluster."
     DEFVAL { 0 }
     ::= {rfManagement  16 }


 wsPowerPlanTimeSinceLastPowerPLan  OBJECT-TYPE
     SYNTAX       DisplayString
     MAX-ACCESS   read-only
     STATUS       current
     DESCRIPTION
         "Time since the last power plan was done. The power plan could have been triggered manually or automatically."
     DEFVAL {"Never"}
     ::= {rfManagement  17 }
--
--   wsChannelPlanPerRadioPerBandStatus
--
  wsChannelPlanPerRadioPerBandTable OBJECT-TYPE
     SYNTAX       SEQUENCE OF WsChannelPlanPerRadioPerBandEntry
     MAX-ACCESS   not-accessible
     STATUS       current
     DESCRIPTION
          "This table contains the per band per radio channel plan status for a Managed AP."
     ::= { rfManagement 18 }

    wsChannelPlanPerRadioPerBandEntry OBJECT-TYPE
     SYNTAX       WsChannelPlanPerRadioPerBandEntry
     MAX-ACCESS   not-accessible
     STATUS       current
     DESCRIPTION
         "Each entry in this table represents channel plan per band per radio status for WS managed AP."
     INDEX    { wsChannelPlanType,
                wsChannelPlanAPMacAddr, wsChannelPlanAPRadioIntf}
     ::= { wsChannelPlanPerRadioPerBandTable 1 }

 WsChannelPlanPerRadioPerBandEntry ::=
     SEQUENCE {
      wsChannelPlanType                                INTEGER,
      wsChannelPlanAPMacAddr                           MacAddress,
      wsChannelPlanAPRadioIntf                         Integer32,
      wsChannelPlanAPIsLocal                           INTEGER,
      wsChannelPlanAPCurrentChannel                    Integer32,
      wsChannelPlanAPOldChannel                        Integer32,
      wsChannelPlanAPStrongestOldSignal                DisplayString,
      wsChannelPlanAPStrongestNewSignal                DisplayString,
      wsChannelPlanAPChannelChangeInd                  INTEGER,
      wsChannelPlanAPReasonCode                        INTEGER,
      wsChannelPlanAPStrongestOldManagedAPandSignal    DisplayString,
      wsChannelPlanAPStrongestNewManagedAPandSignal    DisplayString,
      wsChannelPlanAPStrongestOldUnmanagedAPandSignal  DisplayString,
      wsChannelPlanAPStrongestNewUnmanagedAPandSignal  DisplayString,
      wsChannelPlanAPTimeSinceLastChannelChange        DisplayString,
      wsChannelPlanAPLastChanScanDuration              Integer32
 }

 wsChannelPlanType  OBJECT-TYPE
     SYNTAX       INTEGER {
                   ieee802dot11an(1),
                   ieee802dot11bORgn(2)
                  }
     MAX-ACCESS   not-accessible
     STATUS       current
     DESCRIPTION
        "This object indicates the whether the channel plan
          is for ieee802dot11bORgn or ieee802dot11an."
     ::= {wsChannelPlanPerRadioPerBandEntry  1 }

 wsChannelPlanAPMacAddr  OBJECT-TYPE
     SYNTAX       MacAddress
     MAX-ACCESS   not-accessible
     STATUS       current
     DESCRIPTION
        "The Ethernet address of the Managed AP."
     ::= {wsChannelPlanPerRadioPerBandEntry  2 }

 wsChannelPlanAPRadioIntf  OBJECT-TYPE
     SYNTAX       Integer32(1..2)
     MAX-ACCESS   not-accessible
     STATUS       current
     DESCRIPTION
         "Indicates the radio interface for channel assignment."
     ::= {wsChannelPlanPerRadioPerBandEntry  3 }

 wsChannelPlanAPIsLocal OBJECT-TYPE
     SYNTAX       INTEGER {
                   peerSwitch(0),
                   local(1)
                  }
     MAX-ACCESS   read-only
     STATUS       current
     DESCRIPTION
        "Flag Indicating whether the AP is managed by the cluster controller or a peer controller."
     ::= {wsChannelPlanPerRadioPerBandEntry  4}

 wsChannelPlanAPCurrentChannel  OBJECT-TYPE
     SYNTAX       Integer32
     MAX-ACCESS   read-only
     STATUS       current
     DESCRIPTION
         "Indicates the current operating channel for this
          radio."
     ::= {wsChannelPlanPerRadioPerBandEntry  5 }

 wsChannelPlanAPOldChannel  OBJECT-TYPE
     SYNTAX       Integer32
     MAX-ACCESS   read-only
     STATUS       current
     DESCRIPTION
         "Channel on which this radio was operating before the channel change algorithm changed its channel."
     DEFVAL { 0 }
     ::= {wsChannelPlanPerRadioPerBandEntry  6 }

 wsChannelPlanAPStrongestOldSignal  OBJECT-TYPE
     SYNTAX       DisplayString
     MAX-ACCESS   read-only
     STATUS       current
     DESCRIPTION
         "The strongest signal detected on the old channel. This is the signal used in the channel selection decision."
     DEFVAL { "N/A" }
     ::= {wsChannelPlanPerRadioPerBandEntry  7 }

 wsChannelPlanAPStrongestNewSignal  OBJECT-TYPE
     SYNTAX       DisplayString
     MAX-ACCESS   read-only
     STATUS       current
     DESCRIPTION
         "The strongest signal detected on the new channel during the channel validation scan.
          This is the signal used in the channel selection decision. If the algorithm does not
          change the channel then this is the signal on the current channel detected during the
          channel check scan."
     DEFVAL { "N/A" }
     ::= {wsChannelPlanPerRadioPerBandEntry  8 }

 wsChannelPlanAPChannelChangeInd  OBJECT-TYPE
     SYNTAX       INTEGER {
                    no(0),
                    yes(1),
                    wait(2)
                  }
     MAX-ACCESS   read-only
     STATUS       current
     DESCRIPTION
         "Flag indicating whether the last channel plan cycle changed the channel for this radio."
     DEFVAL { no }
     ::= {wsChannelPlanPerRadioPerBandEntry  9 }

 wsChannelPlanAPReasonCode  OBJECT-TYPE
     SYNTAX       INTEGER {
                    chanPlanNeverExecuted(0),
                    channelIsStatic(1),
                    oneEligibleChannel(2),
                    detectedAPSignalBelowThresh(3),
                    chanFoundWithLowInterference(4),
                    chanNotFoundWithLowInterference(5),
                    partOfWDSLink(6)
                  }
     MAX-ACCESS   read-only
     STATUS       current
     DESCRIPTION
         "The reason code indicating why the channel was changed or not changed for this radio."
     DEFVAL { chanPlanNeverExecuted }
     ::= {wsChannelPlanPerRadioPerBandEntry  10 }

 wsChannelPlanAPStrongestOldManagedAPandSignal  OBJECT-TYPE
     SYNTAX       DisplayString
     MAX-ACCESS   read-only
     STATUS       current
     DESCRIPTION
         "The MAC address and the signal strength of the strongest managed neighbor AP detected on the channel
           before that channel was changed. The MAC address is the base MAC of the managed AP."
     DEFVAL { "N/A" }
     ::= {wsChannelPlanPerRadioPerBandEntry  11 }

 wsChannelPlanAPStrongestNewManagedAPandSignal  OBJECT-TYPE
     SYNTAX       DisplayString
     MAX-ACCESS   read-only
     STATUS       current
     DESCRIPTION
         "The MAC address and the signal strength of the strongest managed neighbor AP detected on the current
          operating channel. The MAC address is the base MAC of the managed AP."
     DEFVAL { "N/A" }
     ::= {wsChannelPlanPerRadioPerBandEntry  12 }

 wsChannelPlanAPStrongestOldUnmanagedAPandSignal  OBJECT-TYPE
     SYNTAX       DisplayString
     MAX-ACCESS   read-only
     STATUS       current
     DESCRIPTION
         "The MAC address and the signal strength of the strongest unmanaged neighbor AP detected on the channel
           before that channel was changed."
     DEFVAL { "N/A" }
     ::= {wsChannelPlanPerRadioPerBandEntry  13 }

 wsChannelPlanAPStrongestNewUnmanagedAPandSignal  OBJECT-TYPE
     SYNTAX       DisplayString
     MAX-ACCESS   read-only
     STATUS       current
     DESCRIPTION
         "The MAC address and the signal strength of the strongest unmanaged neighbor AP detected on the current
          operating channel."
     DEFVAL { "N/A" }
     ::= {wsChannelPlanPerRadioPerBandEntry  14 }

 wsChannelPlanAPTimeSinceLastChannelChange   OBJECT-TYPE
    SYNTAX     DisplayString
    MAX-ACCESS  read-only
    STATUS      current
    DESCRIPTION
       "The UTC time since the channel was last changed by the channel plan algorithm.."
    ::= { wsChannelPlanPerRadioPerBandEntry 15 }

 wsChannelPlanAPLastChanScanDuration  OBJECT-TYPE
     SYNTAX       Integer32(0..999999)
     MAX-ACCESS   read-only
     STATUS       current
     DESCRIPTION
         "Number of milliseconds that the AP spent scanning channels during the last channel plan cycle.
          The scan time includes the operational channel scan, so the time may be non-zero even when the radio
          did not change channels."
     DEFVAL { 0 }
     ::= {wsChannelPlanPerRadioPerBandEntry  16 }

--
--   wsPowerPlanPerRadioStatus
--
  wsPowerPlanPerRadioTable OBJECT-TYPE
     SYNTAX       SEQUENCE OF WsPowerPlanPerRadioEntry
     MAX-ACCESS   not-accessible
     STATUS       current
     DESCRIPTION
         "This table contains the per radio Power Plan Status for a Managed AP ."
     ::= { rfManagement 19 }

    wsPowerPlanPerRadioEntry OBJECT-TYPE
     SYNTAX       WsPowerPlanPerRadioEntry
     MAX-ACCESS   not-accessible
     STATUS       current
     DESCRIPTION
         "Each entry in this table represents the per radio power plan status for WS managed AP."
     INDEX    {wsPowerPlanAPMacAddress, wsPowerPlanAPRadioInterface}
     ::= { wsPowerPlanPerRadioTable 1 }

 WsPowerPlanPerRadioEntry ::=
     SEQUENCE {
      wsPowerPlanAPMacAddress                        MacAddress,
      wsPowerPlanAPRadioInterface                    Integer32,
      wsPowerPlanAPIsLocal                           INTEGER,
      wsPowerPlanAPChannel                           DisplayString,
      wsPowerPlanAPTxPower                           Integer32,
      wsPowerPlanAPNumInterferingAPs                 Integer32,
      wsPowerPlanAPNumInterferingVAPs                Integer32,
      wsPowerPlanAPStrongestDetectorAP               MacAddress,
      wsPowerPlanAPStrongestDetectorRadio            Integer32,
      wsPowerPlanAPStrongestDetectorSignal           DisplayString,
      wsPowerPlanAPStrongestDetectedNeighbor         MacAddress,
      wsPowerPlanAPStrongestDetectedSignal           DisplayString,
      wsPowerPlanAPLastPwrAdjStatus                  INTEGER,
      wsPowerPlanAPLastPwrAdjReasonCode              INTEGER,
      wsPowerPlanAPNumPwrChanges                     Integer32,
      wsPowerPlanAPNumPwrInc                         Integer32,
      wsPowerPlanAPNumPwrDec                         Integer32
 }

 wsPowerPlanAPMacAddress  OBJECT-TYPE
     SYNTAX       MacAddress
     MAX-ACCESS   not-accessible
     STATUS       current
     DESCRIPTION
        "The Ethernet address of the Managed AP."
     ::= {wsPowerPlanPerRadioEntry  1 }

 wsPowerPlanAPRadioInterface  OBJECT-TYPE
     SYNTAX       Integer32(1..2)
     MAX-ACCESS   not-accessible
     STATUS       current
     DESCRIPTION
         "Indicates the radio interface of the Managed AP."
     ::= {wsPowerPlanPerRadioEntry  2 }

 wsPowerPlanAPIsLocal OBJECT-TYPE
     SYNTAX       INTEGER {
                   peerSwitch(0),
                   local(1)
                  }
     MAX-ACCESS   read-only
     STATUS       current
     DESCRIPTION
        "Flag Indicating whether the AP is managed by the cluster controller or a peer controller."
     ::= {wsPowerPlanPerRadioEntry  3}

 wsPowerPlanAPChannel  OBJECT-TYPE
     SYNTAX       DisplayString
     MAX-ACCESS   read-only
     STATUS       current
     DESCRIPTION
         "Channel on which the radio is operating. For sentry radios this field is set to sentry.
          The disabled radios report None."
     DEFVAL {"None"}
     ::= {wsPowerPlanPerRadioEntry  4 }

 wsPowerPlanAPTxPower  OBJECT-TYPE
     SYNTAX       Integer32(0..100)
     MAX-ACCESS   read-only
     STATUS       current
     DESCRIPTION
         "The current operating power for this radio. Sentry radios and disabled radios report 0%."
     DEFVAL { 0 }
     ::= {wsPowerPlanPerRadioEntry  5 }

 wsPowerPlanAPNumInterferingAPs  OBJECT-TYPE
     SYNTAX       Integer32(0..999)
     MAX-ACCESS   read-only
     STATUS       current
     DESCRIPTION
         "The number of APs managed by this cluster detected by this radio on the operational channel."
     DEFVAL { 0 }
     ::= {wsPowerPlanPerRadioEntry  6 }

 wsPowerPlanAPNumInterferingVAPs  OBJECT-TYPE
     SYNTAX       Integer32(0..999)
     MAX-ACCESS   read-only
     STATUS       current
     DESCRIPTION
         "The number of VAPs managed by this cluster detected by this radio on the operational channel."
     DEFVAL { 0 }
     ::= {wsPowerPlanPerRadioEntry  7 }

 wsPowerPlanAPStrongestDetectorAP  OBJECT-TYPE
     SYNTAX       MacAddress
     MAX-ACCESS   read-only
     STATUS       current
     DESCRIPTION
         "The base MAC address of the managed AP that detects this radio with the strongest signal."
     ::= {wsPowerPlanPerRadioEntry  8 }

 wsPowerPlanAPStrongestDetectorRadio  OBJECT-TYPE
     SYNTAX       Integer32
     MAX-ACCESS   read-only
     STATUS       current
     DESCRIPTION
         "The radio number of the managed AP that detects this radio with the strongest signal."
     DEFVAL {0}
     ::= {wsPowerPlanPerRadioEntry  9 }

 wsPowerPlanAPStrongestDetectorSignal  OBJECT-TYPE
     SYNTAX       DisplayString
     MAX-ACCESS   read-only
     STATUS       current
     DESCRIPTION
         "The strongest signal strength in dBm with which a managed neighbor detects this radio."
     DEFVAL { "None" }
     ::= {wsPowerPlanPerRadioEntry  10 }

 wsPowerPlanAPStrongestDetectedNeighbor  OBJECT-TYPE
     SYNTAX       MacAddress
     MAX-ACCESS   read-only
     STATUS       current
     DESCRIPTION
         "The MAC address of the AP that this radio detects with the strongest signal."
     ::= {wsPowerPlanPerRadioEntry  11 }

 wsPowerPlanAPStrongestDetectedSignal  OBJECT-TYPE
     SYNTAX       DisplayString
     MAX-ACCESS   read-only
     STATUS       current
     DESCRIPTION
         "The signal strength with which this radio detects the strongest neighbor."
     DEFVAL { "None" }
     ::= {wsPowerPlanPerRadioEntry  12 }

 wsPowerPlanAPLastPwrAdjStatus  OBJECT-TYPE
     SYNTAX       INTEGER {
                      unchanged(0),
                      increased(1),
                      reduced(2)
                  }
     MAX-ACCESS   read-only
     STATUS       current
     DESCRIPTION
         "The status indicating whether the power was changed during the most recent cycle of the power adjustment algorithm."
     DEFVAL { unchanged }
     ::= {wsPowerPlanPerRadioEntry  13 }

 wsPowerPlanAPLastPwrAdjReasonCode  OBJECT-TYPE
     SYNTAX       INTEGER {
                      powerPlanNeverExecuted(0),
                      powerPlanRadioInSentryMode(1),
                      powerPlanRadioAutoPowerDisable(2),
                      powerPlanRadioPowerUnchanged(3),
                      powerPlanRadioOperatingInMaxPower(4),
                      powerPlanRadioOperatingInMinPower(5),
                      powerPlanRadioMinPowerIs100(6),
                      powerPlanRadioPowerIncreaseRequired(7),
                      powerPlanRadioPowerDecreaseRequired(8),
                      powerPlanRadioPowerAdjNone(9),
                      powerPlanRadioPowerPartOfWDSLink(10)
                  }
     MAX-ACCESS   read-only
     STATUS       current
     DESCRIPTION
         "The reason code indicating why the last power adjustment action was taken or not taken."
     ::= {wsPowerPlanPerRadioEntry  14 }

 wsPowerPlanAPNumPwrChanges  OBJECT-TYPE
     SYNTAX       Integer32
     MAX-ACCESS   read-only
     STATUS       current
     DESCRIPTION
         "Number of transmit power changes done by the power plan algorithm for this radio."
     DEFVAL { 0 }
     ::= {wsPowerPlanPerRadioEntry  15 }

 wsPowerPlanAPNumPwrInc  OBJECT-TYPE
     SYNTAX       Integer32
     MAX-ACCESS   read-only
     STATUS       current
     DESCRIPTION
         "Number of transmit power increases done by the power plan algorithm for this radio."
     DEFVAL { 0 }
     ::= {wsPowerPlanPerRadioEntry  16 }

 wsPowerPlanAPNumPwrDec  OBJECT-TYPE
     SYNTAX       Integer32
     MAX-ACCESS   read-only
     STATUS       current
     DESCRIPTION
         "Number of transmit power reductions done by the power plan algorithm for this radio."
     DEFVAL { 0 }
     ::= {wsPowerPlanPerRadioEntry  17 }

--
--   wsPowerPlanPerProfileStatus
--
  wsPowerPlanPerProfileTable OBJECT-TYPE
     SYNTAX       SEQUENCE OF WsPowerPlanPerProfileEntry
     MAX-ACCESS   not-accessible
     STATUS       current
     DESCRIPTION
         "This table contains the per profile power plan status."
     ::= { rfManagement 20 }

    wsPowerPlanPerProfileEntry OBJECT-TYPE
     SYNTAX       WsPowerPlanPerProfileEntry
     MAX-ACCESS   not-accessible
     STATUS       current
     DESCRIPTION
         "Each entry in this table represents the per profile power plan status."
     INDEX    { wsPowerPlanProfileId }
     ::= { wsPowerPlanPerProfileTable 1 }

 WsPowerPlanPerProfileEntry ::=
     SEQUENCE {
      wsPowerPlanProfileId                           Integer32,
      wsPowerPlanPerProfileAvgNumInterferingAPs         Integer32,
      wsPowerPlanPerProfileAvgNumInterferingVAPs        Integer32,
      wsPowerPlanNumPwrChanges                       Integer32,
      wsPowerPlanNumPwrInc                           Integer32,
      wsPowerPlanNumPwrDec                           Integer32
 }

 wsPowerPlanProfileId  OBJECT-TYPE
     SYNTAX       Integer32(0..999)
     MAX-ACCESS   not-accessible
     STATUS       current
     DESCRIPTION
         "Indicates the profile Id."
     ::= {wsPowerPlanPerProfileEntry  1 }

 wsPowerPlanPerProfileAvgNumInterferingAPs  OBJECT-TYPE
     SYNTAX       Integer32(0..999)
     MAX-ACCESS   read-only
     STATUS       current
     DESCRIPTION
         "The average number of managed radios detected by every operational mode radio that uses this profile.
          If the number of APs is greater than 999 then it is reported as 999.."
     DEFVAL { 0 }
     ::= {wsPowerPlanPerProfileEntry  2 }

 wsPowerPlanPerProfileAvgNumInterferingVAPs  OBJECT-TYPE
     SYNTAX       Integer32(0..999)
     MAX-ACCESS   read-only
     STATUS       current
     DESCRIPTION
         "The average number of managed virtual APs detected by every operational mode radio that uses this profile."
     DEFVAL { 0 }
     ::= {wsPowerPlanPerProfileEntry  3 }

 wsPowerPlanNumPwrChanges  OBJECT-TYPE
     SYNTAX       Integer32
     MAX-ACCESS   read-only
     STATUS       current
     DESCRIPTION
         "Number of transmit power changes done by the power plan algorithm for all radios in this profile."
     DEFVAL { 0 }
     ::= {wsPowerPlanPerProfileEntry  4 }

 wsPowerPlanNumPwrInc  OBJECT-TYPE
     SYNTAX       Integer32
     MAX-ACCESS   read-only
     STATUS       current
     DESCRIPTION
         "Number of transmit power increases done by the power plan algorithm for all radios in this profile."
     DEFVAL { 0 }
     ::= {wsPowerPlanPerProfileEntry  5 }

 wsPowerPlanNumPwrDec  OBJECT-TYPE
     SYNTAX       Integer32
     MAX-ACCESS   read-only
     STATUS       current
     DESCRIPTION
         "Number of transmit power reductions done by the power plan algorithm for all radios in this profile."
     DEFVAL { 0 }
     ::= {wsPowerPlanPerProfileEntry  6 }

--
--   wsNtwProvisioningGlobal
--
 wsNtwProvisoningAction  OBJECT-TYPE
        SYNTAX              INTEGER {
                              none(0),
                              start(1),
                              stop(2)
                            }
        MAX-ACCESS          read-write
        STATUS              current
        DESCRIPTION
            "This action object is used to:
             - start the network provision.
             - stop the network provision."
        DEFVAL              { none }
        ::= {rfManagement  21 }

 wsNtwProvisioningOperatingStatus  OBJECT-TYPE
     SYNTAX       INTEGER {
                       notstarted(0),
                       running(1),
                       finished(2),
                       aborted(3),
                       failed(4)
                  }
     MAX-ACCESS   read-only
     STATUS       current
     DESCRIPTION
         "The Operational Status of the Initial Network Provisioning Protocol."
     DEFVAL { notstarted }
     ::= {rfManagement  22 }

 wsNtwProvisioningTimeStamp OBJECT-TYPE
    SYNTAX      Integer32
    MAX-ACCESS  read-only
    STATUS      current
    DESCRIPTION
       "Number of seconds the latest invocation of the protocol has been running."
     DEFVAL { 0 }
     ::= {rfManagement  23 }

 wsNtwProvisioningChanBGCompletion  OBJECT-TYPE
     SYNTAX       Integer32(0..100)
     MAX-ACCESS   read-only
     STATUS       current
     DESCRIPTION
         "Percent complete for the channel protocol in the 2.4 GHz band."
     DEFVAL { 0 }
     ::= {rfManagement  24 }

 wsNtwProvisioningChanACompletion  OBJECT-TYPE
     SYNTAX       Integer32(0..100)
     MAX-ACCESS   read-only
     STATUS       current
     DESCRIPTION
         "Percent complete for the channel protocol in the 5GHz band."
     DEFVAL { 0 }
     ::= {rfManagement  25 }

wsNtwProvisioningPowerPlanCnt  OBJECT-TYPE
     SYNTAX       Integer32(0..5)
     MAX-ACCESS   read-only
     STATUS       current
     DESCRIPTION
         "Count-Down of how many power plan interations remain to be done."
     DEFVAL { 0 }
     ::= {rfManagement  26 }

--**************************************************************************************
-- managedAP
--**************************************************************************************
--
--   wsManagedAPStatusTable
--
 wsManagedAPStatusTable OBJECT-TYPE
     SYNTAX       SEQUENCE OF WsManagedAPStatusEntry
     MAX-ACCESS   not-accessible
     STATUS       current
     DESCRIPTION
           "This table contains status parameters for all APs managed by the controller."
     ::= { managedAP 1 }

    wsManagedAPStatusEntry OBJECT-TYPE
     SYNTAX       WsManagedAPStatusEntry
     MAX-ACCESS   not-accessible
     STATUS       current
     DESCRIPTION
          "Each entry in this table contains status parameters for
           an AP managed by the controller. Controller can managed up to
           48 APs at a time, with the actual maximum number
           supported dependent on the CPU performance of the
           controller and may be smaller or larger for some implementations."
     INDEX    { wsManagedAPMacAddress }
     ::= { wsManagedAPStatusTable 1 }

 WsManagedAPStatusEntry ::=
     SEQUENCE {
      wsManagedAPMacAddress           MacAddress,
      wsManagedAPIpAddress            IpAddress,
      wsManagedAPVendorId             Integer32,
      wsManagedAPSoftwareVersion      DisplayString,
      wsManagedAPHWType               Integer32,
      wsManagedAPSerialNumber         DisplayString,
      wsManagedAPPartNumber           DisplayString,
      wsManagedAPDiscoveryReason      INTEGER,
      wsManagedAPStatus               INTEGER,
      wsManagedAPAuthenticatedClients Unsigned32,
      wsManagedAPSysUpTime            TimeTicks,
      wsManagedAPProfileId            Integer32,
      wsManagedAPProfileName          DisplayString,
      wsManagedAPProtocolVersion      Integer32,
      wsManagedAPCodeDownloadStatus   INTEGER,
      wsManagedAPLocation             DisplayString,
      wsManagedAPLastFailingConfigElement Integer32,
      wsManagedAPConfigFailureErrMsg   DisplayString,
      wsManagedAPReset                 INTEGER,
      wsManagedAPResetStatus           INTEGER,
      wsManagedAPFailedEntryPurge      INTEGER,
      wsManagedAPDebugPassword         DisplayString,
      wsManagedAPDebugMode             INTEGER,
      wsManagedAPDebugStatus           INTEGER,
      wsManagedAPAge                   TimeTicks,
      wsManagedAPManagingSwitch        INTEGER,
      wsManagedAPSwitchMacAddress      MacAddress,
      wsManagedAPSwitchIpAddress       IpAddress,
      wsManagedAPIpMask                IpAddress,
      wsManagedAPDistTunnelHomeAPClients       Unsigned32,
      wsManagedAPDistTunnelAssocAPClients      Unsigned32,
      wsManagedAPDistTunnelsTotal              Unsigned32,
      wsManagedAPDistTunnelsMaxMcastRepl       Unsigned32,
      wsManagedAPDistTunnelsMaxVlanMcastRepl   Unsigned32

 }

 wsManagedAPMacAddress OBJECT-TYPE
     SYNTAX       MacAddress
     MAX-ACCESS   read-only
     STATUS       current
     DESCRIPTION
        "Ethernet address of the WS managed AP."
     ::= { wsManagedAPStatusEntry 1 }

 wsManagedAPIpAddress OBJECT-TYPE
     SYNTAX       IpAddress
     MAX-ACCESS   read-only
     STATUS       current
     DESCRIPTION
        "Network IP address of the managed AP."
     ::= { wsManagedAPStatusEntry 2 }

 wsManagedAPVendorId OBJECT-TYPE
     SYNTAX       Integer32(0..65535)
     MAX-ACCESS   not-accessible
     STATUS       current
     DESCRIPTION
        "Indicates vendor of the WS managed AP software. Broadcom vendor ID
         is 1."
     ::= { wsManagedAPStatusEntry 3 }

 wsManagedAPSoftwareVersion OBJECT-TYPE
     SYNTAX       DisplayString(SIZE(0..32))
     MAX-ACCESS   read-only
     STATUS       current
     DESCRIPTION
        "Indicates software version of the WS managed AP."
     ::= { wsManagedAPStatusEntry 4 }

 wsManagedAPHWType OBJECT-TYPE
     SYNTAX       Integer32
     MAX-ACCESS   not-accessible
     STATUS       current
     DESCRIPTION
        "Indicates hardware platform of the WS managed AP."
     ::= { wsManagedAPStatusEntry 5 }

 wsManagedAPSerialNumber OBJECT-TYPE
     SYNTAX       DisplayString(SIZE(0..32))
     MAX-ACCESS   not-accessible
     STATUS       current
     DESCRIPTION
        "Indicates serial number of the WS managed AP."
     ::= { wsManagedAPStatusEntry 6 }

 wsManagedAPPartNumber OBJECT-TYPE
     SYNTAX       DisplayString(SIZE(0..32))
     MAX-ACCESS   not-accessible
     STATUS       current
     DESCRIPTION
        "Indicates hardware part number of the WS managed AP."
     ::= { wsManagedAPStatusEntry 7 }

 wsManagedAPDiscoveryReason OBJECT-TYPE
     SYNTAX       INTEGER {
                     ip-poll(1),
                     peer-switch-initiated(2),
                     switch-ip-configured-in-ap(3),
                     switch-ip-obtained-via-dhcp(4),
                     l2Discovery(5)
                 }
     MAX-ACCESS   read-only
     STATUS       current
     DESCRIPTION
        "Indicates discovery method used to detect the AP."
     ::= { wsManagedAPStatusEntry 8 }

 wsManagedAPStatus OBJECT-TYPE
     SYNTAX       INTEGER {
                     discovered(1),
                     authenticated(2),
                     upgrading(3),
                     managed(4),
                     connection-failed(5),
                     deleted(6)
                  }
     MAX-ACCESS   read-only
     STATUS       current
     DESCRIPTION
        "Indicates current state of an AP."
     ::= { wsManagedAPStatusEntry 9 }

 wsManagedAPAuthenticatedClients OBJECT-TYPE
     SYNTAX       Unsigned32
     MAX-ACCESS   read-only
     STATUS       current
     DESCRIPTION
        "Indicates total number of clients currently authenticated to
         an AP."
     ::= { wsManagedAPStatusEntry 10 }

 wsManagedAPSysUpTime OBJECT-TYPE
     SYNTAX       TimeTicks
     MAX-ACCESS   read-only
     STATUS       current
     DESCRIPTION
        "Indicates time in seconds since last power-on reset."
     ::= { wsManagedAPStatusEntry 11 }

 wsManagedAPProfileId OBJECT-TYPE
     SYNTAX       Integer32(0..16)
     MAX-ACCESS   read-only
     STATUS       current
     DESCRIPTION
         "The configuration profile currently applied
          to the AP."
     ::= { wsManagedAPStatusEntry 12 }

 wsManagedAPProfileName OBJECT-TYPE
     SYNTAX       DisplayString(SIZE(0..32))
     MAX-ACCESS   read-only
     STATUS       current
     DESCRIPTION
         "The descriptive name for the profile currently
          applied to the AP."
     ::= { wsManagedAPStatusEntry 13 }

 wsManagedAPProtocolVersion OBJECT-TYPE
     SYNTAX       Integer32(0..65535)
     MAX-ACCESS   read-only
     STATUS       current
     DESCRIPTION
         "Indicates the protocol version supported
          by the software on the AP."
     ::= { wsManagedAPStatusEntry 14 }

 wsManagedAPCodeDownloadStatus OBJECT-TYPE
     SYNTAX       INTEGER {
                    not-started(1),
                    requested(2),
                    code-transfer-in-progress(3),
                    waiting-for-aps-to-download(4),
                    aborted(5),
                    nvram-update-in-progress(6),
                    timed-out(7),
                    failure(8)
                  }
     MAX-ACCESS   read-only
     STATUS       current
     DESCRIPTION
         "This indicates the current status of a code
          download request for this AP."
     ::= { wsManagedAPStatusEntry 15 }

 wsManagedAPLocation OBJECT-TYPE
     SYNTAX       DisplayString(SIZE(0..32))
     MAX-ACCESS   read-only
     STATUS       current
     DESCRIPTION
        "A descriptive name for the AP, usually represented by location."
     ::= { wsManagedAPStatusEntry 16 }

 wsManagedAPLastFailingConfigElement OBJECT-TYPE
     SYNTAX       Integer32(0..65535)
     MAX-ACCESS   read-only
     STATUS       current
     DESCRIPTION
        "Indicates the element Id of the last failing configuration
         element."
     ::= { wsManagedAPStatusEntry 17 }

 wsManagedAPConfigFailureErrMsg OBJECT-TYPE
     SYNTAX       DisplayString(SIZE(1..64))
     MAX-ACCESS   read-only
     STATUS       current
     DESCRIPTION
        "Indicates an ASCII string filled in by the AP, containing
         the error message."
     ::= { wsManagedAPStatusEntry 18 }

 wsManagedAPReset OBJECT-TYPE
     SYNTAX       INTEGER {
                    enable(1),
                    disable(2)
                  }
     MAX-ACCESS   read-only
     STATUS       current
     DESCRIPTION
        "This is an action object. Setting this object to
         enable will reset the AP. Read on this object will
         always return disable."
     ::= { wsManagedAPStatusEntry 19 }

 wsManagedAPResetStatus OBJECT-TYPE
     SYNTAX       INTEGER {
                    not-started(1),
                    in-progress(2),
                    success(3),
                    failure(4)
                  }
     MAX-ACCESS   read-only
     STATUS       current
     DESCRIPTION
        "This object gives status regarding the AP that
         got reset."
     ::= { wsManagedAPStatusEntry 20 }

 wsManagedAPFailedEntryPurge OBJECT-TYPE
     SYNTAX       INTEGER {
                    enable(1),
                    disable(2)
                  }
     MAX-ACCESS   read-only
     STATUS       current
     DESCRIPTION
        "This is an action object. Setting this object to
         enable will purge the failed AP entry. Read on this
         object will always return disable."
     ::= { wsManagedAPStatusEntry 21 }

 wsManagedAPDebugPassword OBJECT-TYPE
     SYNTAX       DisplayString(SIZE(0..32))
     MAX-ACCESS   not-accessible
     STATUS       current
     DESCRIPTION
        "Indicates password to be used for debugging managed AP. User should
        enable debug mode to set debug password. If password is configured,
        read on this object will return '*****'."
     ::= { wsManagedAPStatusEntry 22 }

 wsManagedAPDebugMode OBJECT-TYPE
     SYNTAX       INTEGER {
                    enable(1),
                    disable(2)
                  }
     MAX-ACCESS   not-accessible
     STATUS       current
     DESCRIPTION
        "This is an action object. Enabling this object will
         enable the telnet access to the managed AP."
     ::= { wsManagedAPStatusEntry 23 }

 wsManagedAPDebugStatus OBJECT-TYPE
     SYNTAX       INTEGER {
                    not-started(1),
                    requested(2),
                    in-progress(3),
                    success(4),
                    failure(5)
                  }
     MAX-ACCESS   not-accessible
     STATUS       current
     DESCRIPTION
        "This object indicates the status of the debug action
         requested when managed AP debug mode is set."
     ::= { wsManagedAPStatusEntry 24 }

 wsManagedAPAge OBJECT-TYPE
     SYNTAX       TimeTicks
     MAX-ACCESS   read-only
     STATUS       current
     DESCRIPTION
        "Time since last communication with an AP."
     ::= { wsManagedAPStatusEntry 25 }

 wsManagedAPManagingSwitch OBJECT-TYPE
     SYNTAX       INTEGER {
                    local-switch(1),
                    peer-switch(2)
                  }
     MAX-ACCESS   read-only
     STATUS       current
     DESCRIPTION
        "This object indicates whether the AP is managed by
         this controller or peer-controller."
     ::= {wsManagedAPStatusEntry 26}

 wsManagedAPSwitchMacAddress  OBJECT-TYPE
     SYNTAX       MacAddress
     MAX-ACCESS   read-only
     STATUS       current
     DESCRIPTION
        "MAC address of the WS managing the AP."
     ::= {wsManagedAPStatusEntry 27}

 wsManagedAPSwitchIpAddress OBJECT-TYPE
     SYNTAX       IpAddress
     MAX-ACCESS   read-only
     STATUS       current
     DESCRIPTION
        "IP address of the WS managing the AP."
     ::= {wsManagedAPStatusEntry 28}

 wsManagedAPIpMask OBJECT-TYPE
     SYNTAX       IpAddress
     MAX-ACCESS   read-only
     STATUS       current
     DESCRIPTION
        "Network IP mask of the managed AP."
     ::= { wsManagedAPStatusEntry 29 }

     wsManagedAPDistTunnelHomeAPClients OBJECT-TYPE
     SYNTAX             Unsigned32
     MAX-ACCESS         read-only
     STATUS             current
     DESCRIPTION
     "Number of clients using this AP as a Home AP. It is also the
      number of clients that roamed away from this AP and are
      tunneling data back to it."

       ::= {wsManagedAPStatusEntry 30}


   wsManagedAPDistTunnelAssocAPClients OBJECT-TYPE
     SYNTAX             Unsigned32
     MAX-ACCESS         read-only
     STATUS             current
     DESCRIPTION
            "Number of clients using this AP as an association AP. It is also the
             number of clients that roamed to this AP and are tunneling data
             back to the Home AP."

      ::= {wsManagedAPStatusEntry 31}


   wsManagedAPDistTunnelsTotal OBJECT-TYPE
     SYNTAX             Unsigned32
     MAX-ACCESS         read-only
     STATUS             current
     DESCRIPTION
            "Total number of APs to which this AP establishes
             distributed tunnels."

      ::= {wsManagedAPStatusEntry 32}

   wsManagedAPDistTunnelsMaxMcastRepl OBJECT-TYPE
     SYNTAX             Unsigned32
     MAX-ACCESS         read-only
     STATUS             current
     DESCRIPTION
            "Maximum number of tunnels on the home AP that are members of the
             same VLAN."

      ::= {wsManagedAPStatusEntry 33}


   wsManagedAPDistTunnelsMaxVlanMcastRepl OBJECT-TYPE
     SYNTAX             Unsigned32
     MAX-ACCESS         read-only
     STATUS             current
     DESCRIPTION
            "The VLAN ID over which the max number of multicast
             replications are sent into the distributed tunnels."

      ::= {wsManagedAPStatusEntry 34}



 wsManagedAPFailedEntriesPurge OBJECT-TYPE
     SYNTAX       INTEGER {
                    enable(1),
                    disable(2)
                  }
     MAX-ACCESS   read-only
     STATUS       current
     DESCRIPTION
        "This is an action object. Setting this object to
         enable will purge all the managed AP failed entries.
         Read on this object will always return disable."
     ::= { managedAP 2 }

--
-- wsManagedAPStatisticsTable
--
 wsManagedAPStatisticsTable OBJECT-TYPE
     SYNTAX       SEQUENCE OF WsManagedAPStatisticsEntry
     MAX-ACCESS   not-accessible
     STATUS       current
     DESCRIPTION
         "This table contains statistics available for each AP
          managed by the controller."
     ::= { managedAP 3 }

    wsManagedAPStatisticsEntry OBJECT-TYPE
     SYNTAX       WsManagedAPStatisticsEntry
     MAX-ACCESS   not-accessible
     STATUS       current
     DESCRIPTION
          "Each entry in this table contain statistics available for each AP
           managed by the controller."
     AUGMENTS { wsManagedAPStatusEntry }
     ::= { wsManagedAPStatisticsTable 1 }

 WsManagedAPStatisticsEntry ::=
     SEQUENCE {
      wsManagedAPWLANPktsRecvd                  Counter64,
      wsManagedAPWLANBytesRecvd                 Counter64,
      wsManagedAPWLANPktsTransmitted            Counter64,
      wsManagedAPWLANBytesTransmitted           Counter64,
      wsManagedAPEthernetPktsRecvd              Counter64,
      wsManagedAPEthernetBytesRecvd             Counter64,
      wsManagedAPEthernetMcastPktsRecvd         Counter64,
      wsManagedAPEthernetPktsTransmitted        Counter64,
      wsManagedAPEthernetBytesTransmitted       Counter64,
      wsManagedAPEthernetTransmitErrorCount     Counter64,
      wsManagedAPEthernetRecvdErrorCount        Counter64,
      wsManagedAPCL2TunnelBytesRecvd            Counter64,
      wsManagedAPCL2TunnelPktsRecvd             Counter64,
      wsManagedAPCL2TunnelMcastRecvd            Counter64,
      wsManagedAPCL2TunnelBytesTransmitted      Counter64,
      wsManagedAPCL2TunnelPktsTransmitted       Counter64,
      wsManagedAPCL2TunnelMcastTransmitted      Counter64,
      wsManagedAPWLANPktsRecvDropped            Counter64,
      wsManagedAPWLANBytesRecvDropped           Counter64,
      wsManagedAPWLANPktsTransmitDropped        Counter64,
      wsManagedAPWLANBytesTransmitDropped       Counter64,
      wsManagedAPDistTunnelBytesTransmitted     Counter64,
      wsManagedAPDistTunnelBytesReceived        Counter64,
      wsManagedAPDistTunnelPacketsTransmitted   Counter64,
      wsManagedAPDistTunnelPacketsReceived      Counter64,
      wsManagedAPDistTunnelMcastPacketsTransmitted     Counter64,
      wsManagedAPDistTunnelMcastPacketsReceived        Counter64,
      wsManagedAPDistTunnelRoamedClients               Unsigned32,
      wsManagedAPDistTunnelRoamedClientsIdleTimedOut   Unsigned32,
      wsManagedAPDistTunnelRoamedClientsAgeTimedOut    Unsigned32,
      wsManagedAPDistTunnelMaxClientLimitSetupDenials  Unsigned32,
      wsManagedAPDistTunnelMaxReplSetupDenials         Unsigned32,
      wsManagedAPARPReqsFromBcastToUcast               Unsigned32,
      wsManagedAPFilteredARPRequest                    Unsigned32,
      wsManagedAPBroadcastedARPRequests                Unsigned32

 }

    wsManagedAPWLANPktsRecvd    OBJECT-TYPE
         SYNTAX      Counter64
         MAX-ACCESS  read-only
         STATUS      current
         DESCRIPTION
              "Total packets received by an AP on the wireless
               network."
         ::= { wsManagedAPStatisticsEntry 1 }

    wsManagedAPWLANBytesRecvd    OBJECT-TYPE
         SYNTAX      Counter64
         MAX-ACCESS  read-only
         STATUS      current
         DESCRIPTION
              "Total bytes received by an AP on the wireless
               network."
         ::= { wsManagedAPStatisticsEntry 2}

    wsManagedAPWLANPktsTransmitted    OBJECT-TYPE
         SYNTAX      Counter64
         MAX-ACCESS  read-only
         STATUS      current
         DESCRIPTION
              "Total packets transmitted by an AP on the wireless
               network."
         ::= { wsManagedAPStatisticsEntry 3 }

    wsManagedAPWLANBytesTransmitted    OBJECT-TYPE
         SYNTAX      Counter64
         MAX-ACCESS  read-only
         STATUS      current
         DESCRIPTION
              "Total bytes transmitted by an AP on the wireless
               network."
         ::= { wsManagedAPStatisticsEntry 4 }

    wsManagedAPEthernetPktsRecvd    OBJECT-TYPE
         SYNTAX      Counter64
         MAX-ACCESS  read-only
         STATUS      current
         DESCRIPTION
              "Total packets received by an AP on the wired
               network."
         ::= { wsManagedAPStatisticsEntry 5 }

    wsManagedAPEthernetBytesRecvd    OBJECT-TYPE
         SYNTAX      Counter64
         MAX-ACCESS  read-only
         STATUS      current
         DESCRIPTION
              "Total bytes received by an AP on the wired
               network."
         ::= { wsManagedAPStatisticsEntry 6 }

    wsManagedAPEthernetMcastPktsRecvd    OBJECT-TYPE
         SYNTAX      Counter64
         MAX-ACCESS  read-only
         STATUS      current
         DESCRIPTION
              "Total multicast packets received by an AP on the
               wired network."
         ::= { wsManagedAPStatisticsEntry 7 }

    wsManagedAPEthernetPktsTransmitted    OBJECT-TYPE
         SYNTAX      Counter64
         MAX-ACCESS  read-only
         STATUS      current
         DESCRIPTION
              "Total packets transmitted by an AP on the wired
               network."
         ::= { wsManagedAPStatisticsEntry 8 }

    wsManagedAPEthernetBytesTransmitted    OBJECT-TYPE
         SYNTAX      Counter64
         MAX-ACCESS  read-only
         STATUS      current
         DESCRIPTION
              "Total bytes transmitted by an AP on the wired
               network."
         ::= { wsManagedAPStatisticsEntry 9 }

    wsManagedAPEthernetTransmitErrorCount    OBJECT-TYPE
         SYNTAX      Counter64
         MAX-ACCESS  read-only
         STATUS      current
         DESCRIPTION
              "Total  transmit errors detected  by an AP on the
               wired network."
         ::= { wsManagedAPStatisticsEntry 10 }

    wsManagedAPEthernetRecvdErrorCount    OBJECT-TYPE
         SYNTAX      Counter64
         MAX-ACCESS  read-only
         STATUS      current
         DESCRIPTION
              "Total receive errors detected by an AP on the
               wired network."
         ::= { wsManagedAPStatisticsEntry 11 }

    wsManagedAPCL2TunnelBytesRecvd    OBJECT-TYPE
         SYNTAX      Counter64
         MAX-ACCESS  read-only
         STATUS      current
         DESCRIPTION
              "Total bytes received via central L2 tunnel by the AP."
         ::= { wsManagedAPStatisticsEntry 12 }

    wsManagedAPCL2TunnelPktsRecvd    OBJECT-TYPE
         SYNTAX      Counter64
         MAX-ACCESS  read-only
         STATUS      current
         DESCRIPTION
              "Total packets received via central L2 tunnel by the AP."
         ::= { wsManagedAPStatisticsEntry 13 }

    wsManagedAPCL2TunnelMcastRecvd    OBJECT-TYPE
         SYNTAX      Counter64
         MAX-ACCESS  read-only
         STATUS      current
         DESCRIPTION
              "Total multicast packets received via central L2 tunnel
              by the AP."
         ::= { wsManagedAPStatisticsEntry 14 }

    wsManagedAPCL2TunnelBytesTransmitted    OBJECT-TYPE
         SYNTAX      Counter64
         MAX-ACCESS  read-only
         STATUS      current
         DESCRIPTION
              "Total bytes transmitted via central L2 tunnel by the AP."
         ::= { wsManagedAPStatisticsEntry 15 }

    wsManagedAPCL2TunnelPktsTransmitted    OBJECT-TYPE
         SYNTAX      Counter64
         MAX-ACCESS  read-only
         STATUS      current
         DESCRIPTION
              "Total packets transmitted via central L2 tunnel by the AP."
         ::= { wsManagedAPStatisticsEntry 16 }

    wsManagedAPCL2TunnelMcastTransmitted    OBJECT-TYPE
         SYNTAX      Counter64
         MAX-ACCESS  read-only
         STATUS      current
         DESCRIPTION
              "Total multicast packets transmitted via central L2 tunnel by the AP."
         ::= { wsManagedAPStatisticsEntry 17 }

    wsManagedAPWLANPktsRecvDropped    OBJECT-TYPE
         SYNTAX      Counter64
         MAX-ACCESS  read-only
         STATUS      current
         DESCRIPTION
              "Total packets dropped in the receive direction by an AP
               on the wireless network.  This is due to client QoS actions
               affecting the wireless up (inbound) direction from AP to client."
         ::= { wsManagedAPStatisticsEntry 18 }

    wsManagedAPWLANBytesRecvDropped    OBJECT-TYPE
         SYNTAX      Counter64
         MAX-ACCESS  read-only
         STATUS      current
         DESCRIPTION
              "Total bytes dropped in the receive direction by an AP
               on the wireless network.  This is due to client QoS actions
               affecting the wireless up (inbound) direction from AP to client."
         ::= { wsManagedAPStatisticsEntry 19 }

    wsManagedAPWLANPktsTransmitDropped    OBJECT-TYPE
         SYNTAX      Counter64
         MAX-ACCESS  read-only
         STATUS      current
         DESCRIPTION
              "Total packets dropped in the transmit direction by an AP
               on the wireless network.  This is due to client QoS actions
               affecting the wireless down (outbound) direction from AP to client."
         ::= { wsManagedAPStatisticsEntry 20 }

    wsManagedAPWLANBytesTransmitDropped    OBJECT-TYPE
         SYNTAX      Counter64
         MAX-ACCESS  read-only
         STATUS      current
         DESCRIPTION
              "Total bytes dropped in the transmit direction by an AP
               on the wireless network.  This is due to client QoS actions
               affecting the wireless down (outbound) direction from AP to client."
         ::= { wsManagedAPStatisticsEntry 21 }


    wsManagedAPDistTunnelBytesTransmitted OBJECT-TYPE
        SYNTAX        Counter64
        MAX-ACCESS    read-only
        STATUS        current
        DESCRIPTION
             "Total Bytes transmitted by the AP through all the established
              Distributed Tunnels."
        ::= {wsManagedAPStatisticsEntry 22 }

    wsManagedAPDistTunnelBytesReceived OBJECT-TYPE
        SYNTAX        Counter64
        MAX-ACCESS    read-only
        STATUS        current
        DESCRIPTION
               "Total Bytes received by the AP through all the established
                Distributed Tunnels."
        ::= {wsManagedAPStatisticsEntry 23 }


    wsManagedAPDistTunnelPacketsTransmitted OBJECT-TYPE
        SYNTAX        Counter64
        MAX-ACCESS    read-only
        STATUS        current
        DESCRIPTION
              "Total packets transmitted by the AP through all the established
                Distributed Tunnels."
        ::= {wsManagedAPStatisticsEntry  24 }


    wsManagedAPDistTunnelPacketsReceived OBJECT-TYPE
        SYNTAX         Counter64
        MAX-ACCESS     read-only
        STATUS         current
        DESCRIPTION
             "Total packets received by the AP through all the established
              Distributed Tunnels."
        ::= {wsManagedAPStatisticsEntry  25 }

    wsManagedAPDistTunnelMcastPacketsTransmitted OBJECT-TYPE
        SYNTAX          Counter64
        MAX-ACCESS      read-only
        STATUS          current
        DESCRIPTION
             "Total multicast packets transmitted by the AP through all the established
              Distributed Tunnels."
        ::= {wsManagedAPStatisticsEntry  26 }


    wsManagedAPDistTunnelMcastPacketsReceived OBJECT-TYPE
        SYNTAX           Counter64
        MAX-ACCESS       read-only
        STATUS           current
        DESCRIPTION
             "Total multicast packets received by the AP through all the established
              Distributed Tunnels."
        ::= {wsManagedAPStatisticsEntry  27 }

    wsManagedAPDistTunnelRoamedClients OBJECT-TYPE
        SYNTAX          Unsigned32
        MAX-ACCESS      read-only
        STATUS          current
        DESCRIPTION
             "Total number of clients that used this AP for Distributed Tunneling.
              This inclides clients that roamed away from and to this AP."
        ::= {wsManagedAPStatisticsEntry  28 }

    wsManagedAPDistTunnelRoamedClientsIdleTimedOut OBJECT-TYPE
        SYNTAX          Unsigned32
        MAX-ACCESS      read-only
        STATUS          current
        DESCRIPTION
             "Number of client tunnel sessions that were terminated because of not sending the
              traffic through the tunnel after roaming."
        ::= {wsManagedAPStatisticsEntry  29 }


    wsManagedAPDistTunnelRoamedClientsAgeTimedOut OBJECT-TYPE
        SYNTAX          Unsigned32
        MAX-ACCESS      read-only
        STATUS          current
        DESCRIPTION
             "Number of client tunnel sessions that were terminated because of expiry
              of the tunnel session."
        ::= {wsManagedAPStatisticsEntry  30 }


    wsManagedAPDistTunnelMaxClientLimitSetupDenials OBJECT-TYPE
        SYNTAX         Unsigned32
        MAX-ACCESS     read-only
        STATUS         current
        DESCRIPTION
             "Number of client tunnel session setup denials by the AP because of reaching
              the maximum configured client limit."
        ::= {wsManagedAPStatisticsEntry  31 }

    wsManagedAPDistTunnelMaxReplSetupDenials OBJECT-TYPE
        SYNTAX         Unsigned32
        MAX-ACCESS     read-only
        STATUS         current
        DESCRIPTION
             "Number of client tunnel setup denials by the AP because of reaching the maximum
              configured VLAN replications limit."
        ::= {wsManagedAPStatisticsEntry  32 }

    wsManagedAPARPReqsFromBcastToUcast OBJECT-TYPE
        SYNTAX         Unsigned32
        MAX-ACCESS     read-only
        STATUS         current
        DESCRIPTION
             "Total number of ARP requests converted from broadcast to unicast
              packet before transmitting on wireless network."
        ::= {wsManagedAPStatisticsEntry  33 }

    wsManagedAPFilteredARPRequest OBJECT-TYPE
        SYNTAX         Unsigned32
        MAX-ACCESS     read-only
        STATUS         current
        DESCRIPTION
             "Total number of ARP requests filtered by the wireless ARP
              suppression logic."
        ::= {wsManagedAPStatisticsEntry  34 }

    wsManagedAPBroadcastedARPRequests OBJECT-TYPE
        SYNTAX         Unsigned32
        MAX-ACCESS     read-only
        STATUS         current
        DESCRIPTION
             "Total number of ARP requests broadcasted on to the wireless
              network after being processed by wireless ARP suppression logic."
        ::= {wsManagedAPStatisticsEntry  35 }

--
--   wsManagedAPRadioStatusTable
--
 wsManagedAPRadioStatusTable OBJECT-TYPE
     SYNTAX       SEQUENCE OF WsManagedAPRadioStatusEntry
     MAX-ACCESS   not-accessible
     STATUS       current
     DESCRIPTION
           "This table contains status parameters per radio interface for
           all the APs managed by controller."
     ::= { managedAP 4 }

    wsManagedAPRadioStatusEntry OBJECT-TYPE
     SYNTAX       WsManagedAPRadioStatusEntry
     MAX-ACCESS   not-accessible
     STATUS       current
     DESCRIPTION
          "Each entry in this table contains status parameters per radio
          interface for an AP managed by the controller."
     INDEX    { wsManagedAPMacAddress, wsManagedAPRadioInterface}
     ::= { wsManagedAPRadioStatusTable 1 }

 WsManagedAPRadioStatusEntry ::=
     SEQUENCE {
      wsManagedAPRadioInterface            Integer32,
      wsManagedAPRadioMacAddress           MacAddress,
      wsManagedAPRadioChannel              Integer32,
      wsManagedAPRadioTxPower              Integer32,
      wsManagedAPRadioAuthenticatedClients Unsigned32,
      wsManagedAPRadioWLANUtilization      Integer32,
      wsManagedAPRadioFixedChannelIndicator INTEGER,
      wsManagedAPRadioMCAStatus             INTEGER,
      wsManagedAPRadioFixedPowerIndicator   INTEGER,
      wsManagedAPRadioMPAStatus             INTEGER,
      wsManagedAPRadioNeighborCount         Unsigned32,
      wsManagedAPRadioFixedChannelAction           INTEGER,
      wsManagedAPRadioFixedChannel                 Integer32,
      wsManagedAPRadioFixedPowerAction             INTEGER,
      wsManagedAPRadioFixedPower                   Integer32,
      wsManagedAPRadioBandwidth            INTEGER,
      wsManagedAPRadioResourceMeasEnabled  INTEGER
 }

 wsManagedAPRadioInterface OBJECT-TYPE
     SYNTAX       Integer32(1..2)
     MAX-ACCESS   read-only
     STATUS       current
     DESCRIPTION
        "The physical radio interface on the AP."
     ::= { wsManagedAPRadioStatusEntry 1 }

 wsManagedAPRadioMacAddress OBJECT-TYPE
     SYNTAX       MacAddress
     MAX-ACCESS   read-only
     STATUS       current
     DESCRIPTION
        "The MAC address of the physical radio."
     ::= { wsManagedAPRadioStatusEntry 2 }

 wsManagedAPRadioChannel OBJECT-TYPE
     SYNTAX       Integer32(0..13|36|40|44|48|52|56|60|64)
     MAX-ACCESS   read-only
     STATUS       current
     DESCRIPTION
        "If the radio is operational, the current transmit channel
         for this radio interface."
     ::= { wsManagedAPRadioStatusEntry 3 }

 wsManagedAPRadioTxPower OBJECT-TYPE
     SYNTAX       Integer32(0..100)
     MAX-ACCESS   read-only
     STATUS       current
     DESCRIPTION
        "If the radio is operational, the current transmit power
         of the radio."
     ::= { wsManagedAPRadioStatusEntry 4 }

 wsManagedAPRadioAuthenticatedClients OBJECT-TYPE
     SYNTAX       Unsigned32
     MAX-ACCESS   read-only
     STATUS       current
     DESCRIPTION
        "Total count of clients authenticated on the physical radio."
     ::= { wsManagedAPRadioStatusEntry 5 }

 wsManagedAPRadioWLANUtilization OBJECT-TYPE
     SYNTAX       Integer32(0..100)
     MAX-ACCESS   read-only
     STATUS       current
     DESCRIPTION
        "Total network utilization for the physical radio. This
         value is based on radio statistics."
     ::= { wsManagedAPRadioStatusEntry 6 }

 wsManagedAPRadioFixedChannelIndicator OBJECT-TYPE
     SYNTAX       INTEGER {
                     yes(1),
                     no(2)
                  }
     MAX-ACCESS   read-only
     STATUS       current
     DESCRIPTION
         "This flag indicates if a fixed channel is configured
          and assigned to the radio."
     ::= { wsManagedAPRadioStatusEntry 7 }

 wsManagedAPRadioMCAStatus OBJECT-TYPE
     SYNTAX       INTEGER {
                     none(1),
                     in-progress(2),
                     complete(3),
                     failure(4)
                  }
     MAX-ACCESS   read-only
     STATUS       current
     DESCRIPTION
         "Indicates the current state of a manual request
          to change the channel on this radio."
     ::= { wsManagedAPRadioStatusEntry 8 }

 wsManagedAPRadioFixedPowerIndicator OBJECT-TYPE
     SYNTAX       INTEGER {
                     yes(1),
                     no(2)
                  }
     MAX-ACCESS   read-only
     STATUS       current
     DESCRIPTION
         "This flag indicates if a fixed power setting is configured
          and assigned to the radio."
     ::= { wsManagedAPRadioStatusEntry 9 }

 wsManagedAPRadioMPAStatus OBJECT-TYPE
     SYNTAX       INTEGER {
                     none(1),
                     in-progress(2),
                     complete(3),
                     failure(4)
                  }
     MAX-ACCESS   read-only
     STATUS       current
     DESCRIPTION
         "Indicates the current state of a manual request
          to change the power setting on this radio."
     ::= { wsManagedAPRadioStatusEntry 10 }

 wsManagedAPRadioNeighborCount OBJECT-TYPE
     SYNTAX       Unsigned32
     MAX-ACCESS   read-only
     STATUS       current
     DESCRIPTION
         "Total number of neighbors that can be seen
          by this radio in its RF area."
     ::= { wsManagedAPRadioStatusEntry 11 }

 wsManagedAPRadioFixedChannelAction OBJECT-TYPE
     SYNTAX       INTEGER {
                    none(1),
                    apply(2)
                  }
     MAX-ACCESS   read-only
     STATUS       current
     DESCRIPTION
        "This is an action object. When we set this object to apply,
         along with wsManagedAPRadioFixedChannel, controller starts
         applying fixed channel assignment for this radio. Read
         on this object will always return none."
     ::= { wsManagedAPRadioStatusEntry 12 }

 wsManagedAPRadioFixedChannel OBJECT-TYPE
     SYNTAX       Integer32(0..13|36|40|44|48|52|56|60|64)
     MAX-ACCESS   read-only
     STATUS       current
     DESCRIPTION
        "This object is used to assign the fixed channel for this radio on this
        Managed AP.
        The following MIB objects get changed on successful setting of this
        MIB object -
        1. wsManagedAPRadioChannel --> changes to the channel set here
        2. wsManagedAPRadioFixedChannelIndicator --> changes to 'yes (2)'
        Read on this object will always return 0."
     ::= { wsManagedAPRadioStatusEntry 13 }

 wsManagedAPRadioFixedPowerAction OBJECT-TYPE
     SYNTAX       INTEGER {
                    none(1),
                    apply(2)
                  }
     MAX-ACCESS   read-only
     STATUS       current
     DESCRIPTION
        "This is an action object. When we set this object to apply,
         controller starts applying fixed power adjustment for this radio.
         Read on this object will always return none."
     ::= { wsManagedAPRadioStatusEntry 14 }

 wsManagedAPRadioFixedPower OBJECT-TYPE
     SYNTAX       Integer32(1..100)
     MAX-ACCESS   read-only
     STATUS       current
     DESCRIPTION
        "This object is used to assign the fixed power for this radio on this
        Managed AP.
        The following MIB objects get changed on successful setting of this
        MIB object -
        1. wsManagedAPRadioTxPower --> changes to the power set here
        2. wsManagedAPRadioFixedPowerIndicator --> changes to 'yes (2)'
        Read on this object will always return 0."
     ::= { wsManagedAPRadioStatusEntry 15 }

 wsManagedAPRadioBandwidth OBJECT-TYPE
     SYNTAX       INTEGER {
                    none(0),
                    twentyMHz(1),
                    fortyMHz(2),
                    eightyMHz(3)
                  }
     MAX-ACCESS   read-only
     STATUS       current
     DESCRIPTION
        "Current Channel Bandwidth In Use."
     ::= { wsManagedAPRadioStatusEntry 16 }


 wsManagedAPRadioResourceMeasEnabled OBJECT-TYPE
     SYNTAX       INTEGER {
                    enabled(1),
                    disabled(2)
                  }
     MAX-ACCESS   not-accessible
     STATUS       current
     DESCRIPTION
        "Current state of enablement for Radio Resource Management (RRM)."
     ::= { wsManagedAPRadioStatusEntry 17 }


--
-- wsManagedAPRadioStatisticsTable
--
 wsManagedAPRadioStatisticsTable OBJECT-TYPE
     SYNTAX       SEQUENCE OF  WsManagedAPRadioStatisticsEntry
     MAX-ACCESS   not-accessible
     STATUS       current
     DESCRIPTION
         "This table contains statistics available for each physical
          radio on an AP managed by the controller."
     ::= { managedAP 5 }

    wsManagedAPRadioStatisticsEntry OBJECT-TYPE
     SYNTAX       WsManagedAPRadioStatisticsEntry
     MAX-ACCESS   not-accessible
     STATUS       current
     DESCRIPTION
          "Each entry in this table contain statistics available for each
           physical radio on an  AP managed by controller."
     AUGMENTS { wsManagedAPRadioStatusEntry }
     ::= { wsManagedAPRadioStatisticsTable 1 }

 WsManagedAPRadioStatisticsEntry ::=
     SEQUENCE {
      wsManagedAPRadioWLANPktsRecvd             Counter64,
      wsManagedAPRadioWLANBytesRecvd            Counter64,
      wsManagedAPRadioWLANPktsTransmitted       Counter64,
      wsManagedAPRadioWLANBytesTransmitted      Counter64,
      wsManagedAPRadioTxFragmentCount           Counter32,
      wsManagedAPRadioMcastTxFrameCount         Counter32,
      wsManagedAPRadioFailedCount               Counter32,
      wsManagedAPRadioRetryCount                Counter32,
      wsManagedAPRadioMultipleRetryCount        Counter32,
      wsManagedAPRadioFrameDuplicateCount       Counter32,
      wsManagedAPRadioRTSSuccessCount           Counter32,
      wsManagedAPRadioRTSFailureCount           Counter32,
      wsManagedAPRadioACKFailureCount           Counter32,
      wsManagedAPRadioRecvdFragmentCount        Counter32,
      wsManagedAPRadioMcastRecvdFrameCount      Counter32,
      wsManagedAPRadioFCSErrorCount             Counter32,
      wsManagedAPRadioTxFrameCount              Counter32,
      wsManagedAPRadioWEPUndecryptableCount     Counter32,
      wsManagedAPRadioWLANPktsRecvDropped       Counter64,
      wsManagedAPRadioWLANBytesRecvDropped      Counter64,
      wsManagedAPRadioWLANPktsTransmitDropped   Counter64,
      wsManagedAPRadioWLANBytesTransmitDropped  Counter64

 }

    wsManagedAPRadioWLANPktsRecvd    OBJECT-TYPE
         SYNTAX      Counter64
         MAX-ACCESS  read-only
         STATUS      current
         DESCRIPTION
              "Total packets received by an AP on this radio interface."
         ::= { wsManagedAPRadioStatisticsEntry 1 }

    wsManagedAPRadioWLANBytesRecvd    OBJECT-TYPE
         SYNTAX      Counter64
         MAX-ACCESS  read-only
         STATUS      current
         DESCRIPTION
              "Total bytes received by an AP on this radio interface."
         ::= { wsManagedAPRadioStatisticsEntry 2 }

    wsManagedAPRadioWLANPktsTransmitted    OBJECT-TYPE
         SYNTAX      Counter64
         MAX-ACCESS  read-only
         STATUS      current
         DESCRIPTION
              "Total packets transmitted by an AP on this radio interface."
         ::= { wsManagedAPRadioStatisticsEntry 3 }

    wsManagedAPRadioWLANBytesTransmitted    OBJECT-TYPE
         SYNTAX      Counter64
         MAX-ACCESS  read-only
         STATUS      current
         DESCRIPTION
              "Total bytes transmitted by an AP on this radio interface."
         ::= { wsManagedAPRadioStatisticsEntry 4 }

    wsManagedAPRadioTxFragmentCount    OBJECT-TYPE
         SYNTAX      Counter32
         MAX-ACCESS  read-only
         STATUS      current
         DESCRIPTION
              "Count of acknowledged MPDU with an individual address
               or an MPDU with a multicast address of type data or
               management."
         ::= { wsManagedAPRadioStatisticsEntry 5 }

    wsManagedAPRadioMcastTxFrameCount    OBJECT-TYPE
         SYNTAX      Counter32
         MAX-ACCESS  read-only
         STATUS      current
         DESCRIPTION
             "Count of successfully transmitted MSDU frames where
              the multicast bit is set in the destination MAC address."
         ::= { wsManagedAPRadioStatisticsEntry 6 }

    wsManagedAPRadioFailedCount    OBJECT-TYPE
         SYNTAX      Counter32
         MAX-ACCESS  read-only
         STATUS      current
         DESCRIPTION
              "Number of times a MSDU is not transmitted successfully due to
               transmit attempts exceeding either the short retry limit or the
               long retry limit."
         ::= { wsManagedAPRadioStatisticsEntry 7 }

    wsManagedAPRadioRetryCount    OBJECT-TYPE
         SYNTAX      Counter32
         MAX-ACCESS  read-only
         STATUS      current
         DESCRIPTION
          "Number of times a MSDU is successfully transmitted after one or
           more retries."
         ::= { wsManagedAPRadioStatisticsEntry 8 }

    wsManagedAPRadioMultipleRetryCount    OBJECT-TYPE
         SYNTAX      Counter32
         MAX-ACCESS  read-only
         STATUS      current
         DESCRIPTION
          "Number of times a MSDU is successfully transmitted after
           more than one retry."
         ::= { wsManagedAPRadioStatisticsEntry 9 }

    wsManagedAPRadioFrameDuplicateCount    OBJECT-TYPE
         SYNTAX      Counter32
         MAX-ACCESS  read-only
         STATUS      current
         DESCRIPTION
          "Number of times a frame is received and sequence control
           field indicates is a duplicate."
         ::= { wsManagedAPRadioStatisticsEntry 10 }

    wsManagedAPRadioRTSSuccessCount    OBJECT-TYPE
         SYNTAX      Counter32
         MAX-ACCESS  read-only
         STATUS      current
         DESCRIPTION
           "Count of CTS frames received in response to the RTS frames."
         ::= { wsManagedAPRadioStatisticsEntry 11 }

    wsManagedAPRadioRTSFailureCount    OBJECT-TYPE
         SYNTAX      Counter32
         MAX-ACCESS  read-only
         STATUS      current
         DESCRIPTION
          "Count of CTS frames not received in response to the
           RTS frames."
         ::= { wsManagedAPRadioStatisticsEntry 12 }

    wsManagedAPRadioACKFailureCount    OBJECT-TYPE
         SYNTAX      Counter32
         MAX-ACCESS  read-only
         STATUS      current
         DESCRIPTION
           "Count of ACK frames not received when expected."
         ::= { wsManagedAPRadioStatisticsEntry 13 }

    wsManagedAPRadioRecvdFragmentCount    OBJECT-TYPE
         SYNTAX      Counter32
         MAX-ACCESS  read-only
         STATUS      current
         DESCRIPTION
          "Count of successfully received MPDU frames of type data
           or management."
         ::= { wsManagedAPRadioStatisticsEntry 14 }

    wsManagedAPRadioMcastRecvdFrameCount    OBJECT-TYPE
         SYNTAX      Counter32
         MAX-ACCESS  read-only
         STATUS      current
         DESCRIPTION
          "Count of MSDU frames received with the multicast bit
           set in the destination MAC address."
         ::= { wsManagedAPRadioStatisticsEntry 15 }

    wsManagedAPRadioFCSErrorCount    OBJECT-TYPE
         SYNTAX      Counter32
         MAX-ACCESS  read-only
         STATUS      current
         DESCRIPTION
          "Count of FCS errors detected in a received MPDU frame."
         ::= { wsManagedAPRadioStatisticsEntry 16 }

    wsManagedAPRadioTxFrameCount    OBJECT-TYPE
         SYNTAX      Counter32
         MAX-ACCESS  read-only
         STATUS      current
         DESCRIPTION
          "Count of each successfully transmitted MSDU."
         ::= { wsManagedAPRadioStatisticsEntry 17 }

    wsManagedAPRadioWEPUndecryptableCount    OBJECT-TYPE
         SYNTAX      Counter32
         MAX-ACCESS  read-only
         STATUS      current
         DESCRIPTION
           "Count of encrypted frames received and the key configuration
            of the transmitter indicates that the frame should not have
            been encrypted or that frame was discarded due to the receiving
            station not implementing the privacy option."
         ::= { wsManagedAPRadioStatisticsEntry 18 }

    wsManagedAPRadioWLANPktsRecvDropped    OBJECT-TYPE
         SYNTAX      Counter64
         MAX-ACCESS  not-accessible
         STATUS      current
         DESCRIPTION
              "Total packets dropped in the receive direction on this
               radio interface.  This is due to client QoS actions
               affecting the wireless up (inbound) direction from AP to client."
         ::= { wsManagedAPRadioStatisticsEntry 19 }

    wsManagedAPRadioWLANBytesRecvDropped    OBJECT-TYPE
         SYNTAX      Counter64
         MAX-ACCESS  not-accessible
         STATUS      current
         DESCRIPTION
              "Total bytes dropped in the receive direction on this
               radio interface.  This is due to client QoS actions
               affecting the wireless up (inbound) direction from AP to client."
         ::= { wsManagedAPRadioStatisticsEntry 20 }

    wsManagedAPRadioWLANPktsTransmitDropped    OBJECT-TYPE
         SYNTAX      Counter64
         MAX-ACCESS  not-accessible
         STATUS      current
         DESCRIPTION
              "Total packets dropped in the transmit direction by this
               radio interface.  This is due to client QoS actions
               affecting the wireless down (outbound) direction from AP to client."
         ::= { wsManagedAPRadioStatisticsEntry 21 }

    wsManagedAPRadioWLANBytesTransmitDropped    OBJECT-TYPE
         SYNTAX      Counter64
         MAX-ACCESS  not-accessible
         STATUS      current
         DESCRIPTION
              "Total bytes dropped in the transmit direction by this
               radio interface.  This is due to client QoS actions
               affecting the wireless down (outbound) direction from AP to client."
         ::= { wsManagedAPRadioStatisticsEntry 22 }

--
--   wsManagedAPNeighborAPListTable
--
 wsManagedAPNeighborAPListTable OBJECT-TYPE
     SYNTAX       SEQUENCE OF WsManagedAPNeighborAPListEntry
     MAX-ACCESS   not-accessible
     STATUS       current
     DESCRIPTION
           "This table contains neighbor AP list."
     ::= { managedAP 6 }

    wsManagedAPNeighborAPListEntry OBJECT-TYPE
     SYNTAX       WsManagedAPNeighborAPListEntry
     MAX-ACCESS   not-accessible
     STATUS       current
     DESCRIPTION
          "Each entry in this table contains neighbor AP information."
     INDEX    { wsManagedAPMacAddress, wsManagedAPRadioInterface,
                wsNeighborMacAddress}
     ::= { wsManagedAPNeighborAPListTable 1 }

 WsManagedAPNeighborAPListEntry ::=
     SEQUENCE {
      wsNeighborMacAddress      MacAddress,
      wsNeighborSSID            DisplayString,
      wsNeighborRSSI            Integer32,
      wsNeighborStatus          INTEGER,
      wsNeighborAge             TimeTicks
 }

 wsNeighborMacAddress OBJECT-TYPE
     SYNTAX       MacAddress
     MAX-ACCESS   read-only
     STATUS       current
     DESCRIPTION
        "The MAC address of neighbor AP network. This could be a physical radio MAC or
         VAP MAC address."
     ::= { wsManagedAPNeighborAPListEntry 1 }

 wsNeighborSSID OBJECT-TYPE
     SYNTAX       DisplayString(SIZE(1..32))
     MAX-ACCESS   read-only
     STATUS       current
     DESCRIPTION
        "Service Set ID of neighbor AP network."
     ::= { wsManagedAPNeighborAPListEntry 2 }

 wsNeighborRSSI OBJECT-TYPE
     SYNTAX       Integer32(0..100)
     MAX-ACCESS   read-only
     STATUS       current
     DESCRIPTION
        "This object indicates Received Signal Strength(RSSI)
        from the neighbor radios in a given channel."
     ::= { wsManagedAPNeighborAPListEntry 3 }

 wsNeighborStatus OBJECT-TYPE
     SYNTAX       INTEGER {
                     managed(1),
                     unknown(2),
                     standalone(3),
                     rogue(4)
                  }
     MAX-ACCESS   read-only
     STATUS       current
     DESCRIPTION
        "Indicates managed status of the AP."
     ::= { wsManagedAPNeighborAPListEntry 4 }

 wsNeighborAge OBJECT-TYPE
     SYNTAX       TimeTicks
     MAX-ACCESS   read-only
     STATUS       current
     DESCRIPTION
        "Indicates time since this AP was last detected."
     ::= { wsManagedAPNeighborAPListEntry 5 }


wsManagedAPNeighborEntriesPurge OBJECT-TYPE
     SYNTAX       INTEGER {
                    enable(1),
                    disable(2)
                  }
     MAX-ACCESS   read-only
     STATUS       current
     DESCRIPTION
        "This is an action object used to purge the AP neighbor
         entries. Read on this object will always return disable."
     ::= { managedAP 7 }
--
--   wsManagedAPNeighborClientListTable
--
 wsManagedAPNeighborClientListTable OBJECT-TYPE
     SYNTAX       SEQUENCE OF WsManagedAPNeighborClientListEntry
     MAX-ACCESS   not-accessible
     STATUS       current
     DESCRIPTION
           "This table contains neighbor client list currently
           detected by an RF scan on the radio."
     ::= { managedAP 8 }

    wsManagedAPNeighborClientListEntry OBJECT-TYPE
     SYNTAX       WsManagedAPNeighborClientListEntry
     MAX-ACCESS   not-accessible
     STATUS       current
     DESCRIPTION
          "Each entry in this table contain neighbor client information."
     INDEX    { wsManagedAPMacAddress, wsManagedAPRadioInterface,
                wsNeighborClientMacAddress}
     ::= { wsManagedAPNeighborClientListTable 1 }

 WsManagedAPNeighborClientListEntry ::=
     SEQUENCE {
      wsNeighborClientMacAddress        MacAddress,
      wsNeighborClientRSSI              Integer32,
      wsNeighborClientChannel           Integer32,
      wsNeighborClientAge               TimeTicks,
      wsNeighborClientDiscoveryReason   BITS
 }

 wsNeighborClientMacAddress OBJECT-TYPE
     SYNTAX       MacAddress
     MAX-ACCESS   read-only
     STATUS       current
     DESCRIPTION
        "The MAC address of neighbor client station."
     ::= {wsManagedAPNeighborClientListEntry  1 }

 wsNeighborClientRSSI OBJECT-TYPE
     SYNTAX       Integer32(0..100)
     MAX-ACCESS   read-only
     STATUS       current
     DESCRIPTION
        "Indicates RSSI from neighbor clients on the radio."
     ::= { wsManagedAPNeighborClientListEntry 2 }

 wsNeighborClientChannel OBJECT-TYPE
     SYNTAX       Integer32(1..13|36|40|44|48|52|56|60|64)
     MAX-ACCESS   read-only
     STATUS       current
     DESCRIPTION
        "Indicates AP channel, on which the client frame was received."
     ::= { wsManagedAPNeighborClientListEntry 3 }

 wsNeighborClientAge OBJECT-TYPE
     SYNTAX       TimeTicks
     MAX-ACCESS   read-only
     STATUS       current
     DESCRIPTION
        "Indicates time since a client was last detected."
     ::= { wsManagedAPNeighborClientListEntry 4 }

 wsNeighborClientDiscoveryReason OBJECT-TYPE
     SYNTAX       BITS {
                    none(0),
                    rfscan-discovered(1),
                    neighbor-ap-associated(2),
                    current-ap-associated(3),
                    probe-request-discovered(4),
                    peer-ap-associated(5),
                    ad-hoc-rogue(6)
                  }
     MAX-ACCESS   read-only
     STATUS       current
     DESCRIPTION
        "Indicates discovery methods for the neighbor client."
     ::= { wsManagedAPNeighborClientListEntry 5 }

--
--   wsManagedAPVAPStatusTable
--
 wsManagedAPVAPStatusTable OBJECT-TYPE
     SYNTAX       SEQUENCE OF WsManagedAPVAPStatusEntry
     MAX-ACCESS   not-accessible
     STATUS       current
     DESCRIPTION
           "This table contains status parameters for each VAP
            configured on a radio interface for a WS managed AP."
     ::= { managedAP 9 }

    wsManagedAPVAPStatusEntry OBJECT-TYPE
     SYNTAX       WsManagedAPVAPStatusEntry
     MAX-ACCESS   not-accessible
     STATUS       current
     DESCRIPTION
          "Each entry in this table contains status parameters of each
           VAP configured on radio."
     INDEX    { wsManagedAPMacAddress, wsManagedAPRadioInterface,
                wsManagedVAPId }
     ::= { wsManagedAPVAPStatusTable 1 }

 WsManagedAPVAPStatusEntry ::=
     SEQUENCE {
      wsManagedVAPId                    Integer32,
      wsManagedVAPMacAddress            MacAddress,
      wsManagedVAPSSID                  DisplayString,
      wsManagedVAPAuthenticatedClients  Unsigned32
 }

 wsManagedVAPId OBJECT-TYPE
     SYNTAX       Integer32(0..7)
     MAX-ACCESS   read-only
     STATUS       current
     DESCRIPTION
        "Indicates VAP Id."
     ::= { wsManagedAPVAPStatusEntry 1 }

 wsManagedVAPMacAddress OBJECT-TYPE
     SYNTAX       MacAddress
     MAX-ACCESS   read-only
     STATUS       current
     DESCRIPTION
        "Indicates the ethernet address of the VAP MAC address."
     ::= { wsManagedAPVAPStatusEntry 2 }

 wsManagedVAPSSID OBJECT-TYPE
     SYNTAX       DisplayString(SIZE(1..32))
     MAX-ACCESS   read-only
     STATUS       current
     DESCRIPTION
        "Network assigned to a VAP MAC Address."
     ::= { wsManagedAPVAPStatusEntry 3 }

 wsManagedVAPAuthenticatedClients OBJECT-TYPE
     SYNTAX       Unsigned32
     MAX-ACCESS   read-only
     STATUS       current
     DESCRIPTION
        "Number of clients currently authenticated to VAP."
     ::= { wsManagedAPVAPStatusEntry 4 }

--
-- wsManagedAPVAPStatisticsTable
--
 wsManagedAPVAPStatisticsTable OBJECT-TYPE
     SYNTAX       SEQUENCE OF  WsManagedAPVAPStatisticsEntry
     MAX-ACCESS   not-accessible
     STATUS       current
     DESCRIPTION
         "This table contains statistics available for each VAP
          on the WS managed AP."
     ::= { managedAP 10 }

    wsManagedAPVAPStatisticsEntry OBJECT-TYPE
     SYNTAX       WsManagedAPVAPStatisticsEntry
     MAX-ACCESS   not-accessible
     STATUS       current
     DESCRIPTION
          "Each entry in this table contain statistics available for each
           VAP on the WS managed AP."
     AUGMENTS { wsManagedAPVAPStatusEntry }
     ::= { wsManagedAPVAPStatisticsTable 1 }

 WsManagedAPVAPStatisticsEntry ::=
     SEQUENCE {
      wsManagedVAPAssociationFailures       Counter32,
      wsManagedVAPAuthenticationFailures    Counter32,
      wsManagedVAPWLANPktsRecvd             Counter64,
      wsManagedVAPWLANBytesRecvd            Counter64,
      wsManagedVAPWLANPktsTransmitted       Counter64,
      wsManagedVAPWLANBytesTransmitted      Counter64,
      wsManagedVAPWLANPktsRecvDropped       Counter64,
      wsManagedVAPWLANBytesRecvDropped      Counter64,
      wsManagedVAPWLANPktsTransmitDropped   Counter64,
      wsManagedVAPWLANBytesTransmitDropped  Counter64
 }

    wsManagedVAPAssociationFailures    OBJECT-TYPE
         SYNTAX      Counter32
         MAX-ACCESS  read-only
         STATUS      current
         DESCRIPTION
            "Number of clients that have been denied association to the VAP."
         ::= { wsManagedAPVAPStatisticsEntry 1 }

    wsManagedVAPAuthenticationFailures    OBJECT-TYPE
         SYNTAX      Counter32
         MAX-ACCESS  read-only
         STATUS      current
         DESCRIPTION
            "Number of clients that have failed authentication to the VAP."
         ::= { wsManagedAPVAPStatisticsEntry 2 }

    wsManagedVAPWLANPktsRecvd    OBJECT-TYPE
         SYNTAX      Counter64
         MAX-ACCESS  read-only
         STATUS      current
         DESCRIPTION
            "Total packets received by an AP on this VAP."
         ::= { wsManagedAPVAPStatisticsEntry 3 }

    wsManagedVAPWLANBytesRecvd    OBJECT-TYPE
         SYNTAX      Counter64
         MAX-ACCESS  read-only
         STATUS      current
         DESCRIPTION
            "Total bytes received by an  AP on this VAP."
         ::= { wsManagedAPVAPStatisticsEntry 4 }

    wsManagedVAPWLANPktsTransmitted    OBJECT-TYPE
         SYNTAX      Counter64
         MAX-ACCESS  read-only
         STATUS      current
         DESCRIPTION
            "Total packets transmitted by an AP on this VAP."
         ::= { wsManagedAPVAPStatisticsEntry 5 }

    wsManagedVAPWLANBytesTransmitted    OBJECT-TYPE
         SYNTAX      Counter64
         MAX-ACCESS  read-only
         STATUS      current
         DESCRIPTION
            "Total bytes transmitted by an AP on this VAP."
         ::= { wsManagedAPVAPStatisticsEntry 6 }

    wsManagedVAPWLANPktsRecvDropped    OBJECT-TYPE
         SYNTAX      Counter64
         MAX-ACCESS  not-accessible
         STATUS      current
         DESCRIPTION
            "Total packets dropped in the receive direction by an AP on this VAP.
             This is due to client QoS actions affecting the wireless up (inbound)
             direction from AP to client."
         ::= { wsManagedAPVAPStatisticsEntry 7 }

    wsManagedVAPWLANBytesRecvDropped    OBJECT-TYPE
         SYNTAX      Counter64
         MAX-ACCESS  not-accessible
         STATUS      current
         DESCRIPTION
            "Total bytes dropped in the receive direction by an AP on this VAP.
             This is due to client QoS actions affecting the wireless up (inbound)
             direction from AP to client."
         ::= { wsManagedAPVAPStatisticsEntry 8 }

    wsManagedVAPWLANPktsTransmitDropped    OBJECT-TYPE
         SYNTAX      Counter64
         MAX-ACCESS  not-accessible
         STATUS      current
         DESCRIPTION
            "Total packets dropped in the transmit direction by an AP on this VAP.
             This is due to client QoS actions affecting the wireless down (outbound)
             direction from client to AP."
         ::= { wsManagedAPVAPStatisticsEntry 9 }

    wsManagedVAPWLANBytesTransmitDropped    OBJECT-TYPE
         SYNTAX      Counter64
         MAX-ACCESS  not-accessible
         STATUS      current
         DESCRIPTION
            "Total bytes dropped in the transmit direction by an AP on this VAP.
             This is due to client QoS actions affecting the wireless down (outbound)
             direction from client to AP."
         ::= { wsManagedAPVAPStatisticsEntry 10 }

 wsManagedAPResetAll OBJECT-TYPE
     SYNTAX       INTEGER {
                    enable(1),
                    disable(2)
                  }
     MAX-ACCESS   read-only
     STATUS       current
     DESCRIPTION
        "This is an action object. Setting this object to
         enable will reset all the managed APs.
         Read on this object will always return disable."
     ::= { managedAP 11 }
--
--   wsManagedAPRadioEligibleChannelListTable
--
 wsManagedAPRadioEligibleChannelListTable OBJECT-TYPE
     SYNTAX       SEQUENCE OF WsManagedAPRadioEligibleChannelListEntry
     MAX-ACCESS   not-accessible
     STATUS       current
     DESCRIPTION
         "This table represents eligible channel entries for an AP radio
          to consider for channel algorithm. It is based on country code,
          hardware capabilities and any configured channel limitations."
     ::= { managedAP 12 }

    wsManagedAPRadioEligibleChannelListEntry OBJECT-TYPE
     SYNTAX       WsManagedAPRadioEligibleChannelListEntry
     MAX-ACCESS   not-accessible
     STATUS       current
     DESCRIPTION
        "Each entry in this table represents eligible channel for an
         AP radio."
     INDEX    { wsManagedAPMacAddress, wsManagedAPRadioInterface,
                wsManagedAPRadioEligibleChannel}
     ::= { wsManagedAPRadioEligibleChannelListTable 1 }

 WsManagedAPRadioEligibleChannelListEntry ::=
     SEQUENCE {
      wsManagedAPRadioEligibleChannel                 Integer32,
      wsManagedAPRadioEligibleChannelRdrDetRequired   INTEGER,
      wsManagedAPRadioEligibleChannelRdrDetected      INTEGER,
      wsManagedAPRadioEligibleChannelLastRdrDetTime   DisplayString
 }

 wsManagedAPRadioEligibleChannel  OBJECT-TYPE
     SYNTAX       Integer32(1..64)
     MAX-ACCESS   read-only
     STATUS       current
     DESCRIPTION
         "Indicates list of supported channel by
          the managed ap. List contains one or
          more entries from 1-255, actual range
          is determined by physical mode and country code."
     ::= {wsManagedAPRadioEligibleChannelListEntry  1 }

 wsManagedAPRadioEligibleChannelRdrDetRequired OBJECT-TYPE
     SYNTAX       INTEGER {
                     yes(1),
                     no(2)
                  }
     MAX-ACCESS   read-only
     STATUS       current
     DESCRIPTION
         "This flag indicates if radar detection is enabled or not
          on this channel."
     ::= {wsManagedAPRadioEligibleChannelListEntry 2 }

 wsManagedAPRadioEligibleChannelRdrDetected OBJECT-TYPE
     SYNTAX       INTEGER {
                     yes(1),
                     no(2)
                  }
     MAX-ACCESS   read-only
     STATUS       current
     DESCRIPTION
         "This flag indicates if radar is detected or not
          on this channel."
     ::= {wsManagedAPRadioEligibleChannelListEntry 3 }

 wsManagedAPRadioEligibleChannelLastRdrDetTime OBJECT-TYPE
     SYNTAX       DisplayString
     MAX-ACCESS   read-only
     STATUS       current
     DESCRIPTION
        "Indicates the time in seconds since last radar was detected."
     ::= {wsManagedAPRadioEligibleChannelListEntry 4 }

--**************************************************************************************
-- associatedClient
--**************************************************************************************
--
--   wsAssociatedClientStatusTable
--

 wsAssociatedClientStatusTable OBJECT-TYPE
     SYNTAX       SEQUENCE OF WsAssociatedClientStatusEntry
     MAX-ACCESS   not-accessible
     STATUS       obsolete
     DESCRIPTION
           "This table contains status parameters of clients that are
            currently associated with managed APs."
     ::= { associatedClient 1 }

    wsAssociatedClientStatusEntry OBJECT-TYPE
     SYNTAX       WsAssociatedClientStatusEntry
     MAX-ACCESS   not-accessible
     STATUS       obsolete
     DESCRIPTION
          "Each entry in this table contain client status parameters
           assocaited with the WS managed AP."
     INDEX    { wsAssociatedClientMacAddress }
     ::= { wsAssociatedClientStatusTable 1 }

 WsAssociatedClientStatusEntry ::=
     SEQUENCE {
      wsAssociatedClientMacAddress                MacAddress,
      wsAssociatedClientTunnelIpAddress           IpAddress,
      wsAssociatedClientUserName                  DisplayString,
      wsAssociatedClientSSID                      DisplayString,
      wsAssociatedClientVLAN                      Integer32,
      wsAssociatedClientStatus                    INTEGER,
      wsAssociatedClientTxDataRate                Integer32,
      wsAssociatedClientInactivePeriod            TimeTicks,
      wsAssociatedClientDisassociateAction        INTEGER,
      wsAssociatedClientAge                       TimeTicks,
      wsAssociatedClientNwTime                    TimeTicks,
      wsAssociatedClientAssociatingSwitch         INTEGER,
      wsAssociatedClientSwitchMacAddress          MacAddress,
      wsAssociatedClientSwitchIpAddress           IpAddress,
      wsAssociatedClientDot11nCapable             INTEGER,
      wsAssociatedClientStbcCapable             INTEGER,
      wsAssociatedClientDistTunnelStatus          INTEGER,
      wsAssociatedClientDistTunnelRoamStatus      INTEGER,
      wsAssociatedClientDistTunnelHomeAPMac       MacAddress,
      wsAssociatedClientDistTunnelAssocAPMac      MacAddress,
      wsAssociatedClientAPMacAddress              MacAddress,
      wsAssociatedClientBSSID                     MacAddress,
      wsAssociatedClientRadioInterface            Integer32,
      wsAssociatedClientChannel                   Integer32,
      wsAssociatedClientIpAddress                 IpAddress,
      wsAssociatedClientNetBiosName               DisplayString,
      wsAssociatedClientRRMSupported              INTEGER,
      wsAssociatedClientRRMLocationReportSupported  INTEGER,
      wsAssociatedClientRRMBeaconTableMeasurementSupported  INTEGER,
      wsAssociatedClientRRMBeaconActiveMeasurementSupported  INTEGER,
      wsAssociatedClientRRMBeaconPassiveMeasurementSupported  INTEGER,
      wsAssociatedClientRRMChannelLoadMeasurementSupported  INTEGER
 }

 wsAssociatedClientMacAddress  OBJECT-TYPE
     SYNTAX       MacAddress
     MAX-ACCESS   read-only
     STATUS       obsolete
     DESCRIPTION
        "Associated client MAC address."
     ::= {wsAssociatedClientStatusEntry  1 }

 wsAssociatedClientTunnelIpAddress OBJECT-TYPE
     SYNTAX       IpAddress
     MAX-ACCESS   not-accessible
     STATUS       obsolete
     DESCRIPTION
        "Indicates network IP address of the client station, 0.0.0.0 indicates unknown.
         Tunnel IP subnet is present only for clients authenticated with tunneled VAPs."
     ::= {wsAssociatedClientStatusEntry  2 }

 wsAssociatedClientUserName OBJECT-TYPE
     SYNTAX       DisplayString(SIZE(0..32))
     MAX-ACCESS   read-only
     STATUS       obsolete
     DESCRIPTION
        "Indicates user name of the client that have authenticated via
         802.1x, clients on networks with other security modes will
         not have a user name."
     ::= { wsAssociatedClientStatusEntry 3 }

 wsAssociatedClientSSID OBJECT-TYPE
     SYNTAX       DisplayString(SIZE(0..32))
     MAX-ACCESS   read-only
     STATUS       obsolete
     DESCRIPTION
        "Indicates the network on which the client is connected."
     ::= { wsAssociatedClientStatusEntry 4 }

 wsAssociatedClientVLAN OBJECT-TYPE
     SYNTAX       Integer32(0..4094)
     MAX-ACCESS   read-only
     STATUS       obsolete
     DESCRIPTION
        "If client is on VAP using VLAN data forwarding mode,
         indicates obsolete assigned VLAN."
     ::= { wsAssociatedClientStatusEntry 5 }

 wsAssociatedClientStatus OBJECT-TYPE
     SYNTAX       INTEGER {
                       authenticated(1),
                       associated(2),
                       disassociated(3)
                  }
     MAX-ACCESS   read-only
     STATUS       obsolete
     DESCRIPTION
        "This object indicates client's status."
     ::= { wsAssociatedClientStatusEntry 6 }

 wsAssociatedClientTxDataRate OBJECT-TYPE
     SYNTAX       Integer32(2..1200)
     MAX-ACCESS   read-only
     STATUS       obsolete
     DESCRIPTION
       "Indicates the data rate, AP will actually support
        in setting up communications with client stations
        represented by a count from 2 - 1200, corresponding
        to data rates in multiples of 500 kbit/s from 1 Mbit/s
        to 600 Mbit/s.
        Supported Data Rate          Mbps
            2                          1
            4                          2
            11                         5.5
            12                         6
            18                         9 and so on. "
     ::= { wsAssociatedClientStatusEntry 7 }

 wsAssociatedClientInactivePeriod    OBJECT-TYPE
     SYNTAX      TimeTicks
     MAX-ACCESS  read-only
     STATUS      obsolete
     DESCRIPTION
         "For a current association, period of time that
          the AP has not seen any traffic for the client."
     ::= { wsAssociatedClientStatusEntry 8 }

 wsAssociatedClientDisassociateAction    OBJECT-TYPE
     SYNTAX      INTEGER {
                   none(1),
                   start(2)
                 }
     MAX-ACCESS  read-only
     STATUS      obsolete
     DESCRIPTION
        "This is an action object. Setting this object to start
         will initiate the disassociation of associated client.
         Read on this object will always return none."
     ::= { wsAssociatedClientStatusEntry 9 }

 wsAssociatedClientAge OBJECT-TYPE
     SYNTAX       TimeTicks
     MAX-ACCESS   read-only
     STATUS       obsolete
     DESCRIPTION
        "Indicates time since the controller has received new data for
         this client."
     ::= { wsAssociatedClientStatusEntry 10 }

 wsAssociatedClientAssociatingSwitch OBJECT-TYPE
     SYNTAX       INTEGER {
                    local-switch(1),
                    peer-switch(2)
                  }
     MAX-ACCESS   read-only
     STATUS       obsolete
     DESCRIPTION
        "This object indicates whether the client is associated
         to an AP managed by  this controller or peer-controller."
     ::= {wsAssociatedClientStatusEntry 11}

 wsAssociatedClientSwitchMacAddress  OBJECT-TYPE
     SYNTAX       MacAddress
     MAX-ACCESS   read-only
     STATUS       obsolete
     DESCRIPTION
        "MAC address of the WS associating the client."
     ::= {wsAssociatedClientStatusEntry 12}

 wsAssociatedClientSwitchIpAddress OBJECT-TYPE
     SYNTAX       IpAddress
     MAX-ACCESS   read-only
     STATUS       obsolete
     DESCRIPTION
        "IP address of the WS associating the client."
     ::= {wsAssociatedClientStatusEntry 13}

 wsAssociatedClientDot11nCapable OBJECT-TYPE
     SYNTAX       INTEGER {
                    yes(1),
                    no(2)
                  }
     MAX-ACCESS   read-only
     STATUS       obsolete
     DESCRIPTION
        "Flag indicating whether this client is capable of 802.11n operation."
     ::= {wsAssociatedClientStatusEntry 14}

 wsAssociatedClientStbcCapable OBJECT-TYPE
     SYNTAX       INTEGER {
                    yes(1),
                    no(2)
                  }
     MAX-ACCESS   not-accessible
     STATUS       obsolete
     DESCRIPTION
        "Flag indicating whether this client is capable of Space Time Block Code (STBC) operation."
     ::= {wsAssociatedClientStatusEntry 15}

 wsAssociatedClientDistTunnelStatus         OBJECT-TYPE
     SYNTAX     INTEGER{
                 enable(1),
                 disable(2)
                       }
     MAX-ACCESS        read-only
     STATUS            obsolete
     DESCRIPTION
         "Indicates whether L2 Distributed Tunneling is Enabled or Disabled"
     ::= {wsAssociatedClientStatusEntry   16 }


 wsAssociatedClientDistTunnelRoamStatus     OBJECT-TYPE
    SYNTAX     INTEGER{
                 associated(0),
                 home(1)
                      }
    MAX-ACCESS   read-only
    STATUS       obsolete
    DESCRIPTION
         "Indicates whether the client is using the distrubuted tunnel or not.
          Also indicates if it is a roamed client or not."
    ::= {wsAssociatedClientStatusEntry  17 }


 wsAssociatedClientDistTunnelHomeAPMac       OBJECT-TYPE
   SYNTAX          MacAddress
   MAX-ACCESS      read-only
   STATUS          obsolete
   DESCRIPTION
        "Indicates MAC Address of the client's Home AP. Here the client should be
         associated with the network on which the L2 Distributed Tunneling is enabled."
   ::= {wsAssociatedClientStatusEntry  18 }


 wsAssociatedClientDistTunnelAssocAPMac     OBJECT-TYPE
   SYNTAX          MacAddress
   MAX-ACCESS      read-only
   STATUS          obsolete
   DESCRIPTION
        "MAC Address of the client's Association AP to which the client has roamed to."
  ::= {wsAssociatedClientStatusEntry   19 }

 wsAssociatedClientAPMacAddress     OBJECT-TYPE
   SYNTAX          MacAddress
   MAX-ACCESS      read-only
   STATUS          obsolete
   DESCRIPTION
        "MAC Address of the AP to which client is Associated."
  ::= {wsAssociatedClientStatusEntry   20 }

 wsAssociatedClientBSSID     OBJECT-TYPE
   SYNTAX          MacAddress
   MAX-ACCESS      read-only
   STATUS          obsolete
   DESCRIPTION
        "BSSID of the VAP to which client is associated."
  ::= {wsAssociatedClientStatusEntry   21 }

 wsAssociatedClientRadioInterface  OBJECT-TYPE
     SYNTAX       Integer32(1..2)
     MAX-ACCESS   read-only
     STATUS       obsolete
     DESCRIPTION
         "Indicates the radio interface on which client is associated."
     ::= {wsAssociatedClientStatusEntry  22 }

 wsAssociatedClientChannel  OBJECT-TYPE
     SYNTAX       Integer32(1..165)
     MAX-ACCESS   read-only
     STATUS       obsolete
     DESCRIPTION
       "Indicates channel for associated client entry."
     ::= {wsAssociatedClientStatusEntry  23 }

 wsAssociatedClientNwTime OBJECT-TYPE
      SYNTAX       TimeTicks
      MAX-ACCESS   read-only
      STATUS       obsolete
      DESCRIPTION
          "Indicates time since this client first authenticated with
           the network."
      ::= { wsAssociatedClientStatusEntry 24 }

 wsAssociatedClientIpAddress OBJECT-TYPE
     SYNTAX       IpAddress
     MAX-ACCESS   read-only
     STATUS       obsolete
     DESCRIPTION
        "Indicates network IPv4 address of the client station detetecd through ARP snooping, 0.0.0.0 indicates unknown."
     ::= {wsAssociatedClientStatusEntry  25 }

 wsAssociatedClientNetBiosName OBJECT-TYPE
     SYNTAX       DisplayString(SIZE(0..15))
     MAX-ACCESS   read-only
     STATUS       obsolete
     DESCRIPTION
        "NetBios Name of the client."
     ::= { wsAssociatedClientStatusEntry 26 }

 wsAssociatedClientRRMSupported       OBJECT-TYPE
     SYNTAX     INTEGER{
                 enabled(1),
                 supported(2),
                 unsupported(3)
                       }
     MAX-ACCESS        not-accessible
     STATUS            obsolete
     DESCRIPTION
         "Indicates if the Radio Resource Management (RRM) portion of the
          IEEE 802.11k standard is supported by client and RRM is enabled is on
          the AP Profile.
          Value 2 indicates the client supports RRM portion and
          RRM Mode is not enabled on AP Profile.
          Value 3 indicates client doesnot support RRM "
     ::= {wsAssociatedClientStatusEntry   27 }

 wsAssociatedClientRRMLocationReportSupported       OBJECT-TYPE
     SYNTAX     INTEGER{
                 supported(1),
                 unsupported(2)
                       }
     MAX-ACCESS        not-accessible
     STATUS            obsolete
     DESCRIPTION
         "Indicates if the client can support RRM location report requests."
     ::= {wsAssociatedClientStatusEntry   28 }

 wsAssociatedClientRRMBeaconTableMeasurementSupported       OBJECT-TYPE
     SYNTAX     INTEGER{
                 supported(1),
                 unsupported(2)
                       }
     MAX-ACCESS        not-accessible
     STATUS            obsolete
     DESCRIPTION
         "Indicates if the client can detect APs via RRM beacon table reports."
     ::= {wsAssociatedClientStatusEntry   29 }

 wsAssociatedClientRRMBeaconActiveMeasurementSupported       OBJECT-TYPE
     SYNTAX     INTEGER{
                 supported(1),
                 unsupported(2)
                       }
     MAX-ACCESS        not-accessible
     STATUS            obsolete
     DESCRIPTION
         "Indicates if the client supports active scan capability."
     ::= {wsAssociatedClientStatusEntry   30 }

 wsAssociatedClientRRMBeaconPassiveMeasurementSupported       OBJECT-TYPE
     SYNTAX     INTEGER{
                 supported(1),
                 unsupported(2)
                       }
     MAX-ACCESS        not-accessible
     STATUS            obsolete
     DESCRIPTION
         "Indicates if the client supports passive scan capability."
     ::= {wsAssociatedClientStatusEntry   31 }

 wsAssociatedClientRRMChannelLoadMeasurementSupported       OBJECT-TYPE
     SYNTAX     INTEGER{
                 supported(1),
                 unsupported(2)
                       }
     MAX-ACCESS        not-accessible
     STATUS            obsolete
     DESCRIPTION
         "Indicates if the client supports RRM channel load measurement."
     ::= {wsAssociatedClientStatusEntry   32 }

--
-- wsAssociatedClientStatisticsTable
--
 wsAssociatedClientStatisticsTable OBJECT-TYPE
     SYNTAX       SEQUENCE OF  WsAssociatedClientStatisticsEntry
     MAX-ACCESS   not-accessible
     STATUS       obsolete
     DESCRIPTION
         "This table contains statistics available for each client
          associated to a WS managed AP."
     ::= { associatedClient 2 }

    wsAssociatedClientStatisticsEntry OBJECT-TYPE
     SYNTAX       WsAssociatedClientStatisticsEntry
     MAX-ACCESS   not-accessible
     STATUS       obsolete
     DESCRIPTION
          "Each entry in this table contain statistics available for each
           client associated a WS managed AP."
     AUGMENTS { wsAssociatedClientStatusEntry }
     ::= { wsAssociatedClientStatisticsTable 1 }

 WsAssociatedClientStatisticsEntry ::=
     SEQUENCE {
      wsAssociatedClientPktsRecvd                 Counter64,
      wsAssociatedClientBytesRecvd                Counter64,
      wsAssociatedClientPktsTransmitted           Counter64,
      wsAssociatedClientBytesTransmitted          Counter64,
      wsAssociatedClientDuplicatePktsRecvd        Counter32,
      wsAssociatedClientFragmentedPktsRecvd       Counter32,
      wsAssociatedClientFragmentedPktsTransmitted Counter32,
      wsAssociatedClientTransmitRetryCount        Counter32,
      wsAssociatedClientTransmitRetryFailedCount  Counter32,
      wsAssociatedClientPktsRecvDropped           Counter64,
      wsAssociatedClientBytesRecvDropped          Counter64,
      wsAssociatedClientPktsTransmitDropped       Counter64,
      wsAssociatedClientBytesTransmitDropped      Counter64,
      wsAssociatedClientTsViolatePktsRecvd        Counter32,
      wsAssociatedClientTsViolatePktsTransmitted  Counter32
 }

    wsAssociatedClientPktsRecvd    OBJECT-TYPE
         SYNTAX      Counter64
         MAX-ACCESS  read-only
         STATUS      obsolete
         DESCRIPTION
             "Total packets received by a managed AP from
              the client station."
         ::= { wsAssociatedClientStatisticsEntry 1 }

    wsAssociatedClientBytesRecvd    OBJECT-TYPE
         SYNTAX      Counter64
         MAX-ACCESS  read-only
         STATUS      obsolete
         DESCRIPTION
             "Total bytes received by a managed AP from the
              client station."
         ::= { wsAssociatedClientStatisticsEntry 2 }

    wsAssociatedClientPktsTransmitted    OBJECT-TYPE
         SYNTAX      Counter64
         MAX-ACCESS  read-only
         STATUS      obsolete
         DESCRIPTION
             "Total packets transmitted by a managed AP to
              the client station."
         ::= { wsAssociatedClientStatisticsEntry 3 }

    wsAssociatedClientBytesTransmitted    OBJECT-TYPE
         SYNTAX      Counter64
         MAX-ACCESS  read-only
         STATUS      obsolete
         DESCRIPTION
             "Total bytes transmitted by a managed AP to
              the client station."
         ::= { wsAssociatedClientStatisticsEntry 4 }

    wsAssociatedClientDuplicatePktsRecvd    OBJECT-TYPE
         SYNTAX      Counter32
         MAX-ACCESS  read-only
         STATUS      obsolete
         DESCRIPTION
             "Total duplicate packets received from the
              client station."
         ::= { wsAssociatedClientStatisticsEntry 5 }

    wsAssociatedClientFragmentedPktsRecvd    OBJECT-TYPE
         SYNTAX      Counter32
         MAX-ACCESS  read-only
         STATUS      obsolete
         DESCRIPTION
             "Total fragmented packets received from the
              client station."
         ::= { wsAssociatedClientStatisticsEntry 6 }

    wsAssociatedClientFragmentedPktsTransmitted    OBJECT-TYPE
         SYNTAX      Counter32
         MAX-ACCESS  read-only
         STATUS      obsolete
         DESCRIPTION
             "Total fragmented packets transmitted to
              the client station."
         ::= { wsAssociatedClientStatisticsEntry 7 }

    wsAssociatedClientTransmitRetryCount    OBJECT-TYPE
         SYNTAX      Counter32
         MAX-ACCESS  read-only
         STATUS      obsolete
         DESCRIPTION
             "Indicates number of times transmits to client station
              succeeded after one or more retries."
         ::= { wsAssociatedClientStatisticsEntry 8 }

    wsAssociatedClientTransmitRetryFailedCount    OBJECT-TYPE
         SYNTAX      Counter32
         MAX-ACCESS  read-only
         STATUS      obsolete
         DESCRIPTION
             "Number of times transmits to client station
              failed after one or more retries."
         ::= { wsAssociatedClientStatisticsEntry 9 }

    wsAssociatedClientPktsRecvDropped    OBJECT-TYPE
         SYNTAX      Counter64
         MAX-ACCESS  not-accessible
         STATUS      obsolete
         DESCRIPTION
             "Total packets dropped in the receive direction by a managed AP
              from the client station.  This is due to client QoS actions
              affecting the wireless up (inbound) direction from client to AP."
         ::= { wsAssociatedClientStatisticsEntry 10 }

    wsAssociatedClientBytesRecvDropped    OBJECT-TYPE
         SYNTAX      Counter64
         MAX-ACCESS  not-accessible
         STATUS      obsolete
         DESCRIPTION
             "Total bytes dropped in the receive direction by a managed AP
              from the client station.  This is due to client QoS actions
              affecting the wireless up (inbound) direction from client to AP."
         ::= { wsAssociatedClientStatisticsEntry 11 }

    wsAssociatedClientPktsTransmitDropped    OBJECT-TYPE
         SYNTAX      Counter64
         MAX-ACCESS  not-accessible
         STATUS      obsolete
         DESCRIPTION
             "Total packets dropped in the transmit direction by a managed AP
              to the client station.  This is due to client QoS actions
              affecting the wireless down (outbound) direction from AP to client."
         ::= { wsAssociatedClientStatisticsEntry 12 }

    wsAssociatedClientBytesTransmitDropped    OBJECT-TYPE
         SYNTAX      Counter64
         MAX-ACCESS  not-accessible
         STATUS      obsolete
         DESCRIPTION
             "Total bytes dropped in the transmit direction by a managed AP
              to the client station.  This is due to client QoS actions
              affecting the wireless down (outbound) direction from AP to client."
         ::= { wsAssociatedClientStatisticsEntry 13 }

    wsAssociatedClientTsViolatePktsRecvd    OBJECT-TYPE
         SYNTAX      Counter32
         MAX-ACCESS  not-accessible
         STATUS      obsolete
         DESCRIPTION
             "Number of packets received by the AP from a client station that are in excess
              of the client's alotted traffic stream (TS) uplink bandwidth, or are for an
              access category requiring admission control to which the client station
              has not been admitted."
         ::= { wsAssociatedClientStatisticsEntry 14 }

    wsAssociatedClientTsViolatePktsTransmitted    OBJECT-TYPE
         SYNTAX      Counter32
         MAX-ACCESS  not-accessible
         STATUS      obsolete
         DESCRIPTION
             "Number of packets transmitted by the AP to a client station that are in excess
              of the client's alotted traffic stream (TS) downlink bandwidth, or are for an
              access category requiring admission control to which the client station
              has not been admitted."
         ::= { wsAssociatedClientStatisticsEntry 15 }

--
--   wsAssociatedClientNeighborManagedAPStatusTable
--
  wsAssociatedClientNeighborManagedAPStatusTable OBJECT-TYPE
     SYNTAX       SEQUENCE OF WsAssociatedClientNeighborManagedAPStatusEntry
     MAX-ACCESS   not-accessible
     STATUS       obsolete
     DESCRIPTION
          "This table is maintained to lookup all WS managed APs
           detected, client can see in its RF area."
     ::= { associatedClient 3 }

    wsAssociatedClientNeighborManagedAPStatusEntry OBJECT-TYPE
     SYNTAX       WsAssociatedClientNeighborManagedAPStatusEntry
     MAX-ACCESS   not-accessible
     STATUS       obsolete
     DESCRIPTION
          "Each entry in this table contain WS managed APs that can
           be seen by client in its RF area."
     INDEX    { wsClientStationMacAddress,
                wsClientNeighborWSManagedAPMacAddress,
                wsClientNeighborWSManagedAPRadioInterface }
     ::= { wsAssociatedClientNeighborManagedAPStatusTable 1 }

 WsAssociatedClientNeighborManagedAPStatusEntry ::=
     SEQUENCE {
      wsClientStationMacAddress                 MacAddress,
      wsClientNeighborWSManagedAPMacAddress     MacAddress,
      wsClientNeighborWSManagedAPRadioInterface Integer32,
      wsClientStationDiscoveryReason            BITS
 }

 wsClientStationMacAddress  OBJECT-TYPE
     SYNTAX       MacAddress
     MAX-ACCESS   not-accessible
     STATUS       obsolete
     DESCRIPTION
       "The Ethernet address of a client station."
     ::= {wsAssociatedClientNeighborManagedAPStatusEntry  1 }

 wsClientNeighborWSManagedAPMacAddress  OBJECT-TYPE
     SYNTAX       MacAddress
     MAX-ACCESS   not-accessible
     STATUS       obsolete
     DESCRIPTION
       "The Ethernet address of a WS managed AP."
     ::= {wsAssociatedClientNeighborManagedAPStatusEntry  2 }

 wsClientNeighborWSManagedAPRadioInterface  OBJECT-TYPE
     SYNTAX       Integer32(1..2)
     MAX-ACCESS   not-accessible
     STATUS       obsolete
     DESCRIPTION
       "The radio interface of Managed AP."
     ::= {wsAssociatedClientNeighborManagedAPStatusEntry  3 }

wsClientStationDiscoveryReason  OBJECT-TYPE
    SYNTAX        BITS   {
                     none(0),
                     rfscan-discovered(1),
                     neighbor-ap-associated(2),
                     current-ap-associated(3),
                     probe-request-discovered(4),
                     ad-hoc-rogue(5),
                     associated-to-peer-ap(6)
                     }
    MAX-ACCESS   read-only
    STATUS       obsolete
    DESCRIPTION
      "Indicates the client status with respect to the
       Managed AP it is refering. One or more flags can
       be enabled at the same time."
    ::= {wsAssociatedClientNeighborManagedAPStatusEntry  4 }
--
--   wsVAPAssociatedClientStatusTable
--
  wsVAPAssociatedClientStatusTable OBJECT-TYPE
     SYNTAX       SEQUENCE OF WsVAPAssociatedClientStatusEntry
     MAX-ACCESS   not-accessible
     STATUS       obsolete
     DESCRIPTION
          " This table is maintained to lookup clients associated
            to a specific VAP on a WS managed AP."
     ::= { associatedClient 4 }

    wsVAPAssociatedClientStatusEntry OBJECT-TYPE
     SYNTAX       WsVAPAssociatedClientStatusEntry
     MAX-ACCESS   not-accessible
     STATUS       obsolete
     DESCRIPTION
          "Each entry in this table contain clients associated
           to each VAP."
     INDEX    { wsVAPMacAddress, wsVAPAssociatedClientMacAddress }
     ::= { wsVAPAssociatedClientStatusTable 1 }

 WsVAPAssociatedClientStatusEntry ::=
     SEQUENCE {
      wsVAPMacAddress                   MacAddress,
      wsVAPAssociatedClientMacAddress   MacAddress
 }

 wsVAPMacAddress  OBJECT-TYPE
     SYNTAX       MacAddress
     MAX-ACCESS   read-only
     STATUS       obsolete
     DESCRIPTION
       "The Ethernet address assigned to a VAP."
     ::= {wsVAPAssociatedClientStatusEntry  1 }

 wsVAPAssociatedClientMacAddress  OBJECT-TYPE
     SYNTAX       MacAddress
     MAX-ACCESS   read-only
     STATUS       obsolete
     DESCRIPTION
       "The Ethernet address of associated client station."
     ::= {wsVAPAssociatedClientStatusEntry  2 }

--
--   wsSSIDAssociatedClientStatusTable
--
  wsSSIDAssociatedClientStatusTable OBJECT-TYPE
     SYNTAX       SEQUENCE OF WsSSIDAssociatedClientStatusEntry
     MAX-ACCESS   not-accessible
     STATUS       obsolete
     DESCRIPTION
          " This table is maintained to lookup all clients
            associated to a particular network."
     ::= { associatedClient 5 }

    wsSSIDAssociatedClientStatusEntry OBJECT-TYPE
     SYNTAX       WsSSIDAssociatedClientStatusEntry
     MAX-ACCESS   not-accessible
     STATUS       obsolete
     DESCRIPTION
          "Each entry in this table contain clients
           associated to a particular network."
     INDEX    { wsSSIDAssociatedClientMacAddress }
     ::= { wsSSIDAssociatedClientStatusTable 1 }

 WsSSIDAssociatedClientStatusEntry ::=
     SEQUENCE {
      wsSSID                             DisplayString,
      wsSSIDAssociatedClientMacAddress   MacAddress
 }

 wsSSID  OBJECT-TYPE
     SYNTAX       DisplayString(SIZE(1..32))
     MAX-ACCESS   not-accessible
     STATUS       obsolete
     DESCRIPTION
       "Indicates the network on which the client is connected."
     ::= {wsSSIDAssociatedClientStatusEntry  1 }

 wsSSIDAssociatedClientMacAddress  OBJECT-TYPE
     SYNTAX       MacAddress
     MAX-ACCESS   read-only
     STATUS       obsolete
     DESCRIPTION
        "The Ethernet address of the client station."
     ::= {wsSSIDAssociatedClientStatusEntry  2 }


--
--   wsSwitchAssociatedClientStatusTable
--
  wsSwitchAssociatedClientStatusTable OBJECT-TYPE
     SYNTAX       SEQUENCE OF WsSwitchAssociatedClientStatusEntry
     MAX-ACCESS   not-accessible
     STATUS       obsolete
     DESCRIPTION
          " This table is maintained to lookup clients associated
            to the APs managed by the specific controller."
     ::= { associatedClient 6 }

    wsSwitchAssociatedClientStatusEntry OBJECT-TYPE
     SYNTAX       WsSwitchAssociatedClientStatusEntry
     MAX-ACCESS   not-accessible
     STATUS       obsolete
     DESCRIPTION
          "Each entry in this table contain client associated
           to each controller."
     INDEX    { wsSwitchIPAddress, wsSwitchAssociatedClientMacAddress }
     ::= { wsSwitchAssociatedClientStatusTable 1 }

 WsSwitchAssociatedClientStatusEntry ::=
     SEQUENCE {
      wsAssociatedClientSwitchIPAddress    IpAddress,
      wsSwitchAssociatedClientMacAddress   MacAddress
 }

 wsAssociatedClientSwitchIPAddress OBJECT-TYPE
     SYNTAX       IpAddress
     MAX-ACCESS   not-accessible
     STATUS       obsolete
     DESCRIPTION
        "IP address of the WS associating the client."
     ::= {wsSwitchAssociatedClientStatusEntry 1}

 wsSwitchAssociatedClientMacAddress  OBJECT-TYPE
     SYNTAX       MacAddress
     MAX-ACCESS   read-only
     STATUS       obsolete
     DESCRIPTION
       "Ethernet address of the associated client station."
     ::= {wsSwitchAssociatedClientStatusEntry  2 }


--
-- wsAssociatedClientQosStatusTable
--
 wsAssociatedClientQosStatusTable OBJECT-TYPE
     SYNTAX       SEQUENCE OF WsAssociatedClientQosStatusEntry
     MAX-ACCESS   not-accessible
     STATUS       obsolete
     DESCRIPTION
        "This table contains client QoS status parameters of clients that are
         currently associated with managed APs.  These objects represent the
         actual operational status values in effect for the clients."
      ::= { associatedClient 7 }

 wsAssociatedClientQosStatusEntry OBJECT-TYPE
     SYNTAX       WsAssociatedClientQosStatusEntry
     MAX-ACCESS   not-accessible
     STATUS       obsolete
     DESCRIPTION
         "Each entry in this table contains client QoS status parameters
          for a client associated with the WS managed AP."
     AUGMENTS { wsAssociatedClientStatusEntry }
     ::= { wsAssociatedClientQosStatusTable 1 }

 WsAssociatedClientQosStatusEntry ::=
     SEQUENCE {
         wsAssociatedClientQosBandwidthLimitDown         Unsigned32,
         wsAssociatedClientQosBandwidthLimitUp           Unsigned32,
         wsAssociatedClientQosAccessControlDownType      INTEGER,
         wsAssociatedClientQosAccessControlDownName      DisplayString,
         wsAssociatedClientQosAccessControlUpType        INTEGER,
         wsAssociatedClientQosAccessControlUpName        DisplayString,
         wsAssociatedClientQosDiffservPolicyDownType     INTEGER,
         wsAssociatedClientQosDiffservPolicyDownName     DisplayString,
         wsAssociatedClientQosDiffservPolicyUpType       INTEGER,
         wsAssociatedClientQosDiffservPolicyUpName       DisplayString,
         wsAssociatedClientQosOperStatus                 INTEGER
     }

 wsAssociatedClientQosBandwidthLimitDown OBJECT-TYPE
      SYNTAX      Unsigned32
      MAX-ACCESS  not-accessible
      STATUS      obsolete
      DESCRIPTION
               "Maximum bandwidth rate allowed for the wireless down (outbound)
                direction from AP to client, thus controlling the maximum
                receive rate from the AP for this wireless client.  This
                parameter is specified in bits-per-second (bps).

                The displayed value represents the actual bandwidth rate in use
                for the client, which may differ from the configured value since
                the AP rounds down to the nearest 64000 bps.  A value of 0 indicates
                bandwidth limiting is disabled in this direction for the client."
      ::= { wsAssociatedClientQosStatusEntry 1 }

 wsAssociatedClientQosBandwidthLimitUp OBJECT-TYPE
      SYNTAX      Unsigned32
      MAX-ACCESS  not-accessible
      STATUS      obsolete
      DESCRIPTION
               "Maximum bandwidth rate allowed for the wireless up (inbound)
                direction from client to AP, thus controlling the maximum
                send rate from this wireless client to the AP.  This
                parameter is specified in bits-per-second (bps).

                The displayed value represents the actual bandwidth rate in use
                for the client, which may differ from the configured value since
                the AP rounds down to the nearest 64000 bps.  A value of 0 indicates
                bandwidth limiting is disabled in this direction for the client."
      ::= { wsAssociatedClientQosStatusEntry 2 }

 wsAssociatedClientQosAccessControlDownType OBJECT-TYPE
     SYNTAX       INTEGER {
                    none(1),
                    ip(2),
                    mac(3),
                    ipv6(4)
                  }
     MAX-ACCESS   not-accessible
     STATUS       obsolete
     DESCRIPTION
        "Access list type used for the wireless down (outbound) direction from
         the AP to this client.  The wsAssociatedClientQosAccessControlDownName
         object identifies the access list."
     ::= { wsAssociatedClientQosStatusEntry 3 }

 wsAssociatedClientQosAccessControlDownName OBJECT-TYPE
     SYNTAX       DisplayString(SIZE(1..31))
     MAX-ACCESS   not-accessible
     STATUS       obsolete
     DESCRIPTION
       "Name of the access list in use in accordance with the
        wsAssociatedClientQosAccessControlDownType as follows:

        none(1) - This object is not displayed.

        ip(2)   - This specifies an IP access list number in the range
                  1-199, or an IP access list name as defined by the
                  aclName object in the aclTable in the FASTPATH-QOS-ACL-MIB.
        mac(3)  - This is an alphanumeric string from 1-31 characters, beginning
                  with a letter.  This must be a valid MAC access list name,
                  as defined by the aclMacName object in the FASTPATH-QOS-ACL-MIB.
        ipv6(4) - This is an alphanumeric string from 1-31 characters, beginning
                  with a letter.  This must be a valid IPV6 access list name,
                  as defined by the aclIpv6Name object in the FASTPATH-QOS-ACL-MIB.

        Note that numbered IP access lists are displayed here using a character
        string notation instead of an integer."
        ::= { wsAssociatedClientQosStatusEntry 4 }

 wsAssociatedClientQosAccessControlUpType OBJECT-TYPE
     SYNTAX       INTEGER {
                    none(1),
                    ip(2),
                    mac(3),
                    ipv6(4)
                  }
     MAX-ACCESS   not-accessible
     STATUS       obsolete
     DESCRIPTION
        "Access list type used for the wireless up (inbound) direction from
         this client to the AP.  The wsAssociatedClientQosAccessControlUpName
         object identifies the access list."
     ::= { wsAssociatedClientQosStatusEntry 5 }

 wsAssociatedClientQosAccessControlUpName OBJECT-TYPE
     SYNTAX       DisplayString(SIZE(1..31))
     MAX-ACCESS   not-accessible
     STATUS       obsolete
     DESCRIPTION
       "Name of the access list in use in accordance with the
        wsAssociatedClientQosAccessControlUpType as follows:

        none(1) - This object is not displayed.

        ip(2)   - This specifies an IP access list number in the range
                  1-199, or an IP access list name as defined by the
                  aclName object in the aclTable in the FASTPATH-QOS-ACL-MIB.

        Note that numbered IP access lists are displayed here using a character
        string notation instead of an integer."
        ::= { wsAssociatedClientQosStatusEntry 6 }

 wsAssociatedClientQosDiffservPolicyDownType OBJECT-TYPE
     SYNTAX       INTEGER {
                    none(1),
                    in(2)
                  }
     MAX-ACCESS   not-accessible
     STATUS       obsolete
     DESCRIPTION
        "DiffServ policy type used for the wireless down (outbound) direction from
         the AP to this client.  The wsAssociatedClientQosDiffservPolicyDownName
         object identifies the DiffServ policy."
     ::= { wsAssociatedClientQosStatusEntry 7 }

 wsAssociatedClientQosDiffservPolicyDownName OBJECT-TYPE
     SYNTAX       DisplayString(SIZE(1..31))
     MAX-ACCESS   not-accessible
     STATUS       obsolete
     DESCRIPTION
       "Name of the DiffServ policy in use in accordance with the
        wsAssociatedClientQosDiffservPolicyDownType as follows:

        none(1) - This object is not displayed.

        in(2)   - This specifies a DiffServ policy name, as defined by the
                  agentDiffServPolicyName object in the FASTPATH-QOS-DIFFSERV-PRIVATE-MIB.

        Note that only DiffServ policy defintions of type 'in' are supported for
        wireless client QoS operation."
        ::= { wsAssociatedClientQosStatusEntry 8 }

 wsAssociatedClientQosDiffservPolicyUpType OBJECT-TYPE
     SYNTAX       INTEGER {
                    none(1),
                    in(2)
                  }
     MAX-ACCESS   not-accessible
     STATUS       obsolete
     DESCRIPTION
        "DiffServ policy type used for the wireless up (inbound) direction from
         this client to the AP.  The wsAssociatedClientQosDiffservPolicyUpName
         object identifies the DiffServ policy."
     ::= { wsAssociatedClientQosStatusEntry 9 }

 wsAssociatedClientQosDiffservPolicyUpName OBJECT-TYPE
     SYNTAX       DisplayString(SIZE(1..31))
     MAX-ACCESS   not-accessible
     STATUS       obsolete
     DESCRIPTION
       "Name of the DiffServ policy in use in accordance with the
        wsAssociatedClientQosDiffservPolicyUpType as follows:

        none(1) - This object is not displayed.

        in(2)   - This specifies a DiffServ policy name, as defined by the
                  agentDiffServPolicyName object in the FASTPATH-QOS-DIFFSERV-PRIVATE-MIB.

        Note that only DiffServ policy defintions of type 'in' are supported for
        wireless client QoS operation."
        ::= { wsAssociatedClientQosStatusEntry 10 }


 wsAssociatedClientQosOperStatus OBJECT-TYPE
     SYNTAX        INTEGER {
                      enable(1),
                      disable(2)
                   }
     MAX-ACCESS   not-accessible
     STATUS       obsolete
     DESCRIPTION
        "Designates the AP quality-of-service operational status for
        this wireless client.  This represents the combined states of
        the wsApClientQosMode object and the wsNetworkClientQosMode
        object for the wireless network to which this client is associated."
     ::= { wsAssociatedClientQosStatusEntry 11 }

--
-- wsAssociatedClientSessionStatisticsTable
--
 wsAssociatedClientSessionStatisticsTable OBJECT-TYPE
     SYNTAX       SEQUENCE OF  WsAssociatedClientSessionStatisticsEntry
     MAX-ACCESS   not-accessible
     STATUS       obsolete
     DESCRIPTION
         "This table contains statistics available for each client
          associated to a WS managed AP, but accumulated for the duration
          of the entire WLAN session, inclusive of client roaming."
     ::= { associatedClient 8 }

    wsAssociatedClientSessionStatisticsEntry OBJECT-TYPE
     SYNTAX       WsAssociatedClientSessionStatisticsEntry
     MAX-ACCESS   not-accessible
     STATUS       obsolete
     DESCRIPTION
          "Each entry in this table contain statistics available for each
           client associated a WS managed AP, but accumulated for the duration
           of the entire WLAN session, inclusive of client roaming."
     AUGMENTS { wsAssociatedClientStatusEntry }
     ::= { wsAssociatedClientSessionStatisticsTable 1 }

 WsAssociatedClientSessionStatisticsEntry ::=
     SEQUENCE {
      wsAssociatedClientSessionPktsRecvd                 Counter64,
      wsAssociatedClientSessionBytesRecvd                Counter64,
      wsAssociatedClientSessionPktsTransmitted           Counter64,
      wsAssociatedClientSessionBytesTransmitted          Counter64,
      wsAssociatedClientSessionDuplicatePktsRecvd        Counter32,
      wsAssociatedClientSessionFragmentedPktsRecvd       Counter32,
      wsAssociatedClientSessionFragmentedPktsTransmitted Counter32,
      wsAssociatedClientSessionTransmitRetryCount        Counter32,
      wsAssociatedClientSessionTransmitRetryFailedCount  Counter32,
      wsAssociatedClientSessionPktsRecvDropped           Counter64,
      wsAssociatedClientSessionBytesRecvDropped          Counter64,
      wsAssociatedClientSessionPktsTransmitDropped       Counter64,
      wsAssociatedClientSessionBytesTransmitDropped      Counter64,
      wsAssociatedClientSessionTSViolatePktsRecvd        Counter32,
      wsAssociatedClientSessionTSViolatePktsTransmitted  Counter32
 }

    wsAssociatedClientSessionPktsRecvd    OBJECT-TYPE
         SYNTAX      Counter64
         MAX-ACCESS  read-only
         STATUS      obsolete
         DESCRIPTION
             "Total packets received by managed APs from the client station
              throughout the duration of the current WLAN session."
         ::= { wsAssociatedClientSessionStatisticsEntry 1 }

    wsAssociatedClientSessionBytesRecvd    OBJECT-TYPE
         SYNTAX      Counter64
         MAX-ACCESS  read-only
         STATUS      obsolete
         DESCRIPTION
             "Total bytes received by managed APs from the client station
              throughout the duration of the current WLAN session."
         ::= { wsAssociatedClientSessionStatisticsEntry 2 }

    wsAssociatedClientSessionPktsTransmitted    OBJECT-TYPE
         SYNTAX      Counter64
         MAX-ACCESS  read-only
         STATUS      obsolete
         DESCRIPTION
             "Total packets transmitted by managed APs to the client station
              throughout the duration of the current WLAN session."
         ::= { wsAssociatedClientSessionStatisticsEntry 3 }

    wsAssociatedClientSessionBytesTransmitted    OBJECT-TYPE
         SYNTAX      Counter64
         MAX-ACCESS  read-only
         STATUS      obsolete
         DESCRIPTION
             "Total bytes transmitted by managed APs to the client station
              throughout the duration of the current WLAN session."
         ::= { wsAssociatedClientSessionStatisticsEntry 4 }

    wsAssociatedClientSessionDuplicatePktsRecvd    OBJECT-TYPE
         SYNTAX      Counter32
         MAX-ACCESS  read-only
         STATUS      obsolete
         DESCRIPTION
             "Total duplicate packets received from the client station
              throughout the duration of the current WLAN session."
         ::= { wsAssociatedClientSessionStatisticsEntry 5 }

    wsAssociatedClientSessionFragmentedPktsRecvd    OBJECT-TYPE
         SYNTAX      Counter32
         MAX-ACCESS  read-only
         STATUS      obsolete
         DESCRIPTION
             "Total fragmented packets received from the client station.
              throughout the duration of the current WLAN session."
         ::= { wsAssociatedClientSessionStatisticsEntry 6 }

    wsAssociatedClientSessionFragmentedPktsTransmitted    OBJECT-TYPE
         SYNTAX      Counter32
         MAX-ACCESS  read-only
         STATUS      obsolete
         DESCRIPTION
             "Total fragmented packets transmitted to the client station
              throughout the duration of the current WLAN session."
         ::= { wsAssociatedClientSessionStatisticsEntry 7 }

    wsAssociatedClientSessionTransmitRetryCount    OBJECT-TYPE
         SYNTAX      Counter32
         MAX-ACCESS  read-only
         STATUS      obsolete
         DESCRIPTION
             "Indicates number of times transmits to client station
              succeeded after one or more retries throughout the
              duration of the current WLAN session."
         ::= { wsAssociatedClientSessionStatisticsEntry 8 }

    wsAssociatedClientSessionTransmitRetryFailedCount    OBJECT-TYPE
         SYNTAX      Counter32
         MAX-ACCESS  read-only
         STATUS      obsolete
         DESCRIPTION
             "Number of times transmits to client station
              failed after one or more retries throughout the
              duration of the current WLAN session."
         ::= { wsAssociatedClientSessionStatisticsEntry 9 }

    wsAssociatedClientSessionPktsRecvDropped    OBJECT-TYPE
         SYNTAX      Counter64
         MAX-ACCESS  not-accessible
         STATUS      obsolete
         DESCRIPTION
             "Total packets dropped in the receive direction by managed APs
              from the client station throughout the duration of the current
              WLAN session.  This is due to client QoS actions affecting the
              wireless up (inbound) direction from client to AP."
         ::= { wsAssociatedClientSessionStatisticsEntry 10 }

    wsAssociatedClientSessionBytesRecvDropped    OBJECT-TYPE
         SYNTAX      Counter64
         MAX-ACCESS  not-accessible
         STATUS      obsolete
         DESCRIPTION
             "Total bytes dropped in the receive direction by managed APs
              from the client station throughout the duration of the current
              WLAN session.  This is due to client QoS actions affecting the
              wireless up (inbound) direction from client to AP."
         ::= { wsAssociatedClientSessionStatisticsEntry 11 }

    wsAssociatedClientSessionPktsTransmitDropped    OBJECT-TYPE
         SYNTAX      Counter64
         MAX-ACCESS  not-accessible
         STATUS      obsolete
         DESCRIPTION
             "Total packets dropped in the transmit direction by managed APs
              to the client station throughout the duration of the current
              WLAN session.  This is due to client QoS actions affecting the
              wireless down (outbound) direction from AP to client."
         ::= { wsAssociatedClientSessionStatisticsEntry 12 }

    wsAssociatedClientSessionBytesTransmitDropped    OBJECT-TYPE
         SYNTAX      Counter64
         MAX-ACCESS  not-accessible
         STATUS      obsolete
         DESCRIPTION
             "Total bytes dropped in the transmit direction by managed APs
              to the client station throughout the duration of the current
              WLAN session.  This is due to client QoS actions affecting the
              wireless down (outbound) direction from AP to client."
         ::= { wsAssociatedClientSessionStatisticsEntry 13 }

    wsAssociatedClientSessionTSViolatePktsRecvd    OBJECT-TYPE
         SYNTAX      Counter32
         MAX-ACCESS  not-accessible
         STATUS      obsolete
         DESCRIPTION
             "Number of packets received by managed APs from a client station
              throughout the duration of the current WLAN session that are in excess
              of the client's alotted traffic stream (TS) uplink bandwidth, or are for an
              access category requiring admission control to which the client station
              has not been admitted."
         ::= { wsAssociatedClientSessionStatisticsEntry 14 }

    wsAssociatedClientSessionTSViolatePktsTransmitted    OBJECT-TYPE
         SYNTAX      Counter32
         MAX-ACCESS  not-accessible
         STATUS      obsolete
         DESCRIPTION
             "Number of packets transmitted by managed APs to a client station
              throughout the duration of the current WLAN session that are in excess
              of the client's alotted traffic stream (TS) downlink bandwidth, or are for an
              access category requiring admission control to which the client station
              has not been admitted."
         ::= { wsAssociatedClientSessionStatisticsEntry 15 }

--
-- wsAssociatedClientQosCachedStatusTable
--
 wsAssociatedClientQosCachedStatusTable OBJECT-TYPE
     SYNTAX       SEQUENCE OF WsAssociatedClientQosCachedStatusEntry
     MAX-ACCESS   not-accessible
     STATUS       obsolete
     DESCRIPTION
        "This table contains cached client QoS status parameters of clients that are
         currently associated with managed APs.  These objects represent values
         that were retrieved from a RADIUS server for this client.  See the
         wsAssociatedClientQosStatusTable for the current set of operational
         values in use for this client."
      ::= { associatedClient 9 }

 wsAssociatedClientQosCachedStatusEntry OBJECT-TYPE
     SYNTAX       WsAssociatedClientQosCachedStatusEntry
     MAX-ACCESS   not-accessible
     STATUS       obsolete
     DESCRIPTION
         "Each entry in this table contains client QoS cached status parameters
          for a client associated with the WS managed AP.  Only those parameters
          successfully retrieved from a RADIUS server via 802.1X authentication
          on behalf of a wireless client are displayed."
     AUGMENTS { wsAssociatedClientStatusEntry }
     ::= { wsAssociatedClientQosCachedStatusTable 1 }

 WsAssociatedClientQosCachedStatusEntry ::=
     SEQUENCE {
         wsAssociatedClientQosCachedBandwidthLimitDown         Unsigned32,
         wsAssociatedClientQosCachedBandwidthLimitUp           Unsigned32,
         wsAssociatedClientQosCachedAccessControlDownType      INTEGER,
         wsAssociatedClientQosCachedAccessControlDownName      DisplayString,
         wsAssociatedClientQosCachedAccessControlUpType        INTEGER,
         wsAssociatedClientQosCachedAccessControlUpName        DisplayString,
         wsAssociatedClientQosCachedDiffservPolicyDownType     INTEGER,
         wsAssociatedClientQosCachedDiffservPolicyDownName     DisplayString,
         wsAssociatedClientQosCachedDiffservPolicyUpType       INTEGER,
         wsAssociatedClientQosCachedDiffservPolicyUpName       DisplayString
     }

 wsAssociatedClientQosCachedBandwidthLimitDown OBJECT-TYPE
      SYNTAX      Unsigned32
      MAX-ACCESS  not-accessible
      STATUS      obsolete
      DESCRIPTION
          "Maximum bandwidth rate allowed for the wireless down (outbound)
           direction from AP to client, thus controlling the maximum
           receive rate from the AP for this wireless client.  This
           parameter is specified in bits-per-second (bps).

           A value of 0 indicates bandwidth limiting is disabled in this
           direction for the client."
      ::= { wsAssociatedClientQosCachedStatusEntry 1 }

 wsAssociatedClientQosCachedBandwidthLimitUp OBJECT-TYPE
      SYNTAX      Unsigned32
      MAX-ACCESS  not-accessible
      STATUS      obsolete
      DESCRIPTION
          "Maximum bandwidth rate allowed for the wireless up (inbound)
           direction from client to AP, thus controlling the maximum
           send rate from this wireless client to the AP.  This
           parameter is specified in bits-per-second (bps).

           A value of 0 indicates bandwidth limiting is disabled in this
           direction for the client."
      ::= { wsAssociatedClientQosCachedStatusEntry 2 }

 wsAssociatedClientQosCachedAccessControlDownType OBJECT-TYPE
     SYNTAX       INTEGER {
                    none(1),
                    ip(2),
                    mac(3),
                    ipv6(4)
                  }
     MAX-ACCESS   not-accessible
     STATUS       obsolete
     DESCRIPTION
        "Access list type used for the wireless down (outbound) direction from
         the AP to this client.  The wsAssociatedClientQosCachedAccessControlDownName
         object identifies the access list."
     ::= { wsAssociatedClientQosCachedStatusEntry 3 }

 wsAssociatedClientQosCachedAccessControlDownName OBJECT-TYPE
     SYNTAX       DisplayString(SIZE(1..31))
     MAX-ACCESS   not-accessible
     STATUS       obsolete
     DESCRIPTION
       "Name of the access list in use in accordance with the
        wsAssociatedClientQosCachedAccessControlDownType as follows:

        none(1) - This object is not displayed.

        ip(2)   - This specifies an IP access list number in the range
                  1-199, or an IP access list name as defined by the
                  aclName object in the aclTable in the FASTPATH-QOS-ACL-MIB.
        mac(3)  - This is an alphanumeric string from 1-31 characters, beginning
                  with a letter.  This must be a valid MAC access list name,
                  as defined by the aclMacName object in the FASTPATH-QOS-ACL-MIB.
        ipv6(4) - This is an alphanumeric string from 1-31 characters, beginning
                  with a letter.  This must be a valid IPV6 access list name,
                  as defined by the aclIpv6Name object in the FASTPATH-QOS-ACL-MIB.

        Note that numbered IP access lists are displayed here using a character
        string notation instead of an integer."
        ::= { wsAssociatedClientQosCachedStatusEntry 4 }

 wsAssociatedClientQosCachedAccessControlUpType OBJECT-TYPE
     SYNTAX       INTEGER {
                    none(1),
                    ip(2),
                    mac(3),
                    ipv6(4)
                  }
     MAX-ACCESS   not-accessible
     STATUS       obsolete
     DESCRIPTION
        "Access list type used for the wireless up (inbound) direction from
         this client to the AP.  The wsAssociatedClientQosCachedAccessControlUpName
         object identifies the access list."
     ::= { wsAssociatedClientQosCachedStatusEntry 5 }

 wsAssociatedClientQosCachedAccessControlUpName OBJECT-TYPE
     SYNTAX       DisplayString(SIZE(1..31))
     MAX-ACCESS   not-accessible
     STATUS       obsolete
     DESCRIPTION
       "Name of the access list in use in accordance with the
        wsAssociatedClientQosCachedAccessControlUpType as follows:

        none(1) - This object is not displayed.

        ip(2)   - This specifies an IP access list number in the range
                  1-199, or an IP access list name as defined by the
                  aclName object in the aclTable in the FASTPATH-QOS-ACL-MIB.
        mac(3)  - This is an alphanumeric string from 1-31 characters, beginning
                  with a letter.  This must be a valid MAC access list name,
                  as defined by the aclMacName object in the FASTPATH-QOS-ACL-MIB.
        ipv6(4) - This is an alphanumeric string from 1-31 characters, beginning
                  with a letter.  This must be a valid IPV6 access list name,
                  as defined by the aclIpv6Name object in the FASTPATH-QOS-ACL-MIB.

        Note that numbered IP access lists are displayed here using a character
        string notation instead of an integer."
        ::= { wsAssociatedClientQosCachedStatusEntry 6 }

 wsAssociatedClientQosCachedDiffservPolicyDownType OBJECT-TYPE
     SYNTAX       INTEGER {
                    none(1),
                    in(2)
                  }
     MAX-ACCESS   not-accessible
     STATUS       obsolete
     DESCRIPTION
        "DiffServ policy type used for the wireless down (outbound) direction from
         the AP to this client.  The wsAssociatedClientQosCachedDiffservPolicyDownName
         object identifies the DiffServ policy."
     ::= { wsAssociatedClientQosCachedStatusEntry 7 }

 wsAssociatedClientQosCachedDiffservPolicyDownName OBJECT-TYPE
     SYNTAX       DisplayString(SIZE(1..31))
     MAX-ACCESS   not-accessible
     STATUS       obsolete
     DESCRIPTION
       "Name of the DiffServ policy in use in accordance with the
        wsAssociatedClientQosCachedDiffservPolicyDownType as follows:

        none(1) - This object is not displayed.

        in(2)   - This specifies a DiffServ policy name, as defined by the
                  agentDiffServPolicyName object in the FASTPATH-QOS-DIFFSERV-PRIVATE-MIB.

        Note that only DiffServ policy defintions of type 'in' are supported for
        wireless client QoS operation."
        ::= { wsAssociatedClientQosCachedStatusEntry 8 }

 wsAssociatedClientQosCachedDiffservPolicyUpType OBJECT-TYPE
     SYNTAX       INTEGER {
                    none(1),
                    in(2)
                  }
     MAX-ACCESS   not-accessible
     STATUS       obsolete
     DESCRIPTION
        "DiffServ policy type used for the wireless up (inbound) direction from
         this client to the AP.  The wsAssociatedClientQosCachedDiffservPolicyUpName
         object identifies the DiffServ policy."
     ::= { wsAssociatedClientQosCachedStatusEntry 9 }

 wsAssociatedClientQosCachedDiffservPolicyUpName OBJECT-TYPE
     SYNTAX       DisplayString(SIZE(1..31))
     MAX-ACCESS   not-accessible
     STATUS       obsolete
     DESCRIPTION
       "Name of the DiffServ policy in use in accordance with the
        wsAssociatedClientQosCachedDiffservPolicyUpType as follows:

        none(1) - This object is not displayed.

        in(2)   - This specifies a DiffServ policy name, as defined by the
                  agentDiffServPolicyName object in the FASTPATH-QOS-DIFFSERV-PRIVATE-MIB.

        Note that only DiffServ policy defintions of type 'in' are supported for
        wireless client QoS operation."
        ::= { wsAssociatedClientQosCachedStatusEntry 10 }



--**************************************************************************************
-- peerSwitch
--**************************************************************************************
--
-- wsPeerStatusTable
-- Table not supported in SMB builds
--
 wsPeerStatusTable OBJECT-TYPE
     SYNTAX       SEQUENCE OF WsPeerStatusEntry
     MAX-ACCESS   not-accessible
     STATUS       current
     DESCRIPTION
           "This table contain status parameters of peer controllers of wireless controller."
     ::= { peerSwitch 1 }

 wsPeerStatusEntry OBJECT-TYPE
     SYNTAX       WsPeerStatusEntry
     MAX-ACCESS   not-accessible
     STATUS       current
     DESCRIPTION
           "Each entry describes the status parameters of each peer of
           wireless controller."
     INDEX    { wsPeerIpAddress }
     ::= { wsPeerStatusTable 1 }

 WsPeerStatusEntry ::=
     SEQUENCE {
         wsPeerIpAddress                    IpAddress,
         wsPeerClusterControllerIndicator   INTEGER,
         wsPeerTotalPeerSwitches            Integer32,
         wsPeerVendorId                     Integer32,
         wsPeerProtocolVersion              Integer32,
         wsPeerSoftwareVersion              DisplayString,
         wsPeerDiscoveryReason              INTEGER,
         wsPeerAge                          TimeTicks,
         wsPeerManagedAPCount               INTEGER,
         wsPeerConfigRequestAction          INTEGER,
         wsPeerConfigRequestStatus          INTEGER,
         wsPeerConfigSwitchIp               IpAddress,
         wsPeerConfigReceived               BITS,
         wsPeerConfigReceivedTimestamp      DisplayString
 }

 wsPeerIpAddress OBJECT-TYPE
     SYNTAX       IpAddress
     MAX-ACCESS   read-only
     STATUS       current
     DESCRIPTION
        "IP address of the peer controller."
     ::= { wsPeerStatusEntry 1 }

 wsPeerClusterControllerIndicator OBJECT-TYPE
    SYNTAX        INTEGER {
                  yes(1),
                  no(2)
                  }
     MAX-ACCESS   read-only
     STATUS       current
     DESCRIPTION
        "Indicates if the peer controller is currently the Cluster Controller of the peer group or not."
     ::= { wsPeerStatusEntry 2 }

 wsPeerTotalPeerSwitches OBJECT-TYPE
     SYNTAX       Integer32(0..4)
     MAX-ACCESS   read-only
     STATUS       current
     DESCRIPTION
        "Total number of peer controllers detected on the network."
     ::= { wsPeerStatusEntry 3 }

 wsPeerVendorId OBJECT-TYPE
     SYNTAX       Integer32
     MAX-ACCESS   read-only
     STATUS       current
     DESCRIPTION
        "Indicates vendor of peer controller software."
     DEFVAL  { 0 }
     ::= { wsPeerStatusEntry 4 }

 wsPeerProtocolVersion OBJECT-TYPE
     SYNTAX       Integer32
     MAX-ACCESS    read-only
     STATUS       current
     DESCRIPTION
        "Indicates software version of peer controller."
     DEFVAL  { 0 }
     ::= { wsPeerStatusEntry 5 }

 wsPeerSoftwareVersion OBJECT-TYPE
     SYNTAX       DisplayString(SIZE(0..32))
     MAX-ACCESS   read-only
     STATUS       current
     DESCRIPTION
         "Indicates the protocol version of software on the peer
          controller."
     ::= { wsPeerStatusEntry 6 }

 wsPeerDiscoveryReason OBJECT-TYPE
     SYNTAX       INTEGER {
                    ip-poll(1),
                    l2-poll(2)
                  }
     MAX-ACCESS   read-only
     STATUS       current
     DESCRIPTION
         "Indicates the discovery method of peer controller."
     ::= { wsPeerStatusEntry 7 }

 wsPeerAge OBJECT-TYPE
     SYNTAX       TimeTicks
     MAX-ACCESS   read-only
     STATUS       current
     DESCRIPTION
        "Indicates time in seconds since last communication with the controller."
     ::= { wsPeerStatusEntry 8 }

 wsPeerManagedAPCount OBJECT-TYPE
     SYNTAX       INTEGER (0..192)
     MAX-ACCESS   read-only
     STATUS       current
     DESCRIPTION
        "Number of APs in the peer managed AP database that are authenticated,
         configured, and have an active connection with the wireless controller. "
     DEFVAL      { 0 }
     ::= { wsPeerStatusEntry 9 }

--
-- Peer Controller Config Push Status Parameters
--

 wsPeerConfigRequestAction    OBJECT-TYPE
         SYNTAX      INTEGER {
                       none(1),
                       start(2)
                     }
         MAX-ACCESS  read-only
         STATUS      current
         DESCRIPTION
             "This action object is used to:
                - start - Start the config push into the peer controller.
                - Read on this object will always return none."
         DEFVAL      { none }
         ::= { wsPeerStatusEntry 10 }

 wsPeerConfigRequestStatus    OBJECT-TYPE
     SYNTAX      INTEGER {
                    notStarted(0),
                    requested(1),
                    inProgress(2),
                    invalidCodeVersion(3),
                    invalidHwVersion(4),
                    operationInProgress(5),
                    invalidConfig(6),
                    invalidPacketFormat(7),
                    failureTimeout(8),
                    failureGeneric(9),
                    success(10)
                    }
     MAX-ACCESS  read-only
     STATUS      current
     DESCRIPTION
        "The status for the configuration push operation to this peer controller."
     DEFVAL      { notStarted }
         ::= { wsPeerStatusEntry 11 }

 wsPeerConfigSwitchIp    OBJECT-TYPE
     SYNTAX      IpAddress
     MAX-ACCESS  read-only
     STATUS      current
     DESCRIPTION
        "IP Address of the last controller from which this controller received
         any wireless configuration data."
     ::= { wsPeerStatusEntry 12 }

wsPeerConfigReceived    OBJECT-TYPE
     SYNTAX      BITS  {
                   none (1),
                   globalConfig(2),
                   discoveryConfig(3),
                   validAPDatabase(4),
                   channelPowerConfig(5),
                   profileNetworkConfig(6),
                   knownClientConfig(7),
                   captivePortalConfig(8),
                   radiusClientConfig(9),
                   qosAclConfig(10),
                   qosDiffServConfig(11),
                   wdsGroupConfig(12),
                   deviceLocationConfig(13)
                   }
     MAX-ACCESS  read-only
     STATUS      current
     DESCRIPTION
        "Indicates which portions of configuration were last received from a
         peer controller. The combination of configurations are denoted by doing
         'AND' of the values.BIT zero is ignored.

         Ex: Value 9 specifies only bit 2 and 5 are set, So it denotes
             channelPowerConfig and globalConfig received"
      ::= { wsPeerStatusEntry 13 }

wsPeerConfigReceivedTimestamp    OBJECT-TYPE
     SYNTAX      DisplayString
     MAX-ACCESS  read-only
     STATUS      current
     DESCRIPTION
        "The last time this controller received any configuration data from a
         peer controller."
     ::= { wsPeerStatusEntry 14 }

--
-- wsPeerSwitchManagedAPTable
-- Table not supported in SMB builds
--
 wsPeerSwitchManagedAPTable OBJECT-TYPE
     SYNTAX       SEQUENCE OF WsPeerSwitchManagedAPEntry
     MAX-ACCESS   not-accessible
     STATUS       current
     DESCRIPTION
           "This table contain Managed AP database of the peer controllers of
           wireless controller."
     ::= { peerSwitch 3 }

 wsPeerSwitchManagedAPEntry     OBJECT-TYPE
     SYNTAX       WsPeerSwitchManagedAPEntry
     MAX-ACCESS   not-accessible
     STATUS       current
     DESCRIPTION
           "Each entry describes the Managed AP Entry of the peer of
           wireless controller."
     INDEX    { wsPeerSwitchIpAddress, wsPeerSwitchAPMacAddress }
     ::= { wsPeerSwitchManagedAPTable 1 }

 WsPeerSwitchManagedAPEntry ::=
     SEQUENCE {
         wsPeerSwitchIpAddress            IpAddress,
         wsPeerSwitchAPMacAddress         MacAddress,
         wsPeerSwitchAPLocation           DisplayString,
         wsPeerSwitchAPIPAddress          IpAddress,
         wsPeerSwitchAPProfileId          INTEGER ,
         wsPeerSwitchAPProfileName        DisplayString,
         wsPeerSwitchAPHardwareType       Integer32
     }

 wsPeerSwitchIpAddress OBJECT-TYPE
     SYNTAX       IpAddress
     MAX-ACCESS   read-only
     STATUS       current
     DESCRIPTION
         "The IP Address of the Peer controller."
     ::= { wsPeerSwitchManagedAPEntry 1 }

 wsPeerSwitchAPMacAddress OBJECT-TYPE
     SYNTAX       MacAddress
     MAX-ACCESS   read-only
     STATUS       current
     DESCRIPTION
         "The VAP0 MAC address of the AP managed by the peer controller."
     ::= { wsPeerSwitchManagedAPEntry 2 }

 wsPeerSwitchAPLocation OBJECT-TYPE
     SYNTAX       DisplayString(SIZE(0..32))
     MAX-ACCESS   read-only
     STATUS       current
     DESCRIPTION
        "This object indicates descriptive location of the managed AP by the
        peer controller."
     ::= { wsPeerSwitchManagedAPEntry 3 }

 wsPeerSwitchAPIPAddress OBJECT-TYPE
     SYNTAX       IpAddress
     MAX-ACCESS   read-only
     STATUS       current
     DESCRIPTION
        "IP address for the peer managed AP."
     ::= { wsPeerSwitchManagedAPEntry 4 }

 wsPeerSwitchAPProfileId OBJECT-TYPE
     SYNTAX       INTEGER (1..16)
     MAX-ACCESS   read-only
     STATUS       current
     DESCRIPTION
         "Unique ID for the peer managed AP's configuration profile."
     ::= { wsPeerSwitchManagedAPEntry 5 }

 wsPeerSwitchAPProfileName OBJECT-TYPE
     SYNTAX       DisplayString(SIZE(0..32))
     MAX-ACCESS   read-only
     STATUS       current
     DESCRIPTION
         "The descriptive name for the peer managed AP's configuration profile."
     ::= { wsPeerSwitchManagedAPEntry 6 }

 wsPeerSwitchAPHardwareType OBJECT-TYPE
     SYNTAX       Integer32
     MAX-ACCESS   not-accessible
     STATUS       current
     DESCRIPTION
         "The  Hardware platform for the AP.
          1 --> BROADCOM.  "
     ::= { wsPeerSwitchManagedAPEntry 7 }

--
-- peerSwitch group ends
--

--**************************************************************************************
-- intrusionDetection
--**************************************************************************************
--
--   wsRFScanAPStatusTable
--
  wsRFScanAPStatusTable OBJECT-TYPE
     SYNTAX       SEQUENCE OF WsRFScanAPStatusEntry
     MAX-ACCESS   not-accessible
     STATUS       current
     DESCRIPTION
          "This table is maintained with RF scan data received
           from the WS managed APs."
     ::= { intrusionDetection 1 }

    wsRFScanAPStatusEntry OBJECT-TYPE
     SYNTAX       WsRFScanAPStatusEntry
     MAX-ACCESS   not-accessible
     STATUS       current
     DESCRIPTION
          "Each entry in this table contain RF scan data received
           from the WS managed AP."
     INDEX    { wsRFScanAPMacAddress }
     ::= { wsRFScanAPStatusTable 1 }

 WsRFScanAPStatusEntry ::=
     SEQUENCE {
      wsRFScanAPMacAddress               MacAddress,
      wsRFScanAPRadioInterface           Integer32,
      wsRFScanAPBaseMacAddress           MacAddress,
      wsRFScanAPSSID                     DisplayString,
      wsRFScanAPPhysicalMode             INTEGER,
      wsRFScanAPChannel                  Integer32,
      wsRFScanAPTxRate                   DisplayString,
      wsRFScanAPBeaconInterval           Integer32,
      wsRFScanAPStatus                   INTEGER,
      wsRFScanAPDiscoveredAge            TimeTicks,
      wsRFScanAPAge                      TimeTicks,
      wsRFScanAPStatusInitial            INTEGER,
      wsRFScanAPSecurityMode             INTEGER,
      wsRFScanAPHighRate                 DisplayString,
      wsRFScanAPDot11nMode               INTEGER,
      wsRFScanAPAdHoc                    INTEGER,
      wsRFScanAPPeerManaged              INTEGER,
      wsRFScanAPRogueMitigation          INTEGER,
      wsRFScanAPAcknowledgeRogue         INTEGER,
      wsRFScanAPBSSID                    MacAddress,
      wsRFScanAPOUI                      DisplayString,
      wsRFScanAPRRMSupported             INTEGER,
      wsRFScanAPDot11acMode              INTEGER
 }

 wsRFScanAPMacAddress  OBJECT-TYPE
     SYNTAX       MacAddress
     MAX-ACCESS   read-only
     STATUS       current
     DESCRIPTION
       "The MAC address of the detected AP, this could be a
        physical radio interface or VAP MAC."
     ::= {wsRFScanAPStatusEntry  1 }

 wsRFScanAPRadioInterface  OBJECT-TYPE
     SYNTAX       Integer32(1..2)
     MAX-ACCESS   read-only
     STATUS       current
     DESCRIPTION
         "If status indicates a managed AP, this indicates the
         radio interface on the Detected AP, if the value is
         unknown (i.e. Rogue or third party APs) it is set to '0'."
     ::= {wsRFScanAPStatusEntry  2 }

 wsRFScanAPBaseMacAddress  OBJECT-TYPE
     SYNTAX       MacAddress
     MAX-ACCESS   read-only
     STATUS       current
     DESCRIPTION
         "If status indicates a managed AP, this indicates the
         base MAC address of the detected AP, If the value is
         unknown (i.e. Rogue of third party AP's) it is set to '0'. "
     ::= {wsRFScanAPStatusEntry  3 }

 wsRFScanAPSSID  OBJECT-TYPE
     SYNTAX       DisplayString(SIZE(1..32))
     MAX-ACCESS   read-only
     STATUS       current
     DESCRIPTION
       "Service Set Id of the detected network."
     ::= {wsRFScanAPStatusEntry  4 }

 wsRFScanAPPhysicalMode  OBJECT-TYPE
     SYNTAX       INTEGER {
                     ieee802dot11an(1),
                     ieee802dot11bORgn(2)
                  }
     MAX-ACCESS   read-only
     STATUS       current
     DESCRIPTION
       "Indicates the 802.11 mode being used on an AP."
     ::= {wsRFScanAPStatusEntry  5 }

 wsRFScanAPChannel  OBJECT-TYPE
     SYNTAX       Integer32(0..13|36|40|44|48|52|56|60|64)
     MAX-ACCESS   read-only
     STATUS       current
     DESCRIPTION
       "Indicates transmit channel of an AP."
     ::= {wsRFScanAPStatusEntry  6 }

 wsRFScanAPTxRate  OBJECT-TYPE
     SYNTAX       DisplayString
     MAX-ACCESS   read-only
     STATUS       current
     DESCRIPTION
       "Indicates the rate at which an AP is currently
        transmitting data, from 1 Mbit/s to 600 Mbit/s."
     ::= {wsRFScanAPStatusEntry  7 }

 wsRFScanAPBeaconInterval  OBJECT-TYPE
     SYNTAX       Integer32(20..2000)
     MAX-ACCESS   read-only
     STATUS       current
     DESCRIPTION
       "Indicates beacon interval for a neighbor AP network."
     ::= {wsRFScanAPStatusEntry  8 }

 wsRFScanAPStatus  OBJECT-TYPE
     SYNTAX       INTEGER {
                    managed(1),
                    unknown(2),
                    standalone(3),
                    rogue(4)
                  }
     MAX-ACCESS   read-only
     STATUS       current
     DESCRIPTION
       "Indicates the managed status of an AP."
     ::= {wsRFScanAPStatusEntry  9 }

 wsRFScanAPDiscoveredAge  OBJECT-TYPE
     SYNTAX       TimeTicks
     MAX-ACCESS   read-only
     STATUS       current
     DESCRIPTION
       "Indicates timestamp in seconds when an AP was first detected."
     ::= {wsRFScanAPStatusEntry  10 }

 wsRFScanAPAge  OBJECT-TYPE
     SYNTAX       TimeTicks
     MAX-ACCESS   read-only
     STATUS       current
     DESCRIPTION
       "Indicates time in seconds since an AP was last detected in the scan."
     ::= {wsRFScanAPStatusEntry  11 }

 wsRFScanAPStatusInitial  OBJECT-TYPE
     SYNTAX       INTEGER {
                    managed(1),
                    unknown(2),
                    standalone(3),
                    rogue(4)
                  }
     MAX-ACCESS   read-only
     STATUS       current
     DESCRIPTION
       "Indicates the initial status of an AP."
     ::= {wsRFScanAPStatusEntry  12 }

 wsRFScanAPSecurityMode  OBJECT-TYPE
     SYNTAX       INTEGER {
                    open(1),
                    wep(2),
                    wpa(3)
                  }
     MAX-ACCESS   read-only
     STATUS       current
     DESCRIPTION
       "Indicates the security mode of an AP."
     ::= {wsRFScanAPStatusEntry  13 }

 wsRFScanAPHighRate  OBJECT-TYPE
     SYNTAX       DisplayString
     MAX-ACCESS   read-only
     STATUS       current
     DESCRIPTION
       "Indicates the highest supported rate advertised by an AP in Mbps."
     ::= {wsRFScanAPStatusEntry  14 }

 wsRFScanAPDot11nMode  OBJECT-TYPE
     SYNTAX       INTEGER {
                    notsupported(0),
                    supported(1)
                  }
     MAX-ACCESS   read-only
     STATUS       current
     DESCRIPTION
       "Indicates whether 802.11n is supported by an AP."
     ::= {wsRFScanAPStatusEntry  15 }

 wsRFScanAPAdHoc  OBJECT-TYPE
     SYNTAX       INTEGER {
                    notadhoc(0),
                    adhoc(1)
                  }
     MAX-ACCESS   read-only
     STATUS       current
     DESCRIPTION
       "Indicates that the beacon frame was received from an ad hoc network for an AP."
     ::= {wsRFScanAPStatusEntry  16 }

 wsRFScanAPPeerManaged  OBJECT-TYPE
     SYNTAX       INTEGER {
                    localswitch(0),
                    peerswitch(1)
                  }
     MAX-ACCESS   read-only
     STATUS       current
     DESCRIPTION
       "Indicates that an AP is managed by a peer controller."
     ::= {wsRFScanAPStatusEntry  17 }

 wsRFScanAPRogueMitigation  OBJECT-TYPE
     SYNTAX       INTEGER {
                    notrogue(0),
                    inprogress(1),
                    attackdisabled(2),
                    toomany(3),
                    illegalchannel(4),
                    spoofing(5),
                    adhoc(6)
                  }
     MAX-ACCESS   read-only
     STATUS       current
     DESCRIPTION
       "Indicates whether rogue AP mitigation is in progress for an AP."
     ::= {wsRFScanAPStatusEntry  18 }

 wsRFScanAPAcknowledgeRogue OBJECT-TYPE
         SYNTAX      INTEGER {
                     no-action(0),
                     acknowledge(1)
                  }
         MAX-ACCESS  read-only
         STATUS      current
         DESCRIPTION
                     "This is a command that allows the administrator to restore
                      the initial status for this AP in the RF Scan database.
                      Read on this object will always return no-action."
     ::= { wsRFScanAPStatusEntry 19 }

 wsRFScanAPBSSID  OBJECT-TYPE
     SYNTAX       MacAddress
     MAX-ACCESS   read-only
     STATUS       current
     DESCRIPTION
         "BSSID advertised in the network."
     ::= {wsRFScanAPStatusEntry  20 }

wsRFScanAPOUI  OBJECT-TYPE
     SYNTAX       DisplayString(SIZE(1..32))
     MAX-ACCESS   read-only
     STATUS       current
     DESCRIPTION
       "Manufacturer information for this AP."
     ::= {wsRFScanAPStatusEntry  21 }

wsRFScanAPRRMSupported  OBJECT-TYPE
     SYNTAX       INTEGER {
                    unsupported(0),
                    supported(1)
                  }
     MAX-ACCESS   not-accessible
     STATUS       current
     DESCRIPTION
       "Advertised status of Radio Resource Management (RRM) capability."
     ::= {wsRFScanAPStatusEntry  22 }

wsRFScanAPDot11acMode  OBJECT-TYPE
     SYNTAX       INTEGER {
                    notsupported(0),
                    supported(1)
                  }
     MAX-ACCESS   read-only
     STATUS       current
     DESCRIPTION
       "Indicates whether 802.11ac is supported by an AP."
     ::= {wsRFScanAPStatusEntry  23 }

 wsRFScanAPEntriesPurge OBJECT-TYPE
     SYNTAX       INTEGER {
                    enable(1),
                    disable(2)
                  }
     MAX-ACCESS   read-only
     STATUS       current
     DESCRIPTION
        "This is an action object used to purge the RF scan entries
        present in the network. Read on this object will always return disable."
     ::= { intrusionDetection 2 }

--
--   wsFailureAPStatusTable
--
 wsFailureAPStatusTable OBJECT-TYPE
     SYNTAX       SEQUENCE OF WsFailureAPStatusEntry
     MAX-ACCESS   not-accessible
     STATUS       current
     DESCRIPTION
           "This table contain status parameters of APs
            that failed to authenticate, or associate with
            wireless controller."
     ::= { intrusionDetection 3 }

    wsFailureAPStatusEntry OBJECT-TYPE
     SYNTAX       WsFailureAPStatusEntry
     MAX-ACCESS   not-accessible
     STATUS       current
     DESCRIPTION
          "Each entry in this table contain status parameters of failed AP."
     INDEX    { wsFailedAPMacAddress }
     ::= { wsFailureAPStatusTable 1 }

 WsFailureAPStatusEntry ::=
     SEQUENCE {
      wsFailedAPMacAddress                  MacAddress,
      wsFailedAPIpAddress                   IpAddress,
      wsFailedAPVendorId                    INTEGER,
      wsFailedAPSoftwareVersion             DisplayString,
      wsFailedAPHWType                      INTEGER,
      wsFailedAPFailureType                 INTEGER,
      wsFailedAPValidationFailureCount      Unsigned32,
      wsFailedAPAuthenticationFailureCount  Unsigned32,
      wsFailedAPProtocolVersion             Integer32,
      wsFailedAPAge                         TimeTicks,
      wsFailedAPReportingSwitch             INTEGER,
      wsFailedAPSwitchMacAddress            MacAddress,
      wsFailedAPSwitchIpAddress             IpAddress
    }

 wsFailedAPMacAddress OBJECT-TYPE
     SYNTAX       MacAddress
     MAX-ACCESS   read-only
     STATUS       current
     DESCRIPTION
        "The Ethernet address of the failed AP."
     ::= { wsFailureAPStatusEntry 1 }

 wsFailedAPIpAddress OBJECT-TYPE
     SYNTAX       IpAddress
     MAX-ACCESS   read-only
     STATUS       current
     DESCRIPTION
        "The network IP address of the failed AP."
     ::= { wsFailureAPStatusEntry 2 }

 wsFailedAPVendorId OBJECT-TYPE
     SYNTAX       INTEGER {
                    broadcom(1),
                    others(65535)
                  }
     MAX-ACCESS   not-accessible
     STATUS       current
     DESCRIPTION
        "Indicates vendor of the failed AP."
     ::= { wsFailureAPStatusEntry 3 }

 wsFailedAPSoftwareVersion OBJECT-TYPE
     SYNTAX       DisplayString(SIZE(0..32))
     MAX-ACCESS   read-only
     STATUS       current
     DESCRIPTION
        "Indicates software version of the failed AP."
     ::= { wsFailureAPStatusEntry 4 }

 wsFailedAPHWType OBJECT-TYPE
     SYNTAX       INTEGER {
                    reserved-1(1),
                    reserved-2(2),
                    reserved-3(3),
                    reserved-4(4),
                    tq3600(5),
                    reserved-6(6),
                    reserved-7(7),
                    tq3200(8),
                    tq2450(9),
                    tq3400(10),
                    reserved-11(11),
                    tq4400(12),
                    tq4600(13)
                  }
     MAX-ACCESS   not-accessible
     STATUS       current
     DESCRIPTION
        "Indicates hardware type of the failed AP."
     ::= { wsFailureAPStatusEntry 5 }

 wsFailedAPFailureType OBJECT-TYPE
     SYNTAX       INTEGER {
                    localAuthentication(1),
                    noDbEntry(2),
                    notManaged(3),
                    radiusAuthentication(4),
                    radiusChallenged(5),
                    radiusUnreachable(6),
                    invalidRadiusResponse(7),
                    invalidProfileId(8),
                    profileMismatch(9),
                    radiusMsgSendFailed(10),
                    noAPImageAvailable(11)
                  }
     MAX-ACCESS   read-only
     STATUS       current
     DESCRIPTION
        "Indicates the last type of failure that occured."
     ::= { wsFailureAPStatusEntry 6 }

 wsFailedAPValidationFailureCount OBJECT-TYPE
     SYNTAX       Unsigned32
     MAX-ACCESS   not-accessible
     STATUS       current
     DESCRIPTION
        "Number of times the AP failed to authenticate due to
         MAC address validation failure."
     ::= { wsFailureAPStatusEntry 7 }

 wsFailedAPAuthenticationFailureCount OBJECT-TYPE
     SYNTAX       Unsigned32
     MAX-ACCESS   read-only
     STATUS       current
     DESCRIPTION
        "Number of times the AP failed to authenticate due to
         incorrect authentication credentials."
     ::= { wsFailureAPStatusEntry 8 }

 wsFailedAPProtocolVersion  OBJECT-TYPE
     SYNTAX       Integer32(0..65535)
     MAX-ACCESS   read-only
     STATUS       current
     DESCRIPTION
         "Indicates the protocol version supported by
          the software on this AP."
     ::= { wsFailureAPStatusEntry 9 }

 wsFailedAPAge  OBJECT-TYPE
     SYNTAX       TimeTicks
     MAX-ACCESS   read-only
     STATUS       current
     DESCRIPTION
        "Indicates time since failure occured."
     ::= { wsFailureAPStatusEntry 10 }

 wsFailedAPReportingSwitch OBJECT-TYPE
     SYNTAX       INTEGER {
                    local-switch(1),
                    peer-switch(2)
                  }
     MAX-ACCESS   read-only
     STATUS       current
     DESCRIPTION
        "This object indicates whether the AP failure happened on
         this controller or on the peer-controller."
     ::= {wsFailureAPStatusEntry 11}

 wsFailedAPSwitchMacAddress OBJECT-TYPE
     SYNTAX       MacAddress
     MAX-ACCESS   read-only
     STATUS       current
     DESCRIPTION
        "MAC address of the WS reporting the AP Authentication Failure."
     ::= {wsFailureAPStatusEntry 12}

 wsFailedAPSwitchIpAddress OBJECT-TYPE
     SYNTAX       IpAddress
     MAX-ACCESS   read-only
     STATUS       current
     DESCRIPTION
        "IP address of the WS reporting the AP Authentication Failure."
     ::= {wsFailureAPStatusEntry 13}

 wsAPFailureEntriesPurge OBJECT-TYPE
     SYNTAX       INTEGER {
                    enable(1),
                    disable(2)
                  }
     MAX-ACCESS   read-only
     STATUS       current
     DESCRIPTION
        "This is an action object used to purge the failed AP entries.
         Read on this object will always return disable."
     ::= { intrusionDetection 4 }

--
--   wsAdHocClientStatusTable
--
  wsAdHocClientStatusTable OBJECT-TYPE
     SYNTAX       SEQUENCE OF WsAdHocClientStatusEntry
     MAX-ACCESS   not-accessible
     STATUS       current
     DESCRIPTION
         "This table contains information related to
          Ad hoc clients detected in the network."
     ::= { intrusionDetection 5 }

    wsAdHocClientStatusEntry OBJECT-TYPE
     SYNTAX       WsAdHocClientStatusEntry
     MAX-ACCESS   not-accessible
     STATUS       current
     DESCRIPTION
          "Each entry in this table represents Ad hoc
           client detected in the network."
     INDEX    { wsAdHocClientMacAddress }
     ::= { wsAdHocClientStatusTable 1 }

 WsAdHocClientStatusEntry ::=
     SEQUENCE {
      wsAdHocClientMacAddress           MacAddress,
      wsDetectedAPMacAddress            MacAddress,
      wsDetectedAPRadioInterface        Integer32,
      wsAdHocClientDetectionMode        INTEGER,
      wsAdHocClientAge                  TimeTicks
 }

 wsAdHocClientMacAddress  OBJECT-TYPE
     SYNTAX       MacAddress
     MAX-ACCESS   read-only
     STATUS       current
     DESCRIPTION
       "The Ethernet address of the Ad hoc client detected.
        If detection Mode is 'Beacon' then the client is
        represented as an AP in the RF Scan database and
        the Neighbor AP List. If the detection mode is
        'Data Frame' then the client information is in
        the Neighbor Client List."
     ::= {wsAdHocClientStatusEntry  1 }

 wsDetectedAPMacAddress  OBJECT-TYPE
     SYNTAX       MacAddress
     MAX-ACCESS   read-only
     STATUS       current
     DESCRIPTION
       "The MAC address of an AP which last detected the Ad hoc
        client."
     ::= {wsAdHocClientStatusEntry  2 }

 wsDetectedAPRadioInterface  OBJECT-TYPE
     SYNTAX       Integer32(1..2)
     MAX-ACCESS   read-only
     STATUS       current
     DESCRIPTION
       "The radio interface of an AP which last detected the Ad hoc
        client."
     ::= {wsAdHocClientStatusEntry  3 }

 wsAdHocClientDetectionMode  OBJECT-TYPE
     SYNTAX       INTEGER {
                     beacon-frame(1),
                     data-frame(2)
                  }
     MAX-ACCESS   read-only
     STATUS       current
     DESCRIPTION
        "The mechanism through which this Ad hoc device is
         detected. This can be through beacon frame or data frame."
     ::= {wsAdHocClientStatusEntry  4 }

 wsAdHocClientAge  OBJECT-TYPE
     SYNTAX       TimeTicks
     MAX-ACCESS   read-only
     STATUS       current
     DESCRIPTION
       "Indicates time since the last detection of this Ad hoc client."
     ::= {wsAdHocClientStatusEntry  5 }

 wsAdHocClientEntriesPurge OBJECT-TYPE
     SYNTAX       INTEGER {
                    enable(1),
                    disable(2)
                  }
     MAX-ACCESS   read-only
     STATUS       current
     DESCRIPTION
        "This is an action object used to purge the ad-hoc client
         entries. Read on this object will always return disable."
     ::= { intrusionDetection 6 }

--
--   wsAPTriangulationNonSentryStatusTable
--
 wsAPTriangulationNonSentryStatusTable OBJECT-TYPE
     SYNTAX       SEQUENCE OF WsAPTriangulationNonSentryStatusEntry
     MAX-ACCESS   not-accessible
     STATUS       current
     DESCRIPTION
          "This table contains triangulation data to help the
           administrator determine which non-sentry APs are detecting the device."
     ::= { intrusionDetection 7 }

 wsAPTriangulationNonSentryStatusEntry OBJECT-TYPE
     SYNTAX       WsAPTriangulationNonSentryStatusEntry
     MAX-ACCESS   not-accessible
     STATUS       current
     DESCRIPTION
          "Each entry in this table contains triangulation
           information for the RF Scan entry."
     INDEX    { wsAPTriangulationMacAddr,
                wsAPTriangulationId }
     ::= { wsAPTriangulationNonSentryStatusTable 1 }

 WsAPTriangulationNonSentryStatusEntry ::=
     SEQUENCE {
      wsAPTriangulationMacAddr          MacAddress,
      wsAPTriangulationId               Integer32,
      wsAPTriangulationNonSentryMacAddr MacAddress,
      wsAPTriangulationNonSentryRadio   Integer32,
      wsAPTriangulationRssi             Integer32,
      wsAPTriangulationStrength         Integer32,
      wsAPTriangulationNoise            Integer32,
      wsAPTriangulationAge              TimeTicks
 }

 wsAPTriangulationMacAddr  OBJECT-TYPE
     SYNTAX       MacAddress
     MAX-ACCESS   read-only
     STATUS       current
     DESCRIPTION
       "The MAC address of the detected AP, this could be a
        physical radio interface or VAP MAC."
     ::= {wsAPTriangulationNonSentryStatusEntry  1 }

 wsAPTriangulationId  OBJECT-TYPE
     SYNTAX       Integer32(0..2)
     MAX-ACCESS   read-only
     STATUS       current
     DESCRIPTION
         "Index of the sentry triangulation entry."
     ::= {wsAPTriangulationNonSentryStatusEntry  2 }

 wsAPTriangulationNonSentryMacAddr  OBJECT-TYPE
     SYNTAX       MacAddress
     MAX-ACCESS   read-only
     STATUS       current
     DESCRIPTION
       "The MAC address of the detecting AP."
     ::= {wsAPTriangulationNonSentryStatusEntry  3 }

 wsAPTriangulationNonSentryRadio  OBJECT-TYPE
     SYNTAX       Integer32(1..2)
     MAX-ACCESS   read-only
     STATUS       current
     DESCRIPTION
         "The radio of the detecting AP."
     ::= {wsAPTriangulationNonSentryStatusEntry  4 }

 wsAPTriangulationRssi  OBJECT-TYPE
     SYNTAX       Integer32(0..100)
     MAX-ACCESS   read-only
     STATUS       current
     DESCRIPTION
         "Received signal strength indicator in percent (0 to 100%)."
     ::= {wsAPTriangulationNonSentryStatusEntry  5 }

 wsAPTriangulationStrength  OBJECT-TYPE
     SYNTAX       Integer32(-127..127)
     MAX-ACCESS   read-only
     STATUS       current
     DESCRIPTION
         "Received signal strength in dBm (-127 to 127)."
     ::= {wsAPTriangulationNonSentryStatusEntry  6  }

 wsAPTriangulationNoise  OBJECT-TYPE
     SYNTAX       Integer32(-127..127)
     MAX-ACCESS   read-only
     STATUS       current
     DESCRIPTION
         "Noise reported on the channel by the AP in dBm (-127 to 127)."
     ::= {wsAPTriangulationNonSentryStatusEntry  7 }

 wsAPTriangulationAge OBJECT-TYPE
     SYNTAX       TimeTicks
     MAX-ACCESS   read-only
     STATUS       current
     DESCRIPTION
        "Indicates the age since this device was most
         recently detected by the detecting AP."
     ::= { wsAPTriangulationNonSentryStatusEntry 8 }

--
--   wsAPTriangulationSentryStatusTable
--
 wsAPTriangulationSentryStatusTable OBJECT-TYPE
     SYNTAX       SEQUENCE OF WsAPTriangulationSentryStatusEntry
     MAX-ACCESS   not-accessible
     STATUS       current
     DESCRIPTION
          "This table contains triangulation data to help the
           administrator determine which sentry APs are detecting the device."
     ::= { intrusionDetection 8 }

 wsAPTriangulationSentryStatusEntry OBJECT-TYPE
     SYNTAX       WsAPTriangulationSentryStatusEntry
     MAX-ACCESS   not-accessible
     STATUS       current
     DESCRIPTION
          "Each entry in this table contains triangulation
           information for the RF Scan entry."
     INDEX    { wsAPSentryTriangulationMacAddr,
                wsAPSentryTriangulationId }
     ::= { wsAPTriangulationSentryStatusTable 1 }

 WsAPTriangulationSentryStatusEntry ::=
     SEQUENCE {
      wsAPSentryTriangulationMacAddr          MacAddress,
      wsAPSentryTriangulationId               Integer32,
      wsAPSentryTriangulationSentryMacAddr    MacAddress,
      wsAPSentryTriangulationSentryRadio      Integer32,
      wsAPSentryTriangulationRssi             Integer32,
      wsAPSentryTriangulationStrength         Integer32,
      wsAPSentryTriangulationNoise            Integer32,
      wsAPSentryTriangulationAge              TimeTicks
 }

 wsAPSentryTriangulationMacAddr  OBJECT-TYPE
     SYNTAX       MacAddress
     MAX-ACCESS   read-only
     STATUS       current
     DESCRIPTION
       "The MAC address of the detected AP, this could be a
        physical radio interface or VAP MAC."
     ::= {wsAPTriangulationSentryStatusEntry  1 }

 wsAPSentryTriangulationId  OBJECT-TYPE
     SYNTAX       Integer32(0..2)
     MAX-ACCESS   read-only
     STATUS       current
     DESCRIPTION
         "Index of the sentry triangulation entry."
     ::= {wsAPTriangulationSentryStatusEntry  2 }

 wsAPSentryTriangulationSentryMacAddr  OBJECT-TYPE
     SYNTAX       MacAddress
     MAX-ACCESS   read-only
     STATUS       current
     DESCRIPTION
       "The MAC address of the detecting AP."
     ::= {wsAPTriangulationSentryStatusEntry  3 }

 wsAPSentryTriangulationSentryRadio  OBJECT-TYPE
     SYNTAX       Integer32(1..2)
     MAX-ACCESS   read-only
     STATUS       current
     DESCRIPTION
       "The radio of the detecting AP."
     ::= {wsAPTriangulationSentryStatusEntry  4 }

 wsAPSentryTriangulationRssi  OBJECT-TYPE
     SYNTAX       Integer32(0..100)
     MAX-ACCESS   read-only
     STATUS       current
     DESCRIPTION
         "Received signal strength indicator in percent (0 to 100%)."
     ::= {wsAPTriangulationSentryStatusEntry  5 }

 wsAPSentryTriangulationStrength  OBJECT-TYPE
     SYNTAX       Integer32(-127..127)
     MAX-ACCESS   read-only
     STATUS       current
     DESCRIPTION
         "Received signal strength in dBm (-127 to 127)."
     ::= {wsAPTriangulationSentryStatusEntry  6  }

 wsAPSentryTriangulationNoise  OBJECT-TYPE
     SYNTAX       Integer32(-127..127)
     MAX-ACCESS   read-only
     STATUS       current
     DESCRIPTION
         "Noise reported on the channel by the AP in dBm (-127 to 127)."
     ::= {wsAPTriangulationSentryStatusEntry  7 }

 wsAPSentryTriangulationAge OBJECT-TYPE
     SYNTAX       TimeTicks
     MAX-ACCESS   read-only
     STATUS       current
     DESCRIPTION
        "Indicates age since this device was most
         recently detected by the detecting AP."
     ::= { wsAPTriangulationSentryStatusEntry 8 }

--
--   wsAPRogueClassificationStatusTable
--
 wsAPRogueClassificationStatusTable OBJECT-TYPE
     SYNTAX       SEQUENCE OF WsAPRogueClassificationStatusEntry
     MAX-ACCESS   not-accessible
     STATUS       current
     DESCRIPTION
          "This table contains rogue classification test results."
     ::= { intrusionDetection 9 }

 wsAPRogueClassificationStatusEntry OBJECT-TYPE
     SYNTAX       WsAPRogueClassificationStatusEntry
     MAX-ACCESS   not-accessible
     STATUS       current
     DESCRIPTION
          "Each entry in this table contains triangulation
           information for the RF Scan entry."
     INDEX    { wsAPRogueClassificationMacAddr,
                wsAPRogueClassificationTestId }
     ::= { wsAPRogueClassificationStatusTable 1 }

 WsAPRogueClassificationStatusEntry ::=
     SEQUENCE {
      wsAPRogueClassificationMacAddr          MacAddress,
      wsAPRogueClassificationTestId           Integer32,
      wsAPRogueClassificationTestName         INTEGER,
      wsAPRogueClassificationDetected         INTEGER,
      wsAPRogueClassificationReportingAPMac   MacAddress,
      wsAPRogueClassificationReportingAPRadio Integer32,
      wsAPRogueClassificationTestState        INTEGER,
      wsAPRogueClassificationTestResult       INTEGER,
      wsAPRogueClassificationFirstTime        TimeTicks,
      wsAPRogueClassificationLastTime         TimeTicks
 }

 wsAPRogueClassificationMacAddr  OBJECT-TYPE
     SYNTAX       MacAddress
     MAX-ACCESS   read-only
     STATUS       current
     DESCRIPTION
       "The MAC address of the detected AP, this could be a
        physical radio interface or VAP MAC."
     ::= {wsAPRogueClassificationStatusEntry  1 }

 wsAPRogueClassificationTestId  OBJECT-TYPE
     SYNTAX       Integer32(0..10)
     MAX-ACCESS   read-only
     STATUS       current
     DESCRIPTION
         "The rogue classification test id."
     ::= {wsAPRogueClassificationStatusEntry  2 }

 wsAPRogueClassificationTestName  OBJECT-TYPE
     SYNTAX       INTEGER {
                     widsaprogue01(0),
                     widsaprogue02(1),
                     widsaprogue03(2),
                     widsaprogue04(3),
                     widsaprogue05(4),
                     widsaprogue06(5),
                     widsaprogue07(6),
                     widsaprogue08(7),
                     widsaprogue09(8),
                     widsaprogue10(9),
                     widsaprogue11(10)
                     }
     MAX-ACCESS   read-only
     STATUS       current
     DESCRIPTION
         "The rogue classification test identifier."
     ::= {wsAPRogueClassificationStatusEntry  3 }

 wsAPRogueClassificationDetected  OBJECT-TYPE
     SYNTAX       INTEGER {
                     notdetected(0),
                     detected(1)
                  }
     MAX-ACCESS   read-only
     STATUS       current
     DESCRIPTION
         "Indicates whether this test detected the condition
          that it is designed to detect."
     ::= {wsAPRogueClassificationStatusEntry  4 }

 wsAPRogueClassificationReportingAPMac  OBJECT-TYPE
     SYNTAX       MacAddress
     MAX-ACCESS   read-only
     STATUS       current
     DESCRIPTION
       "The MAC address of the managed AP that last
        reported detecting this condition."
     ::= {wsAPRogueClassificationStatusEntry  5 }

 wsAPRogueClassificationReportingAPRadio  OBJECT-TYPE
     SYNTAX       Integer32(0..2)
     MAX-ACCESS   read-only
     STATUS       current
     DESCRIPTION
         "The radio number of the managed AP that last
          reported detecting this condition.  Zero
          indicates no report available"
     ::= {wsAPRogueClassificationStatusEntry  6 }

 wsAPRogueClassificationTestState  OBJECT-TYPE
     SYNTAX       INTEGER {
                     disabled(0),
                     enabled(1)
                  }
     MAX-ACCESS   read-only
     STATUS       current
     DESCRIPTION
         "Indicates whether this test is configured to report rogues."
     ::= {wsAPRogueClassificationStatusEntry  7 }

 wsAPRogueClassificationTestResult  OBJECT-TYPE
     SYNTAX       INTEGER {
                     notreported(0),
                     roguereported(1)
                  }
     MAX-ACCESS   read-only
     STATUS       current
     DESCRIPTION
         "Indicates whether this test reported the device as rogue."
     ::= {wsAPRogueClassificationStatusEntry  8 }

 wsAPRogueClassificationFirstTime OBJECT-TYPE
     SYNTAX       TimeTicks
     MAX-ACCESS   read-only
     STATUS       current
     DESCRIPTION
        "Indicates how long ago this test first detected the condition."
     ::= { wsAPRogueClassificationStatusEntry 9 }

 wsAPRogueClassificationLastTime OBJECT-TYPE
     SYNTAX       TimeTicks
     MAX-ACCESS   read-only
     STATUS       current
     DESCRIPTION
        "Indicates how long ago this test last detected the condition."
     ::= { wsAPRogueClassificationStatusEntry 10 }


--
--   wsAPDeAuthenticationAttackStatus
--
 wsAPDeAuthenticationAttackStatusTable OBJECT-TYPE
     SYNTAX       SEQUENCE OF WsAPDeAuthenticationAttackStatusEntry
     MAX-ACCESS   not-accessible
     STATUS       current
     DESCRIPTION
          "This table contains the AP de-authentication attack status."
     ::= { intrusionDetection 10 }

 wsAPDeAuthenticationAttackStatusEntry OBJECT-TYPE
     SYNTAX       WsAPDeAuthenticationAttackStatusEntry
     MAX-ACCESS   not-accessible
     STATUS       current
     DESCRIPTION
          "This table contains information about APs against which
           the Cluster Controller initiated a de-authentication attack."
     INDEX    { wsAPDeAuthenticationAttackStatusId }
     ::= { wsAPDeAuthenticationAttackStatusTable 1 }

 WsAPDeAuthenticationAttackStatusEntry ::=
     SEQUENCE {
      wsAPDeAuthenticationAttackStatusId      Integer32,
      wsAPDeAuthenticationAttackBSSID         MacAddress,
      wsAPDeAuthenticationAttackChannel       Integer32,
      wsAPDeAuthenticationAttackTime          TimeTicks,
      wsAPDeAuthenticationAttackAge           TimeTicks
 }

 wsAPDeAuthenticationAttackStatusId  OBJECT-TYPE
     SYNTAX       Integer32(1..16)
     MAX-ACCESS   read-only
     STATUS       current
     DESCRIPTION
         "The AP de-authentication attack status table index."
     ::= {wsAPDeAuthenticationAttackStatusEntry  1 }

 wsAPDeAuthenticationAttackBSSID  OBJECT-TYPE
     SYNTAX       MacAddress
     MAX-ACCESS   read-only
     STATUS       current
     DESCRIPTION
       "BSSID of the AP against which the attack is launched."
     ::= {wsAPDeAuthenticationAttackStatusEntry  2 }

 wsAPDeAuthenticationAttackChannel  OBJECT-TYPE
     SYNTAX       Integer32(1..161)
     MAX-ACCESS   read-only
     STATUS       current
     DESCRIPTION
         "Channel on which the rogue AP is operating."
     ::= {wsAPDeAuthenticationAttackStatusEntry  3 }

 wsAPDeAuthenticationAttackTime OBJECT-TYPE
     SYNTAX       TimeTicks
     MAX-ACCESS   read-only
     STATUS       current
     DESCRIPTION
        "Time since attack started on this AP."
     ::= { wsAPDeAuthenticationAttackStatusEntry 4 }

 wsAPDeAuthenticationAttackAge OBJECT-TYPE
     SYNTAX       TimeTicks
     MAX-ACCESS   read-only
     STATUS       current
     DESCRIPTION
        "Time since RF Scan report about this AP."
     ::= { wsAPDeAuthenticationAttackStatusEntry 5 }

--**************************************************************************************
-- wsDetectedClientTable
--**************************************************************************************

  wsDetectedClientStatusTable OBJECT-TYPE
     SYNTAX       SEQUENCE OF WsDetectedClientStatusEntry
     MAX-ACCESS   not-accessible
     STATUS       current
     DESCRIPTION
          "This table contains status parameters of clients that are
           currently detected."
     ::= { intrusionDetection 11 }

  wsDetectedClientStatusEntry OBJECT-TYPE
     SYNTAX       WsDetectedClientStatusEntry
     MAX-ACCESS   not-accessible
     STATUS       current
     DESCRIPTION
          "Each entry in this table contains detected client status
              parameters."
     INDEX    { wsDetectedClientMacAddress }
     ::= { wsDetectedClientStatusTable 1 }

 WsDetectedClientStatusEntry ::=
     SEQUENCE {
      wsDetectedClientMacAddress                MacAddress,
      wsDetectedClientStatus                    INTEGER,
      wsDetectedClientAuthStatus                INTEGER,
      wsDetectedClientEntryLastUpdatedAt        TimeTicks,
      wsDetectedClientThreatDetectedStatus      INTEGER,
      wsDetectedClientThreatMitigationStatus    INTEGER,
      wsDetectedClientName                      DisplayString,
      wsDetectedClientEntryCreateTime           TimeTicks,
      wsDetectedClientChannel                   Unsigned32,
      wsDetectedClientAuthRSSI                  Unsigned32,
      wsDetectedClientAuthSignal                Integer32,
      wsDetectedClientAuthNoise                 Integer32,
      wsDetectedClientProbeReqRecorded          Unsigned32,
      wsDetectedClientProbeCollectionIntvl      TimeTicks,
      wsDetectedClientHighestNumProbes          Unsigned32,
      wsDetectedClientAuthMsgsRecorded          Unsigned32,
      wsDetectedClientAuthCollectionIntvl       TimeTicks,
      wsDetectedClientHighestNumAuthMsgs        Unsigned32,
      wsDetectedClientDeAuthMsgsRecorded        Unsigned32,
      wsDetectedClientDeAuthCollectionIntvl     TimeTicks,
      wsDetectedClientHighestNumDeAuthMsgs      Unsigned32,
      wsDetectedClientAuthFailures              Unsigned32,
      wsDetectedClientProbesDetected            Unsigned32,
      wsDetectedClientBcastBSSIDProbes          Unsigned32,
      wsDetectedClientBcastSSIDProbes           Unsigned32,
      wsDetectedClientSpecificBSSIDProbes       Unsigned32,
      wsDetectedClientSpecificSSIDProbes        Unsigned32,
      wsDetectedClientLastNonBcastBSSID         MacAddress,
      wsDetectedClientLastNonBcastSSID          DisplayString,
      wsDetectedClientThreatMitigationSent      TimeTicks,
      wsDetectedClientEntryPurge                INTEGER,
-- NOT_SUPPORTED
--    wsDetectedClientEntryHistoryPurge         INTEGER,
--
      wsDetectedClientEntryAcknowledge          INTEGER,
      wsDetectedClientOUI                       DisplayString

 }

 wsDetectedClientMacAddress  OBJECT-TYPE
     SYNTAX       MacAddress
     MAX-ACCESS   read-only
     STATUS       current
     DESCRIPTION
        "Detected client MAC address."
     ::= {wsDetectedClientStatusEntry  1 }

 wsDetectedClientStatus OBJECT-TYPE
     SYNTAX       INTEGER {
                       authenticated(0),
                       detected(1),
                       known(2),
                       black-listed(3),
                       rogue(4)
                  }
     MAX-ACCESS   read-only
     STATUS       current
     DESCRIPTION
        "This object indicates client's status.
         Authenticated- Client is Authenticated with the
                        system and is not Rogue
         Detected- Client is detected, not Authenticated,
                        not rogue, and is not found in the
                        Known Clients Database.
         Known- Client is detected, but is not authenticated.
         Black-Listed- Client tried to associate with the system,
                       but was rejected due to MAC authentication.
         Rogue- Client failed of the the enabled threat tests."
     ::= { wsDetectedClientStatusEntry 2 }

 wsDetectedClientAuthStatus OBJECT-TYPE
     SYNTAX       INTEGER {
                       not-authenticated(0),
                       authenticated(1)
                  }
     MAX-ACCESS   read-only
     STATUS       current
     DESCRIPTION
        "This object indicates client's authentication status.
         Note that the Client Status can be Rogue, but the client
         can be Authenticated."
     ::= { wsDetectedClientStatusEntry 3 }

 wsDetectedClientEntryLastUpdatedAt OBJECT-TYPE
     SYNTAX       TimeTicks
     MAX-ACCESS   read-only
     STATUS       current
     DESCRIPTION
        "This object indicates time since any event has been received
         for this client that updated the detected client database entry."
     ::= { wsDetectedClientStatusEntry 4 }

 wsDetectedClientThreatDetectedStatus OBJECT-TYPE
     SYNTAX       INTEGER {
                       not-detected(0),
                       detected(1)
                  }
     MAX-ACCESS   read-only
     STATUS       current
     DESCRIPTION
        "This object indicates if any one of the threat detection tests
         have been triggered for this client. If the test is disabled the
         client won't be marked as Rogue, but administrator may still be
         interested in investigating why the threat triggered."
     ::= { wsDetectedClientStatusEntry 5 }

 wsDetectedClientThreatMitigationStatus OBJECT-TYPE
     SYNTAX       INTEGER {
                       not-done(0),
                       done(1)
                  }
     MAX-ACCESS   read-only
     STATUS       current
     DESCRIPTION
        "This object indicates whether threat mitigation has been
         done for this client."
     ::= { wsDetectedClientStatusEntry 6 }

 wsDetectedClientName OBJECT-TYPE
     SYNTAX       DisplayString(SIZE(0..32))
     MAX-ACCESS   read-only
     STATUS       current
     DESCRIPTION
        "Nickname from the Known Client Database. If client is not
         in the database then the nickname is blank."
     ::= { wsDetectedClientStatusEntry 7 }

 wsDetectedClientEntryCreateTime OBJECT-TYPE
     SYNTAX       TimeTicks
     MAX-ACCESS   read-only
     STATUS       current
     DESCRIPTION
        "Indicates the time the detected client entry was
         created."
     ::= { wsDetectedClientStatusEntry 8 }

 wsDetectedClientChannel OBJECT-TYPE
     SYNTAX       Unsigned32(0..100)
     MAX-ACCESS   read-only
     STATUS       current
     DESCRIPTION
        "this object indicates channel number in which the client is dtected"
     ::= { wsDetectedClientStatusEntry 9 }

 wsDetectedClientAuthRSSI OBJECT-TYPE
     SYNTAX       Unsigned32(0..100)
     MAX-ACCESS   read-only
     STATUS       current
     DESCRIPTION
        "If the client is authenticated with the managed AP then this
         object indicates Received Signal Strength(RSSI) value reported
         by the AP with which the client is authenticated."
     DEFVAL        { 0 }
     ::= { wsDetectedClientStatusEntry 10 }

 wsDetectedClientAuthSignal  OBJECT-TYPE
     SYNTAX       Integer32(-128..128)
     MAX-ACCESS   read-only
     STATUS       current
     DESCRIPTION
         "This object indicates the last signal strength(in dBm)
          reported by the managed AP with which the client is authenticated."
     DEFVAL        { 0 }
     ::= {wsDetectedClientStatusEntry  11 }

 wsDetectedClientAuthNoise  OBJECT-TYPE
     SYNTAX       Integer32(-128..128)
     MAX-ACCESS   read-only
     STATUS       current
     DESCRIPTION
         "This object indicates the last channel noise(in dBm)
          reported by the managed AP with which the client is authenticated."
     DEFVAL        { 0 }
     ::= {wsDetectedClientStatusEntry  12 }

 wsDetectedClientProbeReqRecorded OBJECT-TYPE
     SYNTAX       Unsigned32
     MAX-ACCESS   read-only
     STATUS       current
     DESCRIPTION
         "This object indicates the number of probe requests
          recorded so far during the probe collection interval."
     ::= {wsDetectedClientStatusEntry  13 }

 wsDetectedClientProbeCollectionIntvl OBJECT-TYPE
     SYNTAX       TimeTicks
     MAX-ACCESS   read-only
     STATUS       current
     DESCRIPTION
         "This object indicates how much time is left before the
          probe collection interval is done and the controller decides
          whether the client is a threat."
     ::= {wsDetectedClientStatusEntry  14 }

 wsDetectedClientHighestNumProbes OBJECT-TYPE
     SYNTAX       Unsigned32
     MAX-ACCESS   read-only
     STATUS       current
     DESCRIPTION
         "This object indicates the largest number of probes that
          the controller detected during the collection interval."
     ::= {wsDetectedClientStatusEntry  15 }

 wsDetectedClientAuthMsgsRecorded OBJECT-TYPE
     SYNTAX       Unsigned32
     MAX-ACCESS   read-only
     STATUS       current
     DESCRIPTION
         "This object indicates the number of 802.11 authentication
          messages recorded so far during the auth collection interval."
     ::= {wsDetectedClientStatusEntry  16 }

 wsDetectedClientAuthCollectionIntvl OBJECT-TYPE
     SYNTAX       TimeTicks
     MAX-ACCESS   read-only
     STATUS       current
     DESCRIPTION
         "This object indicates how much time is left before the
          authentication collection interval is done and the controller decides
          whether the client is a threat."
     ::= {wsDetectedClientStatusEntry  17 }

 wsDetectedClientHighestNumAuthMsgs OBJECT-TYPE
     SYNTAX       Unsigned32
     MAX-ACCESS   read-only
     STATUS       current
     DESCRIPTION
         "This object indicates the largest number of authentications that
          the controller detected during the collection interval."
     ::= {wsDetectedClientStatusEntry  18 }

 wsDetectedClientDeAuthMsgsRecorded OBJECT-TYPE
     SYNTAX       Unsigned32
     MAX-ACCESS   read-only
     STATUS       current
     DESCRIPTION
         "This object indicates the number of 802.11 de-authentication
          messages recorded so far during the de-auth collection interval."
     ::= {wsDetectedClientStatusEntry  19 }

 wsDetectedClientDeAuthCollectionIntvl OBJECT-TYPE
     SYNTAX       TimeTicks
     MAX-ACCESS   read-only
     STATUS       current
     DESCRIPTION
         "This object indicates how much time is left before the
          de-authentication collection interval is done and the controller decides
          whether the client is a threat."
     ::= {wsDetectedClientStatusEntry  20 }

 wsDetectedClientHighestNumDeAuthMsgs OBJECT-TYPE
     SYNTAX       Unsigned32
     MAX-ACCESS   read-only
     STATUS       current
     DESCRIPTION
         "This object indicates the largest number of de-authentication
           messages that the controller detected during the collection interval."
     ::= {wsDetectedClientStatusEntry  21 }

 wsDetectedClientAuthFailures OBJECT-TYPE
     SYNTAX       Unsigned32
     MAX-ACCESS   read-only
     STATUS       current
     DESCRIPTION
         "This object indicates the number of 802.1X Authentication
          failures detected for this client."
     ::= {wsDetectedClientStatusEntry  22 }

 wsDetectedClientProbesDetected OBJECT-TYPE
     SYNTAX       Unsigned32
     MAX-ACCESS   read-only
     STATUS       current
     DESCRIPTION
         "This object indicates the number of probes detected in the last RF Scan."
     ::= {wsDetectedClientStatusEntry  23 }

 wsDetectedClientBcastBSSIDProbes OBJECT-TYPE
     SYNTAX       Unsigned32
     MAX-ACCESS   read-only
     STATUS       current
     DESCRIPTION
         "This object indicates the number of probes to broadcast
          BSSID in the last RF Scan."
     ::= {wsDetectedClientStatusEntry  24 }

 wsDetectedClientBcastSSIDProbes OBJECT-TYPE
     SYNTAX       Unsigned32
     MAX-ACCESS   read-only
     STATUS       current
     DESCRIPTION
         "This object indicates the number of probes to broadcast
          SSID in the last RF Scan."
     ::= {wsDetectedClientStatusEntry  25 }

 wsDetectedClientSpecificBSSIDProbes OBJECT-TYPE
     SYNTAX       Unsigned32
     MAX-ACCESS   read-only
     STATUS       current
     DESCRIPTION
         "This object indicates the number of probes to specific
          BSSID in the last RF Scan."
     ::= {wsDetectedClientStatusEntry  26 }

 wsDetectedClientSpecificSSIDProbes OBJECT-TYPE
     SYNTAX       Unsigned32
     MAX-ACCESS   read-only
     STATUS       current
     DESCRIPTION
         "This object indicates the number of probes to specific
          SSID in the last RF Scan."
     ::= {wsDetectedClientStatusEntry  27 }

 wsDetectedClientLastNonBcastBSSID OBJECT-TYPE
     SYNTAX       MacAddress
     MAX-ACCESS   read-only
     STATUS       current
     DESCRIPTION
         "This object indicates the last non-broadcast BSSID
          detected in the RF Scan."
     ::= {wsDetectedClientStatusEntry  28 }

 wsDetectedClientLastNonBcastSSID OBJECT-TYPE
     SYNTAX       DisplayString
     MAX-ACCESS   read-only
     STATUS       current
     DESCRIPTION
         "This object indicates the last non-broadcast SSID
          detected in the RF Scan."
     ::= {wsDetectedClientStatusEntry  29}

 wsDetectedClientThreatMitigationSent OBJECT-TYPE
     SYNTAX       TimeTicks
     MAX-ACCESS   read-only
     STATUS       current
     DESCRIPTION
        "This object indicates the time since the controller sent
         the last threat mitigation message to this client."
     ::= { wsDetectedClientStatusEntry 30 }

 wsDetectedClientEntryPurge OBJECT-TYPE
     SYNTAX       INTEGER {
                   enable(1),
                   disable(2)
                  }
     MAX-ACCESS   read-only
     STATUS       current
     DESCRIPTION
                 "This is an action object. Setting this object to
                  enable will purge the detected client entry
                  except entries for authenticated clients.
                  Read on this object will always return disable."
     ::= { wsDetectedClientStatusEntry 31 }


-- NOT_SUPPORTED
-- wsDetectedClientEntryHistoryPurge OBJECT-TYPE
--     SYNTAX       INTEGER {
--                  enable(1),
--                  disable(2)
--                  }
--     MAX-ACCESS   read-only
--     STATUS       current
--     DESCRIPTION
--                 "This is an action object. Setting this object to
--                  enable will delete roam and pre-authentication history
--                  for the client entry in the Detected Clients Database.
--                  Read on this object will always return disable."
--     ::= { wsDetectedClientStatusEntry 32 }

 wsDetectedClientEntryAcknowledge OBJECT-TYPE
     SYNTAX      INTEGER {
                 no-action(0),
                 acknowledge(1)
                  }
     MAX-ACCESS  read-only
     STATUS      current
     DESCRIPTION
                 "This is a command that allows the administrator
                  to clear the rogue status for the entry in the
                  Detected clients database"
     ::= { wsDetectedClientStatusEntry 32 }

 wsDetectedClientOUI  OBJECT-TYPE
     SYNTAX       DisplayString(SIZE(1..32))
     MAX-ACCESS   read-only
     STATUS       current
     DESCRIPTION
       "Device manufacturer information for this Detected client."
     ::= {wsDetectedClientStatusEntry  33 }

 wsDetectedClientPurgeAll OBJECT-TYPE
     SYNTAX       INTEGER {
                  enable(1),
                  disable(2)
                  }
     MAX-ACCESS   read-only
     STATUS       current
     DESCRIPTION
                  "This is an action object. Setting this object to
                  enable will purge all the detected clients entries
                  except entries for authenticated clients.
                  Read on this object will always return disable."
     ::= { intrusionDetection 12 }

-- NOT SUPPORTED
-- wsDetectedClientPurgeHistoryAll OBJECT-TYPE
--    SYNTAX       INTEGER {
--                 enable(1),
--                 disable(2)
--                 }
--         MAX-ACCESS   read-only
--         STATUS       current
--         DESCRIPTION
--                 "This is an action object. Setting this object to
--                  enable will delete all roam and pre-authentication history
--                  for all clients in the Detected Clients Database.
--                  Read on this object will always return disable."
--         ::= { intrusionDetection 13 }

 wsDetectedClientAcknowledgeAll OBJECT-TYPE
    SYNTAX      INTEGER {
                no-action(0),
                acknowledge(1)
                }
         MAX-ACCESS  read-only
         STATUS      current
         DESCRIPTION
                "This is a command that allows the administrator
                to clear the rogue status for all entries in the
                Detected clients database"
         ::= { intrusionDetection 13 }

--
--   wsClientRogueClassificationStatusTable
--
 wsClientRogueClassificationStatusTable OBJECT-TYPE
     SYNTAX       SEQUENCE OF WsClientRogueClassificationStatusEntry
     MAX-ACCESS   not-accessible
     STATUS       current
     DESCRIPTION
          "This table contains rogue classification test results for clients."
     ::= { intrusionDetection 14 }

 wsClientRogueClassificationStatusEntry OBJECT-TYPE
     SYNTAX       WsClientRogueClassificationStatusEntry
     MAX-ACCESS   not-accessible
     STATUS       current
     DESCRIPTION
          "Each entry in this table contains rogue classification
          test results for a client."
     INDEX    { wsClientRogueClassificationMacAddr,
                wsClientRogueClassificationTestId }
     ::= { wsClientRogueClassificationStatusTable 1 }

 WsClientRogueClassificationStatusEntry ::=
     SEQUENCE {
      wsClientRogueClassificationMacAddr          MacAddress,
      wsClientRogueClassificationTestId           Integer32,
      wsClientRogueClassificationTestName         INTEGER,
      wsClientRogueClassificationDetected         INTEGER,
      wsClientRogueClassificationReportingAPMac   MacAddress,
      wsClientRogueClassificationReportingAPRadio Integer32,
      wsClientRogueClassificationTestState        INTEGER,
      wsClientRogueClassificationTestResult       INTEGER,
      wsClientRogueClassificationFirstTime        TimeTicks,
      wsClientRogueClassificationLastTime         TimeTicks
 }

 wsClientRogueClassificationMacAddr  OBJECT-TYPE
     SYNTAX       MacAddress
     MAX-ACCESS   read-only
     STATUS       current
     DESCRIPTION
       "The MAC address of the detected client."
     ::= {wsClientRogueClassificationStatusEntry  1 }

 wsClientRogueClassificationTestId  OBJECT-TYPE
     SYNTAX       Integer32(0..10)
     MAX-ACCESS   read-only
     STATUS       current
     DESCRIPTION
         "The rogue classification test id."
     ::= {wsClientRogueClassificationStatusEntry  2 }

 wsClientRogueClassificationTestName  OBJECT-TYPE
     SYNTAX       INTEGER {
                     widsclientrogue01(0),
                     widsclientrogue02(1),
                     widsclientrogue03(2),
                     widsclientrogue04(3),
                     widsclientrogue05(4),
                     widsclientrogue06(5),
                     widsclientrogue07(6)
                     }
     MAX-ACCESS   read-only
     STATUS       current
     DESCRIPTION
         "The rogue classification test identifier."
     ::= {wsClientRogueClassificationStatusEntry  3 }

 wsClientRogueClassificationDetected  OBJECT-TYPE
     SYNTAX       INTEGER {
                     notdetected(0),
                     detected(1)
                  }
     MAX-ACCESS   read-only
     STATUS       current
     DESCRIPTION
         "Indicates whether this test detected the condition
          that it is designed to detect."
     ::= {wsClientRogueClassificationStatusEntry  4 }

 wsClientRogueClassificationReportingAPMac  OBJECT-TYPE
     SYNTAX       MacAddress
     MAX-ACCESS   read-only
     STATUS       current
     DESCRIPTION
       "The MAC address of the managed AP that last
        reported detecting this condition."
     ::= {wsClientRogueClassificationStatusEntry  5 }

 wsClientRogueClassificationReportingAPRadio  OBJECT-TYPE
     SYNTAX       Integer32(0..2)
     MAX-ACCESS   read-only
     STATUS       current
     DESCRIPTION
         "The radio number of the managed AP that last
          reported detecting this condition.  Zero
          indicates no report available"
     ::= {wsClientRogueClassificationStatusEntry  6 }

 wsClientRogueClassificationTestState  OBJECT-TYPE
     SYNTAX       INTEGER {
                     disabled(0),
                     enabled(1)
                  }
     MAX-ACCESS   read-only
     STATUS       current
     DESCRIPTION
         "Indicates whether this test is configured to report rogues."
     ::= {wsClientRogueClassificationStatusEntry  7 }

 wsClientRogueClassificationTestResult  OBJECT-TYPE
     SYNTAX       INTEGER {
                     notreported(0),
                     roguereported(1)
                  }
     MAX-ACCESS   read-only
     STATUS       current
     DESCRIPTION
         "Indicates whether this test reported the device as rogue."
     ::= {wsClientRogueClassificationStatusEntry  8 }

 wsClientRogueClassificationFirstTime OBJECT-TYPE
     SYNTAX       TimeTicks
     MAX-ACCESS   read-only
     STATUS       current
     DESCRIPTION
        "Indicates how long ago this test first detected the condition."
     ::= { wsClientRogueClassificationStatusEntry 9 }

 wsClientRogueClassificationLastTime OBJECT-TYPE
     SYNTAX       TimeTicks
     MAX-ACCESS   read-only
     STATUS       current
     DESCRIPTION
        "Indicates how long ago this test last detected the condition."
     ::= { wsClientRogueClassificationStatusEntry 10 }

--
--   wsDetectedClientTriangulationNonSentryStatusTable
--
 wsDetectedClientTriangulationNonSentryStatusTable OBJECT-TYPE
     SYNTAX       SEQUENCE OF WsDetectedClientTriangulationNonSentryStatusEntry
     MAX-ACCESS   not-accessible
     STATUS       current
     DESCRIPTION
          "This table contains triangulation data to help the
           administrator determine which three managed non-sentry
           APs are detecting the client along with the signal
           strength and the time stamp."
     ::= { intrusionDetection 15 }

 wsDetectedClientTriangulationNonSentryStatusEntry OBJECT-TYPE
     SYNTAX       WsDetectedClientTriangulationNonSentryStatusEntry
     MAX-ACCESS   not-accessible
     STATUS       current
     DESCRIPTION
          "Each entry in this table contains triangulation
           information for the Detected Client entry."
     INDEX    { wsDetectedClientTriangulationMacAddr,
                wsDetectedClientTriangulationId }
     ::= { wsDetectedClientTriangulationNonSentryStatusTable 1 }

 WsDetectedClientTriangulationNonSentryStatusEntry ::=
     SEQUENCE {
      wsDetectedClientTriangulationMacAddr          MacAddress,
      wsDetectedClientTriangulationId               Integer32,
      wsDetectedClientTriangulationNonSentryMacAddr MacAddress,
      wsDetectedClientTriangulationNonSentryRadio   Integer32,
      wsDetectedClientTriangulationRssi             Integer32,
      wsDetectedClientTriangulationStrength         Integer32,
      wsDetectedClientTriangulationNoise            Integer32,
      wsDetectedClientTriangulationAge              TimeTicks
 }

  wsDetectedClientTriangulationMacAddr  OBJECT-TYPE
     SYNTAX       MacAddress
     MAX-ACCESS   read-only
     STATUS       current
     DESCRIPTION
       "The MAC address of the Detected Client."
     ::= {wsDetectedClientTriangulationNonSentryStatusEntry  1 }

 wsDetectedClientTriangulationId  OBJECT-TYPE
     SYNTAX       Integer32(0..2)
     MAX-ACCESS   read-only
     STATUS       current
     DESCRIPTION
         "Index of the non sentry triangulation entry."
     ::= {wsDetectedClientTriangulationNonSentryStatusEntry  2 }

 wsDetectedClientTriangulationNonSentryMacAddr  OBJECT-TYPE
     SYNTAX       MacAddress
     MAX-ACCESS   read-only
     STATUS       current
     DESCRIPTION
       "The MAC address of the detecting AP."
     ::= {wsDetectedClientTriangulationNonSentryStatusEntry  3 }

 wsDetectedClientTriangulationNonSentryRadio  OBJECT-TYPE
     SYNTAX       Integer32(1..2)
     MAX-ACCESS   read-only
     STATUS       current
     DESCRIPTION
         "The radio of the detecting AP."
     ::= {wsDetectedClientTriangulationNonSentryStatusEntry  4 }

 wsDetectedClientTriangulationRssi  OBJECT-TYPE
     SYNTAX       Integer32(0..100)
     MAX-ACCESS   read-only
     STATUS       current
     DESCRIPTION
         "Received signal strength indicator in percent (0 to 100%)."
     ::= {wsDetectedClientTriangulationNonSentryStatusEntry  5 }

 wsDetectedClientTriangulationStrength  OBJECT-TYPE
     SYNTAX       Integer32(-127..127)
     MAX-ACCESS   read-only
     STATUS       current
     DESCRIPTION
         "Received signal strength in dBm (-127 to 127)."
     ::= {wsDetectedClientTriangulationNonSentryStatusEntry  6  }

 wsDetectedClientTriangulationNoise  OBJECT-TYPE
     SYNTAX       Integer32(-127..127)
     MAX-ACCESS   read-only
     STATUS       current
     DESCRIPTION
         "Noise reported on the channel by the AP in dBm (-127 to 127)."
     ::= {wsDetectedClientTriangulationNonSentryStatusEntry  7 }

 wsDetectedClientTriangulationAge OBJECT-TYPE
     SYNTAX       TimeTicks
     MAX-ACCESS   read-only
     STATUS       current
     DESCRIPTION
        "Indicates the time since this device was most
         recently detected by the detecting AP."
     ::= { wsDetectedClientTriangulationNonSentryStatusEntry 8 }

--
--   wsDetectedClientTriangulationSentryStatusTable
--
 wsDetectedClientTriangulationSentryStatusTable OBJECT-TYPE
     SYNTAX       SEQUENCE OF WsDetectedClientTriangulationSentryStatusEntry
     MAX-ACCESS   not-accessible
     STATUS       current
     DESCRIPTION
          "This table contains triangulation data to help the
           administrator determine which three managed sentry
           APs are detecting the client along with the signal
           strength and the time stamp."
     ::= { intrusionDetection 16 }

 wsDetectedClientTriangulationSentryStatusEntry OBJECT-TYPE
     SYNTAX       WsDetectedClientTriangulationSentryStatusEntry
     MAX-ACCESS   not-accessible
     STATUS       current
     DESCRIPTION
          "Each entry in this table contains triangulation
           information for the Detected Client entry."
     INDEX    { wsDetectedClientSentryTriangulationMacAddr,
                wsDetectedClientSentryTriangulationId }
     ::= { wsDetectedClientTriangulationSentryStatusTable 1 }

 WsDetectedClientTriangulationSentryStatusEntry ::=
     SEQUENCE {
      wsDetectedClientSentryTriangulationMacAddr          MacAddress,
      wsDetectedClientSentryTriangulationId               Integer32,
      wsDetectedClientSentryTriangulationSentryMacAddr    MacAddress,
      wsDetectedClientSentryTriangulationSentryRadio      Integer32,
      wsDetectedClientSentryTriangulationRssi             Integer32,
      wsDetectedClientSentryTriangulationStrength         Integer32,
      wsDetectedClientSentryTriangulationNoise            Integer32,
      wsDetectedClientSentryTriangulationAge              TimeTicks
 }

 wsDetectedClientSentryTriangulationMacAddr  OBJECT-TYPE
     SYNTAX       MacAddress
     MAX-ACCESS   read-only
     STATUS       current
     DESCRIPTION
       "The MAC address of the detected client."
     ::= {wsDetectedClientTriangulationSentryStatusEntry  1 }

 wsDetectedClientSentryTriangulationId  OBJECT-TYPE
     SYNTAX       Integer32(0..2)
     MAX-ACCESS   read-only
     STATUS       current
     DESCRIPTION
         "Index of the sentry triangulation entry."
     ::= {wsDetectedClientTriangulationSentryStatusEntry  2 }

 wsDetectedClientSentryTriangulationSentryMacAddr  OBJECT-TYPE
     SYNTAX       MacAddress
     MAX-ACCESS   read-only
     STATUS       current
     DESCRIPTION
       "The MAC address of the AP detecting the client."
     ::= {wsDetectedClientTriangulationSentryStatusEntry  3 }

 wsDetectedClientSentryTriangulationSentryRadio  OBJECT-TYPE
     SYNTAX       Integer32(1..2)
     MAX-ACCESS   read-only
     STATUS       current
     DESCRIPTION
       "The radio of the AP detecting the client."
     ::= {wsDetectedClientTriangulationSentryStatusEntry  4 }

 wsDetectedClientSentryTriangulationRssi  OBJECT-TYPE
     SYNTAX       Integer32(0..100)
     MAX-ACCESS   read-only
     STATUS       current
     DESCRIPTION
         "Received signal strength indicator in percent (0 to 100%)."
     ::= {wsDetectedClientTriangulationSentryStatusEntry  5 }

 wsDetectedClientSentryTriangulationStrength  OBJECT-TYPE
     SYNTAX       Integer32(-127..127)
     MAX-ACCESS   read-only
     STATUS       current
     DESCRIPTION
         "Received signal strength in dBm (-127 to 127)."
     ::= {wsDetectedClientTriangulationSentryStatusEntry  6  }

 wsDetectedClientSentryTriangulationNoise  OBJECT-TYPE
     SYNTAX       Integer32(-127..127)
     MAX-ACCESS   read-only
     STATUS       current
     DESCRIPTION
         "Noise reported on the channel by the AP in dBm (-127 to 127)."
     ::= {wsDetectedClientTriangulationSentryStatusEntry  7 }

 wsDetectedClientSentryTriangulationAge OBJECT-TYPE
     SYNTAX       TimeTicks
     MAX-ACCESS   read-only
     STATUS       current
     DESCRIPTION
        "Indicates time since this device was most
         recently detected by the detecting AP."
     ::= { wsDetectedClientTriangulationSentryStatusEntry 8 }

--
--   wsDetectedClientPreAuthenticationHistoryTable
--
 wsDetectedClientPreAuthenticationHistoryTable OBJECT-TYPE
     SYNTAX       SEQUENCE OF WsDetectedClientPreAuthenticationHistoryEntry
     MAX-ACCESS   not-accessible
     STATUS       current
     DESCRIPTION
          "This table contains pre-authentication history entries for
           detected clients."
     ::= { intrusionDetection 17 }

 wsDetectedClientPreAuthenticationHistoryEntry OBJECT-TYPE
     SYNTAX       WsDetectedClientPreAuthenticationHistoryEntry
     MAX-ACCESS   not-accessible
     STATUS       current
     DESCRIPTION
          "Each entry in this table contains details of pre-authentication
          events occured for the detected client."
     INDEX    { wsDetectedClientPreAuthenticationMacAddr,
                wsDetectedClientPreAuthenticationId}
     ::= { wsDetectedClientPreAuthenticationHistoryTable 1 }

 WsDetectedClientPreAuthenticationHistoryEntry ::=
     SEQUENCE {
      wsDetectedClientPreAuthenticationMacAddr       MacAddress,
      wsDetectedClientPreAuthenticationId            Unsigned32,
      wsDetectedClientPreAuthenticationApMac         MacAddress,
      wsDetectedClientPreAuthenticationApRadioId     Integer32,
      wsDetectedClientPreAuthenticationVapMac        MacAddress,
      wsDetectedClientPreAuthenticationSSID          DisplayString,
      wsDetectedClientPreAuthenticationAge           TimeTicks,
      wsDetectedClientPreAuthenticationStatus        INTEGER
 }

 wsDetectedClientPreAuthenticationMacAddr       OBJECT-TYPE
     SYNTAX       MacAddress
     MAX-ACCESS   read-only
     STATUS       current
     DESCRIPTION
       "The MAC address of the detected client."
     ::= {wsDetectedClientPreAuthenticationHistoryEntry 1 }

 wsDetectedClientPreAuthenticationId    OBJECT-TYPE
     SYNTAX      Unsigned32
     MAX-ACCESS  read-only
     STATUS      current
     DESCRIPTION
       "Numeric identifier for the preAuthentication entry."
     ::= {wsDetectedClientPreAuthenticationHistoryEntry 2 }

 wsDetectedClientPreAuthenticationApMac  OBJECT-TYPE
     SYNTAX       MacAddress
     MAX-ACCESS   read-only
     STATUS       current
     DESCRIPTION
        "The Ethernet address of the AP with which client has pre-authenticated."
     ::= {wsDetectedClientPreAuthenticationHistoryEntry 3 }

 wsDetectedClientPreAuthenticationApRadioId     OBJECT-TYPE
     SYNTAX      Integer32(1..2)
     MAX-ACCESS  read-only
     STATUS      current
     DESCRIPTION
       "The radio number of this radio in the AP with which client has
       pre-authenticated."
     ::= {wsDetectedClientPreAuthenticationHistoryEntry 4 }

 wsDetectedClientPreAuthenticationVapMac  OBJECT-TYPE
     SYNTAX       MacAddress
     MAX-ACCESS   read-only
     STATUS       current
     DESCRIPTION
        "The MAC address of the VAP to which client has roamed."
     ::= {wsDetectedClientPreAuthenticationHistoryEntry 5 }

 wsDetectedClientPreAuthenticationSSID OBJECT-TYPE
     SYNTAX       DisplayString(SIZE(0..32))
     MAX-ACCESS   read-only
     STATUS       current
     DESCRIPTION
        "This object indicates the SSID used by the VAP."
     ::= {wsDetectedClientPreAuthenticationHistoryEntry 6 }

 wsDetectedClientPreAuthenticationAge OBJECT-TYPE
     SYNTAX       TimeTicks
     MAX-ACCESS   read-only
     STATUS       current
     DESCRIPTION
        "Indicates time since this history event occured."
     ::= {wsDetectedClientPreAuthenticationHistoryEntry 7 }

  wsDetectedClientPreAuthenticationStatus     OBJECT-TYPE
     SYNTAX        INTEGER {
                    success(0),
                    failure(1)
                   }
     MAX-ACCESS   read-only
     STATUS       current
     DESCRIPTION
        "Designates the pre-authentication operational status for
        this detected client."
     ::= {wsDetectedClientPreAuthenticationHistoryEntry 8 }

 wsDetectedClientPreAuthenticationHistoryPurgeAll OBJECT-TYPE
     SYNTAX       INTEGER {
                  enable(1),
                  disable(2)
                  }
     MAX-ACCESS   read-only
     STATUS       current
     DESCRIPTION
                  "This is an action object. Setting this object to enable
                  will purge all the pre-authentication history entries for
                  all the detected clients. Read on this object will always
                  return disable."
     ::= { intrusionDetection 18 }

--
--   wsDetectedClientRoamHistoryTable
--
 wsDetectedClientRoamHistoryTable OBJECT-TYPE
     SYNTAX       SEQUENCE OF WsDetectedClientRoamHistoryEntry
     MAX-ACCESS   not-accessible
     STATUS       current
     DESCRIPTION
          "This table contains roam history entries for detected clients."
     ::= { intrusionDetection 19 }

 wsDetectedClientRoamHistoryEntry OBJECT-TYPE
     SYNTAX       WsDetectedClientRoamHistoryEntry
     MAX-ACCESS   not-accessible
     STATUS       current
     DESCRIPTION
          "Each entry in this table contains details of roam
          events occured for the detected client."
     INDEX    { wsDetectedClientRoamMacAddr,
                wsDetectedClientRoamId}
     ::= { wsDetectedClientRoamHistoryTable 1 }

 WsDetectedClientRoamHistoryEntry ::=
     SEQUENCE {
      wsDetectedClientRoamMacAddr       MacAddress,
      wsDetectedClientRoamId            Unsigned32,
      wsDetectedClientRoamApMac         MacAddress,
      wsDetectedClientRoamApRadioId     Integer32,
      wsDetectedClientRoamVapMac        MacAddress,
      wsDetectedClientRoamSSID          DisplayString,
      wsDetectedClientRoamAge           TimeTicks,
      wsDetectedClientRoamStatus        INTEGER
 }

 wsDetectedClientRoamMacAddr       OBJECT-TYPE
     SYNTAX       MacAddress
     MAX-ACCESS   read-only
     STATUS       current
     DESCRIPTION
       "The MAC address of the detected client."
     ::= {wsDetectedClientRoamHistoryEntry 1 }

 wsDetectedClientRoamId    OBJECT-TYPE
     SYNTAX      Unsigned32
     MAX-ACCESS  read-only
     STATUS      current
     DESCRIPTION
       "Numeric identifier for the Roam entry."
     ::= {wsDetectedClientRoamHistoryEntry 2 }

 wsDetectedClientRoamApMac  OBJECT-TYPE
     SYNTAX       MacAddress
     MAX-ACCESS   read-only
     STATUS       current
     DESCRIPTION
        "The Ethernet address of the AP to which client has roamed."
     ::= {wsDetectedClientRoamHistoryEntry 3 }

 wsDetectedClientRoamApRadioId     OBJECT-TYPE
     SYNTAX      Integer32(1..2)
     MAX-ACCESS  read-only
     STATUS      current
     DESCRIPTION
        "The radio number of this radio in the AP with which client has
        roamed."

     ::= {wsDetectedClientRoamHistoryEntry 4 }

 wsDetectedClientRoamVapMac  OBJECT-TYPE
     SYNTAX       MacAddress
     MAX-ACCESS   read-only
     STATUS       current
     DESCRIPTION
        "The MAC address of the VAP to which client has roamed."
     ::= {wsDetectedClientRoamHistoryEntry 5 }

 wsDetectedClientRoamSSID OBJECT-TYPE
     SYNTAX       DisplayString(SIZE(0..32))
     MAX-ACCESS   read-only
     STATUS       current
     DESCRIPTION
        "This object indicates the SSID used by the VAP."

     ::= {wsDetectedClientRoamHistoryEntry 6 }

 wsDetectedClientRoamAge OBJECT-TYPE
     SYNTAX       TimeTicks
     MAX-ACCESS   read-only
     STATUS       current
     DESCRIPTION
        "Indicates time since this roam history event occured."
     ::= {wsDetectedClientRoamHistoryEntry 7 }

  wsDetectedClientRoamStatus     OBJECT-TYPE
     SYNTAX        INTEGER {
                    newAuthentication(1),
                    roam(2)
                   }
     MAX-ACCESS   read-only
     STATUS       current
     DESCRIPTION
        "Designates the roaming operational status for
        this detected client."
     ::= {wsDetectedClientRoamHistoryEntry 8 }

 wsDetectedClientRoamHistoryPurgeAll OBJECT-TYPE
     SYNTAX       INTEGER {
                  enable(1),
                  disable(2)
                  }
     MAX-ACCESS   read-only
     STATUS       current
     DESCRIPTION
                  "This is an action object. Setting this object to enable
                  will purge all the roaming history entries for all the
                  detected clients. Read on this object will always return
                  disable."
     ::= { intrusionDetection 20 }


--**************************************************************************************
-- rrmNeighbor
--**************************************************************************************
--
--  Radio Resource Measurement (RRM) Neighbor Table
--
 wsRrmNeighborTable OBJECT-TYPE
   SYNTAX       SEQUENCE OF WsRrmNeighborEntry
   MAX-ACCESS   not-accessible
   STATUS       current
   DESCRIPTION
     "This table displays the known neighbors of each AP/VAP pair as
      reported through RF scans that conform to the IEEE 802.11k standards
      for Radio Resource Measurement (RRM)."

   ::= { rrmNeighbor 1 }

 wsRrmNeighborEntry OBJECT-TYPE
     SYNTAX       WsRrmNeighborEntry
     MAX-ACCESS   not-accessible
     STATUS       current
     DESCRIPTION
     "Each entry provides information regarding known neighboring
      APs that may be suitable for client roaming."
     INDEX    { wsRrmNeighborApMacAddr,
                wsRrmNeighborVapMacAddr,
                wsRrmNeighborMacAddr   }
     ::= { wsRrmNeighborTable 1 }

 WsRrmNeighborEntry ::=
     SEQUENCE {
         wsRrmNeighborApMacAddr            MacAddress,
         wsRrmNeighborVapMacAddr           MacAddress,
         wsRrmNeighborMacAddr              MacAddress,
         wsRrmNeighborRSSI                 Integer32,
         wsRrmNeighborSSID                 DisplayString,
         wsRrmNeighborChannel              Integer32,
         wsRrmNeighborAge                  TimeTicks,
         wsRrmNeighborAllPurge             INTEGER,
         wsRrmNeighborApPurge              INTEGER,
         wsRrmNeighborVapPurge             INTEGER
     }

 wsRrmNeighborApMacAddr      OBJECT-TYPE
     SYNTAX       MacAddress
     MAX-ACCESS   not-accessible
     STATUS       current
     DESCRIPTION
       "The MAC address of the managed AP that detected the neighbor."
     ::= {wsRrmNeighborEntry 1 }

 wsRrmNeighborVapMacAddr      OBJECT-TYPE
     SYNTAX       MacAddress
     MAX-ACCESS   not-accessible
     STATUS       current
     DESCRIPTION
       "The MAC address of the VAP that detected the neighbor."
     ::= {wsRrmNeighborEntry 2 }

 wsRrmNeighborMacAddr      OBJECT-TYPE
     SYNTAX       MacAddress
     MAX-ACCESS   not-accessible
     STATUS       current
     DESCRIPTION
       "The MAC address of the detected neighbor."
     ::= {wsRrmNeighborEntry 3 }

 wsRrmNeighborRSSI      OBJECT-TYPE
     SYNTAX       Integer32(0..100)
     MAX-ACCESS   not-accessible
     STATUS       current
     DESCRIPTION
       "The RSSI (signal strength) of the detected neighbor."
     ::= {wsRrmNeighborEntry 4 }

 wsRrmNeighborSSID      OBJECT-TYPE
     SYNTAX       DisplayString(SIZE(0..32))
     MAX-ACCESS   not-accessible
     STATUS       current
     DESCRIPTION
       "The SSID of the detected neighbor."
     ::= {wsRrmNeighborEntry 5 }

 wsRrmNeighborChannel    OBJECT-TYPE
     SYNTAX       Integer32(0..14|36|40|42|44|48|50|52|56|58|60|
                            64|100|104|108|112|116|120|124|128|132|
                            136|140|149|152|153|157|160|161|165)
     MAX-ACCESS   not-accessible
     STATUS       current
     DESCRIPTION
       "The channel of the detected neighbor."
     ::= {wsRrmNeighborEntry 6 }

 wsRrmNeighborAge  OBJECT-TYPE
     SYNTAX       TimeTicks
     MAX-ACCESS   not-accessible
     STATUS       current
     DESCRIPTION
       "The age, in seconds, of this table entry for the detected neighbor."
     ::= {wsRrmNeighborEntry 7 }

 wsRrmNeighborAllPurge OBJECT-TYPE
     SYNTAX       INTEGER {
                    enable(1),
                    disable(2)
                  }
     MAX-ACCESS   not-accessible
     STATUS       current
     DESCRIPTION
        "This is an action object used to purge all neighbors.
         Reads on this object will always return disable."
     ::= {wsRrmNeighborEntry 8 }

 wsRrmNeighborApPurge OBJECT-TYPE
     SYNTAX       INTEGER {
                    enable(1),
                    disable(2)
                  }
     MAX-ACCESS   not-accessible
     STATUS       current
     DESCRIPTION
        "This is an action object used to purge all neighbors
         detected by the managed AP described by this entry.
         Reads on this object will always return disable."
     ::= {wsRrmNeighborEntry 9 }

 wsRrmNeighborVapPurge OBJECT-TYPE
     SYNTAX       INTEGER {
                    enable(1),
                    disable(2)
                  }
     MAX-ACCESS   not-accessible
     STATUS       current
     DESCRIPTION
        "This is an action object used to purge all neighbors
         detected by the VAP described by this entry.
         Reads on this object will always return disable."
     ::= {wsRrmNeighborEntry 10 }


--
--  RRM Neighbor Table
--

--**************************************************************************************
-- rrmChannelLoad
--**************************************************************************************
--
--  Radio Resource Measurement (RRM) Channel Load Measurement History Table
--
--

 wsRrmChannelLoadHistoryTable OBJECT-TYPE
   SYNTAX       SEQUENCE OF WsRrmChannelLoadHistoryEntry
   MAX-ACCESS   not-accessible
   STATUS       current
   DESCRIPTION
     "This table displays the known channel load measurement history items.
      Channel load measurements are part of the IEEE 802.11k standards
      for Radio Resource Measurement (RRM)."
     ::= { rrmChannelLoad 1 }

 wsRrmChannelLoadHistoryEntry OBJECT-TYPE
     SYNTAX       WsRrmChannelLoadHistoryEntry
     MAX-ACCESS   not-accessible
     STATUS       current
     DESCRIPTION
     "Each entry provides information regarding previous channel load
      measurement reports from clients ."
     INDEX    { wsRrmChannelLoadHistoryEntryId }
     ::= { wsRrmChannelLoadHistoryTable 1 }

 WsRrmChannelLoadHistoryEntry ::=
     SEQUENCE {
         wsRrmChannelLoadHistoryEntryId              Unsigned32,
         wsRrmChannelLoadHistoryEntryApMacAddr       MacAddress,
         wsRrmChannelLoadHistoryEntryClientMacAddr   MacAddress,
         wsRrmChannelLoadHistoryEntryChannel         Unsigned32,
         wsRrmChannelLoadHistoryEntryDuration        Unsigned32,
         wsRrmChannelLoadHistoryEntryAge             TimeTicks,
         wsRrmChannelLoadHistoryEntryLoad            Unsigned32
     }

 wsRrmChannelLoadHistoryEntryId        OBJECT-TYPE
     SYNTAX       Unsigned32
     MAX-ACCESS   not-accessible
     STATUS       current
     DESCRIPTION
       "A unique identifier for a history entry."
     ::= {wsRrmChannelLoadHistoryEntry 1 }

 wsRrmChannelLoadHistoryEntryApMacAddr      OBJECT-TYPE
     SYNTAX       MacAddress
     MAX-ACCESS   not-accessible
     STATUS       current
     DESCRIPTION
       "The MAC address of the managed AP associated to the client."
     ::= {wsRrmChannelLoadHistoryEntry 2 }

 wsRrmChannelLoadHistoryEntryClientMacAddr      OBJECT-TYPE
     SYNTAX       MacAddress
     MAX-ACCESS   not-accessible
     STATUS       current
     DESCRIPTION
       "The MAC address of client that conducted the measurement."
     ::= {wsRrmChannelLoadHistoryEntry 3 }

 wsRrmChannelLoadHistoryEntryChannel    OBJECT-TYPE
     SYNTAX       Unsigned32(0..14|36|40|42|44|48|50|52|56|58|60|
                            64|100|104|108|112|116|120|124|128|132|
                            136|140|149|152|153|157|160|161|165)
     MAX-ACCESS   not-accessible
     STATUS       current
     DESCRIPTION
       "The channel used for the measurement."
     ::= {wsRrmChannelLoadHistoryEntry 4 }

 wsRrmChannelLoadHistoryEntryAge        OBJECT-TYPE
     SYNTAX       TimeTicks
     MAX-ACCESS   not-accessible
     STATUS       current
     DESCRIPTION
       "The age of the measurement history entry."
     ::= {wsRrmChannelLoadHistoryEntry 5 }

 wsRrmChannelLoadHistoryEntryLoad      OBJECT-TYPE
     SYNTAX       Unsigned32(0..100)
     MAX-ACCESS   not-accessible
     STATUS       current
     DESCRIPTION
       "The measured load, expressed as a percentage."
     ::= {wsRrmChannelLoadHistoryEntry 6 }

 wsRrmChannelLoadHistoryEntryDuration      OBJECT-TYPE
     SYNTAX       Unsigned32(0..65535)
     MAX-ACCESS   not-accessible
     STATUS       current
     DESCRIPTION
       "The duration of the measurement, expressed in time units (TUs), where
        one TU equals 1024 microseconds."
     ::= {wsRrmChannelLoadHistoryEntry 7 }

--
--  RRM Channel Load Table
--



--
--  Radio Resource Measurement (RRM) Channel Load Measurement Current Request
--

 wsRrmChannelLoadCurrentRequest OBJECT IDENTIFIER ::= { rrmChannelLoad 2 }

  wsRrmChannelLoadCurrentRequestClientMacAddr      OBJECT-TYPE
     SYNTAX       MacAddress
     MAX-ACCESS   not-accessible
     STATUS       current
     DESCRIPTION
       "The MAC address of client involved with the request."
     ::= { wsRrmChannelLoadCurrentRequest 1 }

  wsRrmChannelLoadCurrentRequestApMacAddr      OBJECT-TYPE
     SYNTAX       MacAddress
     MAX-ACCESS   not-accessible
     STATUS       current
     DESCRIPTION
       "The MAC address of the managed AP associated with the client
        involved with the request."
     ::= { wsRrmChannelLoadCurrentRequest 2 }

  wsRrmChannelLoadCurrentRequestChannel    OBJECT-TYPE
     SYNTAX       Unsigned32(0..14|36|40|42|44|48|50|52|56|58|60|
                            64|100|104|108|112|116|120|124|128|132|
                            136|140|149|152|153|157|160|161|165)
     MAX-ACCESS   not-accessible
     STATUS       current
     DESCRIPTION
       "The channel specified within the current request."
     ::= { wsRrmChannelLoadCurrentRequest 3 }

  wsRrmChannelLoadCurrentRequestDuration      OBJECT-TYPE
     SYNTAX       Unsigned32(0..65535)
     MAX-ACCESS   not-accessible
     STATUS       current
     DESCRIPTION
       "The duration specified in the current request, expressed
        in time units (TUs), where one TU equals 1024 microseconds."
     ::= { wsRrmChannelLoadCurrentRequest 4 }

  wsRrmChannelLoadCurrentRequestStatus          OBJECT-TYPE
     SYNTAX       INTEGER {
                    notStarted(0),
                    success(1),
                    inProgress(2),
                    timedOut(3),
                    aborted(4),
                    incapable(5),
                    refused(6)
                  }
     MAX-ACCESS   not-accessible
     STATUS       current
     DESCRIPTION
       "The status of the current request."
     ::= { wsRrmChannelLoadCurrentRequest 5 }

  wsRrmChannelLoadCurrentRequestTimeRemaining        OBJECT-TYPE
     SYNTAX       TimeTicks
     MAX-ACCESS   not-accessible
     STATUS       current
     DESCRIPTION
       "The time remaining for the current request."
     ::= { wsRrmChannelLoadCurrentRequest 6 }

  wsRrmChannelLoadCurrentRequestAbort        OBJECT-TYPE
     SYNTAX       INTEGER {
                    no(0),
                    yes(1)
                  }
     MAX-ACCESS   not-accessible
     STATUS       current
     DESCRIPTION
       "Aborts a pending request if 'yes' given as value.
        Reads of this element will always return 'no'."
     ::= {wsRrmChannelLoadCurrentRequest 7 }

--
--  Radio Resource Measurement (RRM) Channel Load Measurement Current Request
--


--
--  Radio Resource Measurement (RRM) Channel Load Measurement New Request Handler
--

 wsRrmChannelLoadNewRequest  OBJECT IDENTIFIER ::= { rrmChannelLoad 3 }

  wsRrmChannelLoadNewRequestClientMacAddr      OBJECT-TYPE
     SYNTAX       MacAddress
     MAX-ACCESS   not-accessible
     STATUS       current
     DESCRIPTION
       "The MAC address of client chosen to execute the new request."
     ::= { wsRrmChannelLoadNewRequest 1 }

  wsRrmChannelLoadNewRequestChannel    OBJECT-TYPE
     SYNTAX       Unsigned32(0..14|36|40|42|44|48|50|52|56|58|60|64|
                               100|104|108|112|116|120|124|128|132|
                               136|140|149|152|153|157|160|161|165)
     MAX-ACCESS   not-accessible
     STATUS       current
     DESCRIPTION
       "The channel to be used in the next submitted request."
     ::= {wsRrmChannelLoadNewRequest 2 }

  wsRrmChannelLoadNewRequestDuration      OBJECT-TYPE
     SYNTAX       Unsigned32(0..65535)
     MAX-ACCESS   not-accessible
     STATUS       current
     DESCRIPTION
       "The duration to be used in the next request, expressed
        in time units (TUs), where one TU equals 1024 microseconds."
     DEFVAL       { 1000 }
     ::= {wsRrmChannelLoadNewRequest 3 }

  wsRrmChannelLoadNewRequestSend       OBJECT-TYPE
     SYNTAX       INTEGER {
                    no(0),
                    yes(1)
                  }
     MAX-ACCESS   not-accessible
     STATUS       current
     DESCRIPTION
       "Sends a new request if 'yes' given as value.
        Reads of this element will always return 'no'."
     ::= {wsRrmChannelLoadNewRequest 4 }


--
--  Radio Resource Measurement (RRM) Channel Load Measurement New Request Handler
--




--**************************************************************************************
-- wsCapability
--**************************************************************************************
--
--  AP Hardware Capability Table
--
 wsAPHardwareCapabilityTable OBJECT-TYPE
   SYNTAX       SEQUENCE OF WsAPHardwareCapabilityEntry
   MAX-ACCESS   not-accessible
   STATUS       current
   DESCRIPTION
     "This table defines supported features for APs of specific
      hardware type. This is a read only table and is used by
      application to validate parameters  "
   ::= { wsCapability 1 }

 wsAPHardwareCapabilityEntry OBJECT-TYPE
     SYNTAX       WsAPHardwareCapabilityEntry
     MAX-ACCESS   not-accessible
     STATUS       current
     DESCRIPTION
     "Each entry provides access point hardware type details for each
     AP hardware type supported by the WS."
     INDEX    { wsAPHWTypeID }
     ::= { wsAPHardwareCapabilityTable 1 }

 WsAPHardwareCapabilityEntry ::=
     SEQUENCE {
         wsAPHWTypeID                    Integer32,
         wsAPHWTypeDescription           DisplayString,
         wsAPHWTypeRadioCount            Integer32,
         wsAPImageTypeID                 Integer32,
         wsAPHWDualBootSuppport          INTEGER
 }

 wsAPHWTypeID    OBJECT-TYPE
     SYNTAX      Integer32(1..13)
     MAX-ACCESS  not-accessible
     STATUS      current
     DESCRIPTION
       "Numeric identifier for the AP hardware type."
     ::= { wsAPHardwareCapabilityEntry 1 }

 wsAPHWTypeDescription    OBJECT-TYPE
     SYNTAX      DisplayString(SIZE(1..32))
     MAX-ACCESS  not-accessible
     STATUS      current
     DESCRIPTION
        "Descriptive name of the AP hardware type."
     ::= { wsAPHardwareCapabilityEntry 2 }

 wsAPHWTypeRadioCount     OBJECT-TYPE
     SYNTAX      Integer32(1..2)
     MAX-ACCESS  not-accessible
     STATUS      current
     DESCRIPTION
       "Number of radios supported by this hardware type AP."
     ::= { wsAPHardwareCapabilityEntry 3 }

 wsAPImageTypeID     OBJECT-TYPE
     SYNTAX      Integer32(1..2)
     MAX-ACCESS  not-accessible
     STATUS      current
     DESCRIPTION
       "Image type for code download for this hardware type AP."
     ::= { wsAPHardwareCapabilityEntry 4 }

 wsAPHWDualBootSuppport    OBJECT-TYPE
     SYNTAX       INTEGER {
                     notsupported(0),
                     supported(1)
                  }
     MAX-ACCESS   not-accessible
     STATUS       current
     DESCRIPTION
       "Dual boot support for this hardware type AP."
     ::= { wsAPHardwareCapabilityEntry 5 }


--
--  AP Hardware Capability Table Ends
--

--
--  AP Hardware Radio Capability Table
--

 wsAPHardwareRadioCapabilityTable OBJECT-TYPE
     SYNTAX       SEQUENCE OF WsAPHardwareRadioCapabilityEntry
     MAX-ACCESS   not-accessible
     STATUS       current
     DESCRIPTION
     "The AP harware radio capability table contain only those
     parameters that vary from one AP hardware type to another.
     Parameters that don't vary depending on AP type or radio type
     are not included in the table.This read-only table provides the
     user to view configurable parameters for the APs of specific
     hardware type through the profile."
     ::= { wsCapability 2 }

 wsAPHardwareRadioCapabilityEntry OBJECT-TYPE
     SYNTAX       WsAPHardwareRadioCapabilityEntry
     MAX-ACCESS   not-accessible
     STATUS       current
     DESCRIPTION
     "Each entry provides radio capability details for each AP hardware
     type supported by the WS."
     INDEX    { wsAPHWTypeID,wsAPHWTypeRadioNum }
     ::= { wsAPHardwareRadioCapabilityTable 1 }

 WsAPHardwareRadioCapabilityEntry ::=
     SEQUENCE {
     wsAPHWTypeRadioNum                             Integer32,
     wsAPHWTypeRadioID                              Integer32,
     wsAPHWTypeRadioDescription                     DisplayString,
     wsAPHWTypeRadioVapCount                        Integer32,
     wsAPHWTypeRadioAmodeSupport                    INTEGER,
     wsAPHWTypeRadioBGmodeSupport                   INTEGER,
     wsAPHWTypeRadioNmodeSupport                    INTEGER,
     wsAPHWTypeRadioACmodeSupport                   INTEGER
 }

 wsAPHWTypeRadioNum     OBJECT-TYPE
     SYNTAX      Integer32(1..2)
     MAX-ACCESS  not-accessible
     STATUS      current
     DESCRIPTION
       "The radio number of this radio in the AP."
     ::= { wsAPHardwareRadioCapabilityEntry 1 }

 wsAPHWTypeRadioID     OBJECT-TYPE
     SYNTAX      Integer32(1..43421)
     MAX-ACCESS  read-only
     STATUS      current
     DESCRIPTION
       "The device id for this radio in the AP."
     ::= { wsAPHardwareRadioCapabilityEntry 2 }

 wsAPHWTypeRadioDescription     OBJECT-TYPE
     SYNTAX      DisplayString(SIZE(1..32))
     MAX-ACCESS  not-accessible
     STATUS      current
     DESCRIPTION
       "Text description of this radio type."
     ::= { wsAPHardwareRadioCapabilityEntry 3 }

 wsAPHWTypeRadioVapCount     OBJECT-TYPE
     SYNTAX      Integer32(1..16)
     MAX-ACCESS  not-accessible
     STATUS      current
     DESCRIPTION
       "Number of virtual access points supported by this radio."
     ::= { wsAPHardwareRadioCapabilityEntry 4 }

 wsAPHWTypeRadioAmodeSupport     OBJECT-TYPE
     SYNTAX       INTEGER {
                      enable(1),
                      disable(2)
                  }
     MAX-ACCESS  not-accessible
     STATUS      current
     DESCRIPTION
       "Flag indicating whether this radio supports 802.11a mode."
     ::= { wsAPHardwareRadioCapabilityEntry 5 }
 wsAPHWTypeRadioBGmodeSupport     OBJECT-TYPE
     SYNTAX       INTEGER {
                      enable(1),
                      disable(2)
                  }
     MAX-ACCESS  not-accessible
     STATUS      current
     DESCRIPTION
       "Flag indicating whether this radio supports 802.11bg mode."
     ::= { wsAPHardwareRadioCapabilityEntry 6 }

 wsAPHWTypeRadioNmodeSupport     OBJECT-TYPE
     SYNTAX       INTEGER {
                      enable(1),
                      disable(2)
                  }
     MAX-ACCESS  not-accessible
     STATUS      current
     DESCRIPTION
       "Flag indicating whether this radio supports 802.11n
       configuration parameters."
     ::= { wsAPHardwareRadioCapabilityEntry 7 }

 wsAPHWTypeRadioACmodeSupport     OBJECT-TYPE
     SYNTAX       INTEGER {
                      enable(1),
                      disable(2)
                  }
     MAX-ACCESS  read-only
     STATUS      current
     DESCRIPTION
       "Flag indicating whether this radio supports 802.11ac
       configuration parameters."
     ::= { wsAPHardwareRadioCapabilityEntry 8 }

--
--  AP Hardware Radio Capability Table Ends
--

--
--  AP Image Capability Table
--
 wsAPImageTypeCapabilityTable OBJECT-TYPE
   SYNTAX       SEQUENCE OF WsAPImageTypeCapabilityEntry
   MAX-ACCESS   not-accessible
   STATUS       current
   DESCRIPTION
     "This table defines supported image types for APs. This is a read
      only table and is used by application to view possible image types"
   ::= { wsCapability 3 }

 wsAPImageTypeCapabilityEntry OBJECT-TYPE
     SYNTAX       WsAPImageTypeCapabilityEntry
     MAX-ACCESS   not-accessible
     STATUS       current
     DESCRIPTION
     "Each entry provides access point image type details for each
     AP image type supported by the WS."
     INDEX    { wsAPImageTypeID }
     ::= { wsAPImageTypeCapabilityTable 1 }

   WsAPImageTypeCapabilityEntry ::=
       SEQUENCE {
       wsAPImageTypeDescription           DisplayString
   }
   wsAPImageTypeDescription    OBJECT-TYPE
       SYNTAX      DisplayString(SIZE(1..96))
       MAX-ACCESS  not-accessible
       STATUS      current
       DESCRIPTION
          "Descriptive name of the AP image type."
       ::= { wsAPImageTypeCapabilityEntry 1 }
--
--  AP Image Capability Table Ends
--

--
--  AP Image Availability Table
--
    wsAPImageAvailabilityTable OBJECT-TYPE
         SYNTAX      SEQUENCE OF WsAPImageAvailabilityEntry
         MAX-ACCESS  not-accessible
         STATUS      current
         DESCRIPTION
               "This table lists the wireless controller stored AP code images."
         ::= { wsCapability 4 }

    wsAPImageAvailabilityEntry OBJECT-TYPE
         SYNTAX      WsAPImageAvailabilityEntry
         MAX-ACCESS  not-accessible
         STATUS      current
         DESCRIPTION
               "Each entry provides the code version of an AP image stored on the wireless controller."
         INDEX    { wsAPImageTypeID }
         ::= { wsAPImageAvailabilityTable 1 }

    WsAPImageAvailabilityEntry ::= SEQUENCE {
         wsAPImageAvailability    DisplayString
    }

    wsAPImageAvailability    OBJECT-TYPE
         SYNTAX      DisplayString
         MAX-ACCESS  not-accessible
         STATUS      current
         DESCRIPTION
               "The code version of each AP image stored on the wireless controller."
         ::= { wsAPImageAvailabilityEntry 1 }
--
--  AP Image Availability Table Ends
--


--**************************************************************************************
-- snmpTrapsConfig
--**************************************************************************************
    wsStatusTrapMode    OBJECT-TYPE
         SYNTAX     INTEGER {
                         enable(1),
                         disable(2)
                    }
         MAX-ACCESS  read-only
         STATUS      current
         DESCRIPTION
                     "Flag to enable/disable SNMP traps for:
                        WS Enabled,
                        WS Disabled,
                        WS Managed AP Database Full,
                        WS Managed AP - AP Neighbor List Full,
                        WS Managed AP - Client Neighbor List Full,
                        WS - AP Failure List Full,
                        RF Scan AP List Full,
                        Client Association Database Full,
                        Client Failure List Full."
         DEFVAL      { disable }
         ::= { snmpTrapsConfig 1 }

-- Object not supported in SMB builds
    wsPeerWSTrapMode    OBJECT-TYPE
         SYNTAX     INTEGER {
                         enable(1),
                         disable(2)
                    }
         MAX-ACCESS  read-only
         STATUS      current
         DESCRIPTION
                     "Flag to enable/disable SNMP traps for:
                         Peer WS Discovered,
                         Peer WS Failed,
                         Peer WS Unknown Protocol Discovered."
         DEFVAL      { disable }
         ::= { snmpTrapsConfig 2 }

    wsAPStateTrapMode    OBJECT-TYPE
         SYNTAX     INTEGER {
                         enable(1),
                         disable(2)
                    }
         MAX-ACCESS  read-only
         STATUS      current
         DESCRIPTION
                     "Flag to enable/disable SNMP traps for:
                         WS Managed AP Discovered,
                         WS Managed AP Failed,
                         WS Managed AP Unknown Protocol Discovered."
         DEFVAL      { disable }
         ::= { snmpTrapsConfig 3 }

    wsAPFailureTrapMode    OBJECT-TYPE
         SYNTAX     INTEGER {
                         enable(1),
                         disable(2)
                    }
         MAX-ACCESS  read-only
         STATUS      current
         DESCRIPTION
                     "Flag to enable/disable SNMP traps for:
                         WS AP Association Failure,
                         WS AP Authentication Failure."
         DEFVAL      { disable }
         ::= { snmpTrapsConfig 4 }

    wsRogueAPTrapMode    OBJECT-TYPE
         SYNTAX     INTEGER {
                         enable(1),
                         disable(2)
                    }
         MAX-ACCESS  read-only
         STATUS      current
         DESCRIPTION
                     "Flag to enable/disable SNMP traps for:
                         RF Scan Rogue AP Detected."
         DEFVAL      { disable }
         ::= { snmpTrapsConfig 5 }

    wsRFScanTrapMode    OBJECT-TYPE
         SYNTAX     INTEGER {
                         enable(1),
                         disable(2)
                    }
         MAX-ACCESS  read-only
         STATUS      current
         DESCRIPTION
                     "Flag to enable/disable SNMP traps for:
                           RF Scan New AP Detected,
                           RF Scan New Client Detected.
                           RF Scan Ad hoc Client Detected."
         DEFVAL      { disable }
         ::= { snmpTrapsConfig 6 }

    wsClientStateTrapMode    OBJECT-TYPE
         SYNTAX     INTEGER {
                         enable(1),
                         disable(2)
                    }
         MAX-ACCESS  read-only
         STATUS      current
         DESCRIPTION
                     "Flag to enable/disable SNMP traps for:
                            Client Association Detected,
                            Client Disassociation Detected,
                            Client Roam Detected."
         DEFVAL      { disable }
         ::= { snmpTrapsConfig 7 }

    wsWidsStatusMode    OBJECT-TYPE
         SYNTAX     INTEGER {
                         enable(1),
                         disable(2)
                    }
         MAX-ACCESS  read-only
         STATUS      current
         DESCRIPTION
                     "Flag to enable/disable SNMP traps for:
                         This controller is Cluster Controller,
                         Rogues are Present in the Network,
                         RF Scan Rogue AP Detected."
         DEFVAL      { disable }
         ::= { snmpTrapsConfig 8 }

    wsTspecTrapMode    OBJECT-TYPE
         SYNTAX     INTEGER {
                         enable(1),
                         disable(2)
                    }
         MAX-ACCESS  not-accessible
         STATUS      current
         DESCRIPTION
                     "Flag to enable/disable SNMP traps for:
                           TSPEC Client ACM Bandwidth Exceeded,
                           TSPEC Client Traffic Unauthorized."
         DEFVAL      { disable }
         ::= { snmpTrapsConfig 9 }
    wsClientFailureTrapMode    OBJECT-TYPE
         SYNTAX     INTEGER {
                         enable(1),
                         disable(2)
                    }
         MAX-ACCESS  read-only
         STATUS      current
         DESCRIPTION
                     "Flag to enable/disable SNMP traps for:
                           Client Association Failure,
                           Client Authentication Failure."
         DEFVAL      { disable }
         ::= { snmpTrapsConfig 10 }

--**************************************************************************************
-- wsTraps
--**************************************************************************************
 wsModeEnabled NOTIFICATION-TYPE
    STATUS  current
    DESCRIPTION
       "A wsModeEnabled trap signifies that the SNMP entity, acting in
        an agent role, has detected that Wireless functionality on the
        device is enabled."
    ::= { wsTraps 1 }

 wsModeDisabled NOTIFICATION-TYPE
    STATUS  current
    DESCRIPTION
       "A wsModeDisabled trap signifies that the SNMP entity, acting in
        an agent role, has detected that Wireless functionality on the
        device is disabled."
    ::= { wsTraps 2 }

 wsManagedAPDatabaseFull NOTIFICATION-TYPE
    OBJECTS { wsManagedAPMacAddress }
    STATUS  current
    DESCRIPTION
       "A wsAPDatabaseFull trap signifies that the SNMP entity, acting in
        an agent role, has detected that AP Database is full."
    ::= { wsTraps 3 }

 wsManagedAPNeighborAPListFull NOTIFICATION-TYPE
    STATUS  current
    DESCRIPTION
       "A wsManagedAPNeighborListFull trap signifies that the SNMP entity, acting in
        an agent role, has detected that ManagedAP neighbor AP list is full."
    ::= { wsTraps 4 }

 wsManagedAPNeighborClientListFull NOTIFICATION-TYPE
    STATUS  current
    DESCRIPTION
       "A wsManagedAPNeighborClientListFull trap signifies that the SNMP entity, acting in
        an agent role, has detected that ManagedAP neighbor client list is full."
    ::= { wsTraps 5 }

 wsAPFailureListFull NOTIFICATION-TYPE
    STATUS  current
    DESCRIPTION
       "A wsAPFailureListFull trap signifies that the SNMP entity, acting in
        an agent role, has detected that AP failure list full."
    ::= { wsTraps 6 }

 wsRFScanAPListFull NOTIFICATION-TYPE
    STATUS  current
    DESCRIPTION
       "A wsRFScanAPListFull trap signifies that the SNMP entity, acting in
        an agent role, has detected that RF scan AP list is full."
    ::= { wsTraps 7 }

 wsClientAssociationDatabaseFull NOTIFICATION-TYPE
    OBJECTS { wsAssociatedClientMacAddress }
    STATUS  current
    DESCRIPTION
       "A wsClientAssociationDatabaseFull trap signifies that the SNMP entity, acting in
        an agent role, has detected that client association database is full."
    ::= { wsTraps 8 }

 wsPeerSwitchDiscovered NOTIFICATION-TYPE
    OBJECTS { wsPeerIpAddress }
    STATUS  current
    DESCRIPTION
       "A wsPeerSwitchDiscovered trap signifies that the SNMP entity, acting in
        an agent role, has detected peer controller in the network."
    ::= { wsTraps 9 }

 wsPeerSwitchFailed NOTIFICATION-TYPE
    OBJECTS { wsPeerIpAddress }
    STATUS  current
    DESCRIPTION
       "A wsPeerSwitchFailed trap signifies that the SNMP entity, acting in
        an agent role, has detected that peer controller connection failed."
    ::= { wsTraps 10 }

 wsPeerSwitchUnknownProtocol NOTIFICATION-TYPE
    OBJECTS { wsPeerIpAddress, wsPeerProtocolVersion }
    STATUS  current
    DESCRIPTION
       "A wsPeerSwitchUnknownProtocol trap signifies that the SNMP entity, acting in
        an agent role, has detected unknown protocol between wireless controller and peer controller
        communication."
    ::= { wsTraps 11 }

 wsManagedAPDiscovered NOTIFICATION-TYPE
    OBJECTS { wsManagedAPMacAddress }
    STATUS  current
    DESCRIPTION
       "A wsManagedAPDiscovered trap signifies that the SNMP entity, acting in
        an agent role, has detected the managed AP."
    ::= { wsTraps 12 }

 wsManagedAPFailed NOTIFICATION-TYPE
    OBJECTS { wsManagedAPMacAddress }
    STATUS  current
    DESCRIPTION
       "A wsManagedAPFailed trap signifies that the SNMP entity, acting in
        an agent role, has detected the failed AP."
    ::= { wsTraps 13 }

 wsManagedAPUnknownProtocol NOTIFICATION-TYPE
    OBJECTS { wsFailedAPMacAddress, wsFailedAPProtocolVersion }
    STATUS  current
    DESCRIPTION
       "A wsManagedAPUnknownProtocol trap signifies that the SNMP entity, acting in
        an agent role, has detected the unknown protocol between wireless controller and managed
        AP communication."
    ::= { wsTraps 14 }

 wsAPAssociationFailure NOTIFICATION-TYPE
    OBJECTS { wsFailedAPMacAddress }
    STATUS  current
    DESCRIPTION
       "A wsAPAssociationFailure trap signifies that the SNMP entity, acting in
        an agent role, has detected that AP association failed."
    ::= { wsTraps 15 }

 wsAPAuthenticationFailure NOTIFICATION-TYPE
    OBJECTS { wsFailedAPMacAddress }
    STATUS  current
    DESCRIPTION
       "A wsAPAuthenticationFailure trap signifies that the SNMP entity, acting in
        an agent role, has detected that AP authentication failed."
    ::= { wsTraps 16 }

 wsRFScanRogueAPDetected NOTIFICATION-TYPE
    OBJECTS { wsManagedAPMacAddress, wsManagedAPRadioInterface,
              wsRFScanAPMacAddress,wsRFScanAPSSID }
    STATUS  current
    DESCRIPTION
       "A wsRFScanRogueAPDetected trap signifies that the SNMP entity, acting in
        an agent role, has detected Rogue AP through RF Scan."
    ::= { wsTraps 17 }

 wsRFScanAPDetected NOTIFICATION-TYPE
    OBJECTS { wsManagedAPMacAddress, wsManagedAPRadioInterface,
              wsRFScanAPMacAddress,wsRFScanAPSSID }
    STATUS  current
    DESCRIPTION
       "A wsRFScanAPDetected trap signifies that the SNMP entity, acting in
        an agent role, has detected AP through RF Scan."
    ::= { wsTraps 18 }

 wsRFScanNewClientDetected NOTIFICATION-TYPE
    OBJECTS { wsManagedAPMacAddress, wsManagedAPRadioInterface,
              wsNeighborClientMacAddress }
    STATUS  current
    DESCRIPTION
       "A wsRFScanNewClientDetected trap signifies that the SNMP entity, acting in
        an agent role, has detected new client through RF Scan."
    ::= { wsTraps 19 }

 wsClientAssociationDetected NOTIFICATION-TYPE
    OBJECTS { wsAssociatedClientMacAddress,wsVAPMacAddress,
              wsManagedAPMacAddress }
    STATUS  current
    DESCRIPTION
       "A wsClientAssociationDetected trap signifies that the SNMP entity, acting in
        an agent role, has detected client association."
    ::= { wsTraps 20 }

 wsClientDisassociationDetected NOTIFICATION-TYPE
    OBJECTS { wsAssociatedClientMacAddress,wsVAPMacAddress,
              wsManagedAPMacAddress }
    STATUS  current
    DESCRIPTION
       "A wsClientDisassociationDetected trap signifies that the SNMP entity, acting in
        an agent role, has detected client disassociation."
    ::= { wsTraps 21 }

 wsClientRoamDetected NOTIFICATION-TYPE
    OBJECTS { wsAssociatedClientMacAddress,wsVAPMacAddress,
              wsManagedAPMacAddress }
    STATUS  current
    DESCRIPTION
       "A wsClientRoamDetected trap signifies that the SNMP entity, acting in
        an agent role, has detected client roaming."
    ::= { wsTraps 22 }

 wsClientAssociationFailure NOTIFICATION-TYPE
    OBJECTS { wsNeighborClientMacAddress }
    STATUS  current
    DESCRIPTION
       "A wsClientAssociationFailure trap signifies that the SNMP entity, acting in
        an agent role, has detected client association failure."
    ::= { wsTraps 23 }

 wsClientAuthenticationFailure NOTIFICATION-TYPE
    OBJECTS { wsNeighborClientMacAddress }
    STATUS  current
    DESCRIPTION
       "A wsAuthenticationFailure trap signifies that the SNMP entity, acting in
        an agent role, has detected client authentication failure."
    ::= { wsTraps 24 }

 wsAdHocClientDetected NOTIFICATION-TYPE
    OBJECTS { wsAdHocClientMacAddress, wsDetectedAPMacAddress,
              wsDetectedAPRadioInterface }
    STATUS  current
    DESCRIPTION
       "A wsAdHocClientDetected trap signifies that the SNMP entity, acting in
        an agent role, has detected Ad hoc client."
    ::= { wsTraps 25 }

 wsWLANBandwidthUtilizationExceeded NOTIFICATION-TYPE
    OBJECTS { wsManagedAPMacAddress, wsManagedAPRadioMacAddress,
              wsManagedAPRadioInterface,wsManagedAPRadioWLANUtilization }
    STATUS  current
    DESCRIPTION
       "A wsWLANBandwidthUtilizationExceeded trap signifies that the SNMP entity, acting in
        an agent role, has detected WLAN bandwidth utilization exceeding the limit."
    ::= { wsTraps 26 }

  wsAdHocClientListFull NOTIFICATION-TYPE
    STATUS  current
    DESCRIPTION
       "A wsAdHocClientListFull trap signifies that the SNMP entity,
        acting in an agent role, has detected that Ad hoc client database
        is full."
    ::= { wsTraps 27 }

 wsPeerSwitchConfigurationCommandReceived NOTIFICATION-TYPE
    OBJECTS { wsPeerIpAddress, wsPeerConfigReceived }
    STATUS  current
    DESCRIPTION
       "A wsPeerSwitchConfigurationCommandReceived trap signifies that the SNMP entity,
        acting in an agent role, has received Configuration command from the
        peer controller in the network. The config mask received is also returned
        in the trap."
    ::= { wsTraps 28 }

 wsPeerSwitchManagedAPLimitExceeded NOTIFICATION-TYPE
    OBJECTS { wsPeerIpAddress, wsPeerSwitchAPMacAddress }
    STATUS  current
    DESCRIPTION
       "A wsPeerSwitchManagedAPLimitExceeded trap signifies that the SNMP entity,
        acting in an agent role, has detected that the Peer controller Managed AP database
        limit has exceeded."
    ::= { wsTraps 29 }

 wsPeerSwitchClientLimitExceeded NOTIFICATION-TYPE
    OBJECTS { wsPeerIpAddress, wsAssociatedClientMacAddress }
    STATUS  current
    DESCRIPTION
       "A wsPeerSwitchClientLimitExceeded trap signifies that the SNMP entity, acting in
        an agent role, has detected that the Peer controller Client database limit
        has exceeded."
    ::= { wsTraps 30 }

 wsClusterControllerElected NOTIFICATION-TYPE
    OBJECTS { wsIPAddress }
    STATUS  current
    DESCRIPTION
       "A wsClusterControllerElected trap signifies that the SNMP entity, acting in
        an agent role, has elected itself as Cluster Controller in the peer group."
    ::= { wsTraps 32 }

 wsClusterMaxAPExceeded NOTIFICATION-TYPE
    OBJECTS { wsIPAddress, wsManagedAPMacAddress, wsManagedAPIpAddress, wsManagedAPSwitchIpAddress}
    STATUS  current
    DESCRIPTION
       "A wsClusterMaxAPExceeded trap signifies that the SNMP entity, acting in
        an agent role, has detected that the managed APs in the network has exceeded."
    ::= { wsTraps 33 }

 wsRoguesPresent NOTIFICATION-TYPE
    STATUS  current
    DESCRIPTION
       "A wsRoguesPresent trap signifies that the SNMP entity, acting in
        an agent role, has detected one or more Rogues present in the network."
    ::= { wsTraps 34 }

  wsDetectedClientListFull NOTIFICATION-TYPE
    STATUS  current
    DESCRIPTION
       "A wsDetectedClientListFull trap signifies that the SNMP entity,
        acting in an agent role, has detected that Detected client database
        is full."
    ::= { wsTraps 35 }

 wsRogueClientsPresent NOTIFICATION-TYPE
    STATUS  current
    DESCRIPTION
       "A wsRogueClientsPresent trap signifies that the SNMP entity, acting in
        an agent role, has detected one or more Rogue Clients present in the network."
    ::= { wsTraps 36 }

 wsChannelPlanAlgoComplete NOTIFICATION-TYPE
    STATUS  current
    DESCRIPTION
       "A wsChannelAlgorithmComplete trap signifies that the SNMP entity, acting in
        an agent role, has detected channel algorithm complete event."
    ::= { wsTraps 37 }

 wsPowerPlanAlgoComplete NOTIFICATION-TYPE
    STATUS  current
    DESCRIPTION
       "A wsPowerAlgorithmComplete trap signifies that the SNMP entity, acting in
        an agent role, has detected power algorithm complete event."
    ::= { wsTraps 38 }



 wsLocallyManagedAPLimitExceeded NOTIFICATION-TYPE
    OBJECTS { wsManagedAPMacAddress }
    STATUS  current
    DESCRIPTION
       "A wsLocallyManagedAPLimitExceeded trap signifies that the SNMP entity, acting in
        an agent role, has detected that the WS locally managed AP limit is exceeded."
    ::= { wsTraps 41 }

--**************************************************************************************
-- tspec (status and statistics) Begin
--**************************************************************************************

   tspecGlobal                           OBJECT IDENTIFIER ::= { tspec 1 }
   tspecSwitch                           OBJECT IDENTIFIER ::= { tspec 2 }
   tspecManagedAP                        OBJECT IDENTIFIER ::= { tspec 3 }
   tspecClient                           OBJECT IDENTIFIER ::= { tspec 4 }

--
--  wsGlobalTspecStatus
--
   wsGlobalTspecStatus                   OBJECT IDENTIFIER ::= { tspecGlobal 1 }

  wsTspecTotalVoiceTrafficStreams OBJECT-TYPE
         SYNTAX      Unsigned32
         MAX-ACCESS  not-accessible
         STATUS      current
         DESCRIPTION
               "Total number of traffic streams currently established
                for the voice access category.
                For a Cluster Controller, this value represents
                the entire cluster."
     ::= { wsGlobalTspecStatus 1 }

  wsTspecTotalVideoTrafficStreams OBJECT-TYPE
         SYNTAX      Unsigned32
         MAX-ACCESS  not-accessible
         STATUS      current
         DESCRIPTION
               "Total number of traffic streams currently established
                for the video access category.
                For a Cluster Controller, this value represents
                the entire cluster."
     ::= { wsGlobalTspecStatus 2 }

  wsTspecTotalTrafficStreamClients OBJECT-TYPE
         SYNTAX      Unsigned32
         MAX-ACCESS  not-accessible
         STATUS      current
         DESCRIPTION
               "Total number of clients that currently possess
                one or more traffic streams in any access category.
                For a Cluster Controller, this value represents
                the entire cluster."
     ::= { wsGlobalTspecStatus 3 }

  wsTspecTotalTrafficStreamRoamingClients OBJECT-TYPE
         SYNTAX      Unsigned32
         MAX-ACCESS  not-accessible
         STATUS      current
         DESCRIPTION
               "Total number of roaming clients that currently possess
                one or more traffic streams in any access category.
                For a Cluster Controller, this value represents
                the entire cluster."
     ::= { wsGlobalTspecStatus 4 }

--
--  wsGlobalTspecStatisticsTable
--
  wsGlobalTspecStatisticsTable OBJECT-TYPE
      SYNTAX       SEQUENCE OF WsGlobalTspecStatisticsEntry
      MAX-ACCESS   not-accessible
      STATUS       current
      DESCRIPTION
           "This table contains global TSPEC statistics indexed
            on a per access category (AC) basis."
      ::= { tspecGlobal 2 }

  wsGlobalTspecStatisticsEntry OBJECT-TYPE
      SYNTAX       WsGlobalTspecStatisticsEntry
      MAX-ACCESS   not-accessible
      STATUS       current
      DESCRIPTION
          "Each entry contains global TSPEC statistics indexed
           on a per access category (AC) basis for the wireless
           controller.  If this controller is a Cluster Controller, these
           object values represent the entire cluster."
      INDEX    { wsTspecACIndex }
      ::= { wsGlobalTspecStatisticsTable 1 }

  WsGlobalTspecStatisticsEntry ::=
      SEQUENCE {
          wsTspecACIndex                              TspecSuppAC,
          wsTotalWLANTspecPktsRecvd                   Counter64,
          wsTotalWLANTspecPktsTransmitted             Counter64,
          wsTotalWLANTspecBytesRecvd                  Counter64,
          wsTotalWLANTspecBytesTransmitted            Counter64,
          wsTotalWLANTspecsAccepted                   Counter32,
          wsTotalWLANTspecsRejected                   Counter32,
          wsTotalWLANRoamingTspecsAccepted            Counter32,
          wsTotalWLANRoamingTspecsRejected            Counter32
  }

  wsTspecACIndex OBJECT-TYPE
      SYNTAX       TspecSuppAC
      MAX-ACCESS   not-accessible
      STATUS       current
      DESCRIPTION
          "Access category (AC) index used for referencing objects in the
           table row.  Only those ACs that support mandatory admission control
           are available through this index.  The currently supported AC index
           values are:
                0 - Voice
                1 - Video
           "
      ::= { wsGlobalTspecStatisticsEntry 1 }

  wsTotalWLANTspecPktsRecvd    OBJECT-TYPE
       SYNTAX      Counter64
       MAX-ACCESS  not-accessible
       STATUS      current
       DESCRIPTION
            "Total packets received across all APs managed by
             this controller for all traffic streams belonging to
             the specified access category."
       ::= { wsGlobalTspecStatisticsEntry 2 }

  wsTotalWLANTspecPktsTransmitted    OBJECT-TYPE
       SYNTAX      Counter64
       MAX-ACCESS  not-accessible
       STATUS      current
       DESCRIPTION
            "Total packets transmitted across all APs managed by
             this controller for all traffic streams belonging to
             the specified access category."
       ::= { wsGlobalTspecStatisticsEntry 3 }

  wsTotalWLANTspecBytesRecvd    OBJECT-TYPE
       SYNTAX      Counter64
       MAX-ACCESS  not-accessible
       STATUS      current
       DESCRIPTION
            "Total bytes received across all APs managed by
             this controller for all traffic streams belonging to
             the specified access category."
       ::= { wsGlobalTspecStatisticsEntry 4 }

  wsTotalWLANTspecBytesTransmitted    OBJECT-TYPE
       SYNTAX      Counter64
       MAX-ACCESS  not-accessible
       STATUS      current
       DESCRIPTION
            "Total bytes transmitted across all APs managed by
             this controller for all traffic streams belonging to
             the specified access category."
       ::= { wsGlobalTspecStatisticsEntry 5 }

  wsTotalWLANTspecsAccepted    OBJECT-TYPE
       SYNTAX      Counter32
       MAX-ACCESS  not-accessible
       STATUS      current
       DESCRIPTION
            "Total number of TSPECs accepted across all APs managed by
             this controller for the specified access category."
       ::= { wsGlobalTspecStatisticsEntry 6 }

  wsTotalWLANTspecsRejected    OBJECT-TYPE
       SYNTAX      Counter32
       MAX-ACCESS  not-accessible
       STATUS      current
       DESCRIPTION
            "Total number of TSPECs rejected across all APs managed by
             this controller for the specified access category."
       ::= { wsGlobalTspecStatisticsEntry 7 }

  wsTotalWLANRoamingTspecsAccepted    OBJECT-TYPE
       SYNTAX      Counter32
       MAX-ACCESS  not-accessible
       STATUS      current
       DESCRIPTION
            "Total number of TSPECs accepted from roaming clients across
             all APs managed by this controller for the specified
             access category.

             The value of this object is also included in the
             wsTotalWLANTspecsAccepted object."
       ::= { wsGlobalTspecStatisticsEntry 8 }

  wsTotalWLANRoamingTspecsRejected    OBJECT-TYPE
       SYNTAX      Counter32
       MAX-ACCESS  not-accessible
       STATUS      current
       DESCRIPTION
            "Total number of TSPECs rejected from roaming clients across
             all APs managed by this controller for the specified
             access category.

             The value of this object is also included in the
             wsTotalWLANTspecsRejected object."
       ::= { wsGlobalTspecStatisticsEntry 9 }

--
--  wsSwitchTspecStatusTable
--
   wsSwitchTspecStatusTable OBJECT-TYPE
          SYNTAX       SEQUENCE OF WsSwitchTspecStatusEntry
          MAX-ACCESS   not-accessible
          STATUS       current
          DESCRIPTION
                "This table contains TSPEC status parameters
                 for peer controllers of the wireless controller."
                ::= { tspecSwitch 1 }

   wsSwitchTspecStatusEntry OBJECT-TYPE
          SYNTAX       WsSwitchTspecStatusEntry
          MAX-ACCESS   not-accessible
          STATUS       current
          DESCRIPTION
                "Each entry describes the TPEC status parameters
                 for a specific peer of the wireless controller."
          INDEX    { wsSwitchIPAddress }
          ::= { wsSwitchTspecStatusTable 1 }

   WsSwitchTspecStatusEntry ::=
     SEQUENCE {
         wsSwitchTspecTotalVoiceTrafficStreams              Unsigned32,
         wsSwitchTspecTotalVideoTrafficStreams              Unsigned32,
         wsSwitchTspecTotalTrafficStreamClients             Unsigned32,
         wsSwitchTspecTotalTrafficStreamRoamingClients      Unsigned32
     }

  wsSwitchTspecTotalVoiceTrafficStreams OBJECT-TYPE
         SYNTAX      Unsigned32
         MAX-ACCESS  not-accessible
         STATUS      current
         DESCRIPTION
               "Total number of traffic streams currently established for
                the voice access category for the specified controller."
     ::= { wsSwitchTspecStatusEntry 1 }

  wsSwitchTspecTotalVideoTrafficStreams OBJECT-TYPE
         SYNTAX      Unsigned32
         MAX-ACCESS  not-accessible
         STATUS      current
         DESCRIPTION
               "Total number of traffic streams currently established for
                the video access category for the specified controller."
     ::= { wsSwitchTspecStatusEntry 2 }

  wsSwitchTspecTotalTrafficStreamClients OBJECT-TYPE
         SYNTAX      Unsigned32
         MAX-ACCESS  not-accessible
         STATUS      current
         DESCRIPTION
               "Total number of clients that currently possess one or more
                traffic streams in any access category for the specified controller."
     ::= { wsSwitchTspecStatusEntry 3 }

  wsSwitchTspecTotalTrafficStreamRoamingClients OBJECT-TYPE
         SYNTAX      Unsigned32
         MAX-ACCESS  not-accessible
         STATUS      current
         DESCRIPTION
               "Total number of roaming clients that currently possess one or more
                traffic streams in any access category for the specified controller."
     ::= { wsSwitchTspecStatusEntry 4 }

--
--  wsSwitchTspecStatisticsTable
--
  wsSwitchTspecStatisticsTable OBJECT-TYPE
      SYNTAX       SEQUENCE OF WsSwitchTspecStatisticsEntry
      MAX-ACCESS   not-accessible
      STATUS       current
      DESCRIPTION
           "This table contains WLAN TSPEC statistics on a per access category (AC)
            basis for each controller in the peer group.  Only the Cluster Controller
            maintains entries for peer controllers.  A non-Cluster Controller controller
            just keeps its local statistics."
      ::= { tspecSwitch 2 }

  wsSwitchTspecStatisticsEntry OBJECT-TYPE
      SYNTAX       WsSwitchTspecStatisticsEntry
      MAX-ACCESS   not-accessible
      STATUS       current
      DESCRIPTION
          "Each entry contains WLAN TSPEC statistics on a per access category (AC)
           basis for the specified wireless controller."
      INDEX    { wsSwitchIPAddress, wsTspecACIndex }
      ::= { wsSwitchTspecStatisticsTable 1 }

  WsSwitchTspecStatisticsEntry ::=
      SEQUENCE {
          wsSwitchWLANTspecPktsRecvd                  Counter64,
          wsSwitchWLANTspecPktsTransmitted            Counter64,
          wsSwitchWLANTspecBytesRecvd                 Counter64,
          wsSwitchWLANTspecBytesTransmitted           Counter64,
          wsSwitchWLANTspecsAccepted                  Counter32,
          wsSwitchWLANTspecsRejected                  Counter32,
          wsSwitchWLANRoamingTspecsAccepted           Counter32,
          wsSwitchWLANRoamingTspecsRejected           Counter32
  }

  wsSwitchWLANTspecPktsRecvd    OBJECT-TYPE
       SYNTAX      Counter64
       MAX-ACCESS  not-accessible
       STATUS      current
       DESCRIPTION
            "Total packets received across all APs managed by
             this controller for all traffic streams belonging to
             the specified access category."
       ::= { wsSwitchTspecStatisticsEntry 1 }

  wsSwitchWLANTspecPktsTransmitted    OBJECT-TYPE
       SYNTAX      Counter64
       MAX-ACCESS  not-accessible
       STATUS      current
       DESCRIPTION
            "Total packets transmitted across all APs managed by
             this controller for all traffic streams belonging to
             the specified access category."
       ::= { wsSwitchTspecStatisticsEntry 2 }

  wsSwitchWLANTspecBytesRecvd    OBJECT-TYPE
       SYNTAX      Counter64
       MAX-ACCESS  not-accessible
       STATUS      current
       DESCRIPTION
            "Total bytes received across all APs managed by
             this controller for all traffic streams belonging to
             the specified access category."
       ::= { wsSwitchTspecStatisticsEntry 3 }

  wsSwitchWLANTspecBytesTransmitted    OBJECT-TYPE
       SYNTAX      Counter64
       MAX-ACCESS  not-accessible
       STATUS      current
       DESCRIPTION
            "Total bytes transmitted across all APs managed by
             this controller for all traffic streams belonging to
             the specified access category."
       ::= { wsSwitchTspecStatisticsEntry 4 }

  wsSwitchWLANTspecsAccepted    OBJECT-TYPE
       SYNTAX      Counter32
       MAX-ACCESS  not-accessible
       STATUS      current
       DESCRIPTION
            "Total number of TSPECs accepted across all APs managed by
             this controller for the specified access category."
       ::= { wsSwitchTspecStatisticsEntry 5 }

  wsSwitchWLANTspecsRejected    OBJECT-TYPE
       SYNTAX      Counter32
       MAX-ACCESS  not-accessible
       STATUS      current
       DESCRIPTION
            "Total number of TSPECs rejected across all APs managed by
             this controller for the specified access category."
       ::= { wsSwitchTspecStatisticsEntry 6 }

  wsSwitchWLANRoamingTspecsAccepted    OBJECT-TYPE
       SYNTAX      Counter32
       MAX-ACCESS  not-accessible
       STATUS      current
       DESCRIPTION
            "Total number of TSPECs accepted from roaming clients across
             all APs managed by this controller for the specified
             access category.

             This value of this object is also included in the
             wsSwitchWLANTspecsAccepted object."
       ::= { wsSwitchTspecStatisticsEntry 7 }

  wsSwitchWLANRoamingTspecsRejected    OBJECT-TYPE
       SYNTAX      Counter32
       MAX-ACCESS  not-accessible
       STATUS      current
       DESCRIPTION
            "Total number of TSPECs rejected from roaming clients across
             all APs managed by this controller for the specified
             access category.

             The value of this object is also included in the
             wsSwitchWLANTspecsRejected object."
       ::= { wsSwitchTspecStatisticsEntry 8 }

--
--   wsManagedAPTspecStatusTable
--
 wsManagedAPTspecStatusTable OBJECT-TYPE
     SYNTAX       SEQUENCE OF WsManagedAPTspecStatusEntry
     MAX-ACCESS   not-accessible
     STATUS       current
     DESCRIPTION
           "This table contains TSPEC status parameters for all APs
            managed by the controller."
     ::= { tspecManagedAP 1 }

    wsManagedAPTspecStatusEntry OBJECT-TYPE
     SYNTAX       WsManagedAPTspecStatusEntry
     MAX-ACCESS   not-accessible
     STATUS       current
     DESCRIPTION
          "Each entry in this table contains TSPEC status parameters for
           a specific AP managed by the controller."
     INDEX    { wsManagedAPMacAddress, wsTspecACIndex }
     ::= { wsManagedAPTspecStatusTable 1 }

 WsManagedAPTspecStatusEntry ::=
     SEQUENCE {
      wsManagedAPTspecNumActiveTrafficStreams             Unsigned32,
      wsManagedAPTspecNumTrafficStreamClients             Unsigned32,
      wsManagedAPTspecNumTrafficStreamRoamingClients      Unsigned32
 }

 wsManagedAPTspecNumActiveTrafficStreams OBJECT-TYPE
     SYNTAX       Unsigned32
     MAX-ACCESS   not-accessible
     STATUS       current
     DESCRIPTION
        "Indicates the current number of active traffic streams (TSs)
         for the specified access category of the WS managed AP."
     ::= { wsManagedAPTspecStatusEntry 1 }

 wsManagedAPTspecNumTrafficStreamClients OBJECT-TYPE
     SYNTAX       Unsigned32
     MAX-ACCESS   not-accessible
     STATUS       current
     DESCRIPTION
        "Indicates the current number of clients with at least one
         active traffic stream (TS) for the specified access category
         of the WS managed AP."
     ::= { wsManagedAPTspecStatusEntry 2 }

 wsManagedAPTspecNumTrafficStreamRoamingClients OBJECT-TYPE
     SYNTAX       Unsigned32
     MAX-ACCESS   not-accessible
     STATUS       current
     DESCRIPTION
        "Indicates the current number of roaming clients with at least one
         active traffic stream (TS) for the specified access category
         of the WS managed AP.

         The value of this object is also included in the
         wsManagedAPTspecNumTSClients object."
     ::= { wsManagedAPTspecStatusEntry 3 }

--
-- wsManagedAPTspecStatisticsTable
--
 wsManagedAPTspecStatisticsTable OBJECT-TYPE
     SYNTAX       SEQUENCE OF WsManagedAPTspecStatisticsEntry
     MAX-ACCESS   not-accessible
     STATUS       current
     DESCRIPTION
         "This table contains TSPEC statistics available for all APs
          managed by the controller."
     ::= { tspecManagedAP 2 }

    wsManagedAPTspecStatisticsEntry OBJECT-TYPE
     SYNTAX       WsManagedAPTspecStatisticsEntry
     MAX-ACCESS   not-accessible
     STATUS       current
     DESCRIPTION
          "Each entry in this table contains TSPEC statistics for
           a specific AP managed by the controller."
     AUGMENTS { wsManagedAPTspecStatusEntry }
     ::= { wsManagedAPTspecStatisticsTable 1 }

 WsManagedAPTspecStatisticsEntry ::=
     SEQUENCE {
      wsManagedAPTspecPktsRecvd                 Counter64,
      wsManagedAPTspecPktsTransmitted           Counter64,
      wsManagedAPTspecBytesRecvd                Counter64,
      wsManagedAPTspecBytesTransmitted          Counter64,
      wsManagedAPTspecsAccepted                 Counter32,
      wsManagedAPTspecsRejected                 Counter32,
      wsManagedAPRoamingTspecsAccepted          Counter32,
      wsManagedAPRoamingTspecsRejected          Counter32

 }

    wsManagedAPTspecPktsRecvd    OBJECT-TYPE
         SYNTAX      Counter64
         MAX-ACCESS  not-accessible
         STATUS      current
         DESCRIPTION
              "Total packets received by this AP on the wireless
               network for all traffic streams belonging to
               the specified access category."
         ::= { wsManagedAPTspecStatisticsEntry 1 }

    wsManagedAPTspecPktsTransmitted    OBJECT-TYPE
         SYNTAX      Counter64
         MAX-ACCESS  not-accessible
         STATUS      current
         DESCRIPTION
              "Total packets transmitted by this AP on the wireless
               network for all traffic streams belonging to
               the specified access category."
         ::= { wsManagedAPTspecStatisticsEntry 2 }

    wsManagedAPTspecBytesRecvd    OBJECT-TYPE
         SYNTAX      Counter64
         MAX-ACCESS  not-accessible
         STATUS      current
         DESCRIPTION
              "Total bytes received by this AP on the wireless
               network for all traffic streams belonging to
               the specified access category."
         ::= { wsManagedAPTspecStatisticsEntry 3 }

    wsManagedAPTspecBytesTransmitted    OBJECT-TYPE
         SYNTAX      Counter64
         MAX-ACCESS  not-accessible
         STATUS      current
         DESCRIPTION
              "Total bytes transmitted by this AP on the wireless
               network for all traffic streams belonging to
               the specified access category."
         ::= { wsManagedAPTspecStatisticsEntry 4 }

    wsManagedAPTspecsAccepted    OBJECT-TYPE
         SYNTAX      Counter32
         MAX-ACCESS  not-accessible
         STATUS      current
         DESCRIPTION
              "Total number of TSPECs accepted by this AP on the wireless
               network for the specified access category."
         ::= { wsManagedAPTspecStatisticsEntry 5 }

    wsManagedAPTspecsRejected    OBJECT-TYPE
         SYNTAX      Counter32
         MAX-ACCESS  not-accessible
         STATUS      current
         DESCRIPTION
              "Total number of TSPECs rejected by this AP on the wireless
               network for the specified access category."
         ::= { wsManagedAPTspecStatisticsEntry 6 }

    wsManagedAPRoamingTspecsAccepted    OBJECT-TYPE
         SYNTAX      Counter32
         MAX-ACCESS  not-accessible
         STATUS      current
         DESCRIPTION
              "Total number of TSPECs accepted from roaming clients by
               an AP on the wireless network for the specified
               access category.

               This value of this object is also included in the
               wsManagedAPTspecsAccepted object."
         ::= { wsManagedAPTspecStatisticsEntry 7 }

    wsManagedAPRoamingTspecsRejected    OBJECT-TYPE
         SYNTAX      Counter32
         MAX-ACCESS  not-accessible
         STATUS      current
         DESCRIPTION
              "Total number of TSPECs rejected from roaming clients by
               an AP on the wireless network for the specified
               access category.

               This value of this object is also included in the
               wsManagedAPTspecsRejected object."
         ::= { wsManagedAPTspecStatisticsEntry 8 }

--
--   wsManagedAPRadioTspecStatusTable
--
 wsManagedAPRadioTspecStatusTable OBJECT-TYPE
     SYNTAX       SEQUENCE OF WsManagedAPRadioTspecStatusEntry
     MAX-ACCESS   not-accessible
     STATUS       current
     DESCRIPTION
           "This table contains TSPEC status parameters per radio interface
            for all APs managed by the controller."
     ::= { tspecManagedAP 3 }

    wsManagedAPRadioTspecStatusEntry OBJECT-TYPE
     SYNTAX       WsManagedAPRadioTspecStatusEntry
     MAX-ACCESS   not-accessible
     STATUS       current
     DESCRIPTION
          "Each entry in this table contains TSPEC status parameters
           per radio interface for a specific AP managed by the controller."
     INDEX    { wsManagedAPMacAddress, wsManagedAPRadioInterface,
                wsTspecACIndex }
     ::= { wsManagedAPRadioTspecStatusTable 1 }

 WsManagedAPRadioTspecStatusEntry ::=
     SEQUENCE {
      wsManagedAPRadioTspecOperStatus                       INTEGER,
      wsManagedAPRadioTspecNumActiveTrafficStreams          Unsigned32,
      wsManagedAPRadioTspecNumTrafficStreamClients          Unsigned32,
      wsManagedAPRadioTspecNumTrafficStreamRoamingClients   Unsigned32,
      wsManagedAPRadioTspecMediumTimeAdmitted               Unsigned32,
      wsManagedAPRadioTspecMediumTimeUnallocated            Unsigned32,
      wsManagedAPRadioTspecMediumTimeRoamingUnallocated     Unsigned32
 }

 wsManagedAPRadioTspecOperStatus OBJECT-TYPE
     SYNTAX       INTEGER {
                    disabled(0),
                    enabled(1)
                  }
     MAX-ACCESS   not-accessible
     STATUS       current
     DESCRIPTION
        "Indicates the current operational status for the specified
         access category on this radio.  If enabled(1),
         this access category operates in accordance with admission
         control mandatory (ACM) procedures."
     ::= { wsManagedAPRadioTspecStatusEntry 1 }

 wsManagedAPRadioTspecNumActiveTrafficStreams OBJECT-TYPE
     SYNTAX       Unsigned32
     MAX-ACCESS   not-accessible
     STATUS       current
     DESCRIPTION
        "Indicates the current number of active traffic streams (TSs)
         for the specified access category on this radio."
     ::= { wsManagedAPRadioTspecStatusEntry 2 }

 wsManagedAPRadioTspecNumTrafficStreamClients OBJECT-TYPE
     SYNTAX       Unsigned32
     MAX-ACCESS   not-accessible
     STATUS       current
     DESCRIPTION
        "Indicates the current number of clients with at least one
         active traffic stream (TS) for the specified access category
         on this radio."
     ::= { wsManagedAPRadioTspecStatusEntry 3 }

 wsManagedAPRadioTspecNumTrafficStreamRoamingClients OBJECT-TYPE
     SYNTAX       Unsigned32
     MAX-ACCESS   not-accessible
     STATUS       current
     DESCRIPTION
        "Indicates the current number of roaming clients with at least one
         active traffic stream (TS) for the specified access category
         on this radio.

         The value of this object is also included in the
         wsManagedAPRadioTspecNumTSClients object."
     ::= { wsManagedAPRadioTspecStatusEntry 4 }

 wsManagedAPRadioTspecMediumTimeAdmitted OBJECT-TYPE
     SYNTAX       Unsigned32
     MAX-ACCESS   not-accessible
     STATUS       current
     DESCRIPTION
        "Current sum of medium times allocated to clients with an active
         traffic stream (TS) belonging to the specified access category on this
         radio."
     ::= { wsManagedAPRadioTspecStatusEntry 5 }

 wsManagedAPRadioTspecMediumTimeUnallocated OBJECT-TYPE
     SYNTAX       Unsigned32
     MAX-ACCESS   not-accessible
     STATUS       current
     DESCRIPTION
        "Amount of configured medium time not currently allocated for the
         specified access category on this radio that is available for
         both non-roaming and roaming clients."
     ::= { wsManagedAPRadioTspecStatusEntry 6 }

 wsManagedAPRadioTspecMediumTimeRoamingUnallocated OBJECT-TYPE
     SYNTAX       Unsigned32
     MAX-ACCESS   not-accessible
     STATUS       current
     DESCRIPTION
        "Amount of configured medium time not currently allocated for the
         specified access category on this radio that is available for
         roaming clients only."
     ::= { wsManagedAPRadioTspecStatusEntry 7 }

--
-- wsManagedAPRadioTspecStatisticsTable
--
 wsManagedAPRadioTspecStatisticsTable OBJECT-TYPE
     SYNTAX       SEQUENCE OF WsManagedAPRadioTspecStatisticsEntry
     MAX-ACCESS   not-accessible
     STATUS       current
     DESCRIPTION
         "This table contains TSPEC statistics available per radio
          interface for all APs managed by the controller."
     ::= { tspecManagedAP 4 }

    wsManagedAPRadioTspecStatisticsEntry OBJECT-TYPE
     SYNTAX       WsManagedAPRadioTspecStatisticsEntry
     MAX-ACCESS   not-accessible
     STATUS       current
     DESCRIPTION
          "Each entry in this table contains TSPEC statistics per radio
           interface for a specific AP managed by the controller."
     AUGMENTS { wsManagedAPRadioTspecStatusEntry }
     ::= { wsManagedAPRadioTspecStatisticsTable 1 }

 WsManagedAPRadioTspecStatisticsEntry ::=
     SEQUENCE {
      wsManagedAPRadioTspecPktsRecvd                 Counter64,
      wsManagedAPRadioTspecPktsTransmitted           Counter64,
      wsManagedAPRadioTspecBytesRecvd                Counter64,
      wsManagedAPRadioTspecBytesTransmitted          Counter64

 }

    wsManagedAPRadioTspecPktsRecvd    OBJECT-TYPE
         SYNTAX      Counter64
         MAX-ACCESS  not-accessible
         STATUS      current
         DESCRIPTION
              "Total packets received on this radio
               for all traffic streams belonging to
               the specified access category."
         ::= { wsManagedAPRadioTspecStatisticsEntry 1 }

    wsManagedAPRadioTspecPktsTransmitted    OBJECT-TYPE
         SYNTAX      Counter64
         MAX-ACCESS  not-accessible
         STATUS      current
         DESCRIPTION
              "Total packets transmitted on this radio
               for all traffic streams belonging to
               the specified access category."
         ::= { wsManagedAPRadioTspecStatisticsEntry 2 }

    wsManagedAPRadioTspecBytesRecvd    OBJECT-TYPE
         SYNTAX      Counter64
         MAX-ACCESS  not-accessible
         STATUS      current
         DESCRIPTION
              "Total bytes received on this radio
               for all traffic streams belonging to
               the specified access category."
         ::= { wsManagedAPRadioTspecStatisticsEntry 3 }

    wsManagedAPRadioTspecBytesTransmitted    OBJECT-TYPE
         SYNTAX      Counter64
         MAX-ACCESS  not-accessible
         STATUS      current
         DESCRIPTION
              "Total bytes transmitted on this radio
               for all traffic streams belonging to
               the specified access category."
         ::= { wsManagedAPRadioTspecStatisticsEntry 4 }

--
--   wsManagedAPVAPTspecStatusTable
--
 wsManagedAPVAPTspecStatusTable OBJECT-TYPE
     SYNTAX       SEQUENCE OF WsManagedAPVAPTspecStatusEntry
     MAX-ACCESS   not-accessible
     STATUS       current
     DESCRIPTION
           "This table contains TSPEC status parameters for each VAP
            on the specified radio interface for all APs managed
            by the controller."
     ::= { tspecManagedAP 5 }

    wsManagedAPVAPTspecStatusEntry OBJECT-TYPE
     SYNTAX       WsManagedAPVAPTspecStatusEntry
     MAX-ACCESS   not-accessible
     STATUS       current
     DESCRIPTION
          "Each entry in this table contains TSPEC status parameters for each VAP
           on the specified radio interface for a specific AP managed by the controller."
     INDEX    { wsManagedAPMacAddress, wsManagedAPRadioInterface,
                wsManagedVAPId, wsTspecACIndex }
     ::= { wsManagedAPVAPTspecStatusTable 1 }

 WsManagedAPVAPTspecStatusEntry ::=
     SEQUENCE {
      wsManagedAPVAPTspecOperStatus                         INTEGER,
      wsManagedAPVAPTspecNumActiveTrafficStreams            Unsigned32,
      wsManagedAPVAPTspecNumTrafficStreamClients            Unsigned32,
      wsManagedAPVAPTspecNumTrafficStreamRoamingClients     Unsigned32,
      wsManagedAPVAPTspecMediumTimeAdmitted                 Unsigned32,
      wsManagedAPVAPTspecMediumTimeUnallocated              Unsigned32,
      wsManagedAPVAPTspecMediumTimeRoamingUnallocated       Unsigned32
 }

 wsManagedAPVAPTspecOperStatus OBJECT-TYPE
     SYNTAX       INTEGER {
                    disabled(0),
                    enabled(1)
                  }
     MAX-ACCESS   not-accessible
     STATUS       current
     DESCRIPTION
        "Indicates the current operational status for the specified
         access category on this VAP.  If enabled(1),
         this access category operates in accordance with admission
         control mandatory (ACM) procedures."
     ::= { wsManagedAPVAPTspecStatusEntry 1 }

 wsManagedAPVAPTspecNumActiveTrafficStreams OBJECT-TYPE
     SYNTAX       Unsigned32
     MAX-ACCESS   not-accessible
     STATUS       current
     DESCRIPTION
        "Indicates the current number of active traffic streams (TSs)
         for the specified access category on this VAP."
     ::= { wsManagedAPVAPTspecStatusEntry 2 }

 wsManagedAPVAPTspecNumTrafficStreamClients OBJECT-TYPE
     SYNTAX       Unsigned32
     MAX-ACCESS   not-accessible
     STATUS       current
     DESCRIPTION
        "Indicates the current number of clients with at least one
         active traffic stream (TS) for the specified access category
         on this VAP."
     ::= { wsManagedAPVAPTspecStatusEntry 3 }

 wsManagedAPVAPTspecNumTrafficStreamRoamingClients OBJECT-TYPE
     SYNTAX       Unsigned32
     MAX-ACCESS   not-accessible
     STATUS       current
     DESCRIPTION
        "Indicates the current number of roaming clients with at least one
         active traffic stream (TS) for the specified access category
         on this VAP.

         The value of this object is also included in the
         wsManagedAPVAPTspecNumTSClients object."
     ::= { wsManagedAPVAPTspecStatusEntry 4 }

 wsManagedAPVAPTspecMediumTimeAdmitted OBJECT-TYPE
     SYNTAX       Unsigned32
     MAX-ACCESS   not-accessible
     STATUS       current
     DESCRIPTION
        "Current sum of medium times allocated to clients with an active
         traffic stream (TS) belonging to the specified access category on this
         VAP."
     ::= { wsManagedAPVAPTspecStatusEntry 5 }

 wsManagedAPVAPTspecMediumTimeUnallocated OBJECT-TYPE
     SYNTAX       Unsigned32
     MAX-ACCESS   not-accessible
     STATUS       current
     DESCRIPTION
        "Amount of configured medium time not currently allocated for the
         specified access category on this VAP that is available for
         both non-roaming and roaming clients."
     ::= { wsManagedAPVAPTspecStatusEntry 6 }

 wsManagedAPVAPTspecMediumTimeRoamingUnallocated OBJECT-TYPE
     SYNTAX       Unsigned32
     MAX-ACCESS   not-accessible
     STATUS       current
     DESCRIPTION
        "Amount of configured medium time not currently allocated for the
         specified access category on this VAP that is available for
         roaming clients only."
     ::= { wsManagedAPVAPTspecStatusEntry 7 }

--
-- wsManagedAPVAPTspecStatisticsTable
--
 wsManagedAPVAPTspecStatisticsTable OBJECT-TYPE
     SYNTAX       SEQUENCE OF WsManagedAPVAPTspecStatisticsEntry
     MAX-ACCESS   not-accessible
     STATUS       current
     DESCRIPTION
         "This table contains TSPEC statistics available for each VAP
          on the specified radio interface for all APs managed
          by the controller."
     ::= { tspecManagedAP 6 }

    wsManagedAPVAPTspecStatisticsEntry OBJECT-TYPE
     SYNTAX       WsManagedAPVAPTspecStatisticsEntry
     MAX-ACCESS   not-accessible
     STATUS       current
     DESCRIPTION
          "Each entry in this table contains TSPEC statistics for each VAP
           on the specified radio for a specific AP managed by the controller."
     AUGMENTS { wsManagedAPVAPTspecStatusEntry }
     ::= { wsManagedAPVAPTspecStatisticsTable 1 }

 WsManagedAPVAPTspecStatisticsEntry ::=
     SEQUENCE {
      wsManagedAPVAPTspecPktsRecvd                 Counter64,
      wsManagedAPVAPTspecPktsTransmitted           Counter64,
      wsManagedAPVAPTspecBytesRecvd                Counter64,
      wsManagedAPVAPTspecBytesTransmitted          Counter64

 }

    wsManagedAPVAPTspecPktsRecvd    OBJECT-TYPE
         SYNTAX      Counter64
         MAX-ACCESS  not-accessible
         STATUS      current
         DESCRIPTION
              "Total packets received on this VAP
               for all traffic streams belonging to
               the specified access category."
         ::= { wsManagedAPVAPTspecStatisticsEntry 1 }

    wsManagedAPVAPTspecPktsTransmitted    OBJECT-TYPE
         SYNTAX      Counter64
         MAX-ACCESS  not-accessible
         STATUS      current
         DESCRIPTION
              "Total packets transmitted on this VAP
               for all traffic streams belonging to
               the specified access category."
         ::= { wsManagedAPVAPTspecStatisticsEntry 2 }

    wsManagedAPVAPTspecBytesRecvd    OBJECT-TYPE
         SYNTAX      Counter64
         MAX-ACCESS  not-accessible
         STATUS      current
         DESCRIPTION
              "Total bytes received on this VAP
               for all traffic streams belonging to
               the specified access category."
         ::= { wsManagedAPVAPTspecStatisticsEntry 3 }

    wsManagedAPVAPTspecBytesTransmitted    OBJECT-TYPE
         SYNTAX      Counter64
         MAX-ACCESS  not-accessible
         STATUS      current
         DESCRIPTION
              "Total bytes transmitted on this VAP
               for all traffic streams belonging to
               the specified access category."
         ::= { wsManagedAPVAPTspecStatisticsEntry 4 }

--
--   wsAssociatedClientTsStatusTable
--

 wsAssociatedClientTsStatusTable OBJECT-TYPE
     SYNTAX       SEQUENCE OF WsAssociatedClientTsStatusEntry
     MAX-ACCESS   not-accessible
     STATUS       current
     DESCRIPTION
           "This table contains TSPEC traffic stream status parameters
            for clients currently associated with managed APs.  Only
            clients possessing one or more active traffic streams
            appear in this table."
     ::= { tspecClient 1 }

    wsAssociatedClientTsStatusEntry OBJECT-TYPE
     SYNTAX       WsAssociatedClientTsStatusEntry
     MAX-ACCESS   not-accessible
     STATUS       current
     DESCRIPTION
          "Each entry in this table contains TSPEC traffic stream status
           parameters for a specific client that is currently associated
           with the WS managed AP."
     INDEX    { wsAssociatedClientMacAddress, wsAssociatedClientTsTid }
     ::= { wsAssociatedClientTsStatusTable 1 }

 WsAssociatedClientTsStatusEntry ::=
     SEQUENCE {
      wsAssociatedClientTsTid                      Unsigned32,
      wsAssociatedClientTsAccessCategory           TspecSuppAC,
      wsAssociatedClientTsDirection                INTEGER,
      wsAssociatedClientTsUserPriority             Unsigned32,
      wsAssociatedClientTsMediumTime               Unsigned32,
      wsAssociatedClientTsExcessUsageEvents        Unsigned32,
      wsAssociatedClientTsRoamingClientIndicator   INTEGER
 }

 wsAssociatedClientTsTid OBJECT-TYPE
     SYNTAX       Unsigned32(0..7)
     MAX-ACCESS   not-accessible
     STATUS       current
     DESCRIPTION
        "The traffic stream identifier (TID) indicated in the TSPEC that
         defines the traffic stream for the specified access category
         for the wireless client.  Each traffic stream for a particular
         client must have a unique TID in the range 0-7, but per specification,
         any TID may map to any user priority and hence to any access category."
     ::= { wsAssociatedClientTsStatusEntry 1 }

 wsAssociatedClientTsAccessCategory OBJECT-TYPE
     SYNTAX       TspecSuppAC
     MAX-ACCESS   not-accessible
     STATUS       current
     DESCRIPTION
        "Access category (AC) of this client traffic stream.
         Only those ACs that support mandatory admission control
         are used.  The currently supported AC values are:
              0 - Voice
              1 - Video
         "
     ::= { wsAssociatedClientTsStatusEntry 2 }

 wsAssociatedClientTsDirection OBJECT-TYPE
     SYNTAX       INTEGER {
                     uplink(1),
                     downlink(2),
                     bidirectional(3)
                  }
     MAX-ACCESS   not-accessible
     STATUS       current
     DESCRIPTION
        "The direction of the client traffic stream (TS) as indicated
         in the TSPEC.  An uplink(1) TS monitors data traffic flowing
         from client station to AP, while a downlink(2) TS pertains to
         the opposite direction.  A bidirectional(3) TS covers both
         directions and is treated as an uplink TS and downlink TS
         operating concurrently for the specified access category."
     ::= { wsAssociatedClientTsStatusEntry 3 }

 wsAssociatedClientTsUserPriority OBJECT-TYPE
     SYNTAX       Unsigned32
     MAX-ACCESS   not-accessible
     STATUS       current
     DESCRIPTION
        "The user priority indicated in the TSPEC that defines
         the traffic stream for the specified access category
         for the wireless client.  QoS Data frames to/from the client
         containing this user priority are categorized as belonging
         to the traffic stream, depending on direction."
     ::= { wsAssociatedClientTsStatusEntry 4 }

 wsAssociatedClientTsMediumTime OBJECT-TYPE
     SYNTAX       Unsigned32
     MAX-ACCESS   not-accessible
     STATUS       current
     DESCRIPTION
        "Indicates the amount of time this client is allowed to access
         the wireless medium each second for the specified access category through
         this traffic stream.  This value is calculated by the AP based
         on various parameters supplied in the TSPEC add request from
         the client.

         The medium time is specified as the number of 32 microsecond time
         units the client is allowed to access the wireless network each
         second.  This is referred to as units of 32 usec-per-sec and is
         generally treated as an average value, with any over-usage
         in one interval deducted from the alotted medium time for the next
         interval."
     ::= { wsAssociatedClientTsStatusEntry 5 }

 wsAssociatedClientTsExcessUsageEvents OBJECT-TYPE
     SYNTAX       Unsigned32
     MAX-ACCESS   not-accessible
     STATUS       current
     DESCRIPTION
        "The number of times the wireless client has appreciably exceeded
         the medium time established for its TSPEC.  The actual measure
         of 'appreciably exceeded' is implementation-dependent, but it is
         not necessarily a single occurrence of exceeding the medium time
         for any given one second interval.  Rather, this event may be
         indicated after repeated violations of the medium time over some
         measurement interval, and is intended as an heuristic to identify
         a wireless client whose TSPEC medium time may be set too low relative
         to its actual traffic stream requirements.

         This object reflects the number of excess usage events that have
         accumulated, but have not been reported, through the Trap Manager,
         with such reporting enabled by the wsTspecTrapMode object.
         Whenever a trap report is generated for this event, the value of
         this object restarts counting from zero."
     ::= { wsAssociatedClientTsStatusEntry 6 }

 wsAssociatedClientTsRoamingClientIndicator OBJECT-TYPE
     SYNTAX       INTEGER {
                     yes(1),
                     no(2)
                  }
     MAX-ACCESS   not-accessible
     STATUS       current
     DESCRIPTION
        "A flag indicating whether this traffic stream was established
         by a wireless client that was considered to be a roaming client."
     ::= { wsAssociatedClientTsStatusEntry 7 }

--
--   wsAssociatedClientTsStatisticsTable
--

 wsAssociatedClientTsStatisticsTable OBJECT-TYPE
     SYNTAX       SEQUENCE OF WsAssociatedClientTsStatisticsEntry
     MAX-ACCESS   not-accessible
     STATUS       current
     DESCRIPTION
           "This table contains TSPEC traffic stream statistics
            for clients currently associated with managed APs.  Only
            clients possessing one or more active traffic streams
            appear in this table."
     ::= { tspecClient 2 }

    wsAssociatedClientTsStatisticsEntry OBJECT-TYPE
     SYNTAX       WsAssociatedClientTsStatisticsEntry
     MAX-ACCESS   not-accessible
     STATUS       current
     DESCRIPTION
          "Each entry in this table contains TSPEC traffic stream statistics
           for a specific client that is currently associated with the
           WS managed AP."
     AUGMENTS    { wsAssociatedClientTsStatusEntry }
     ::= { wsAssociatedClientTsStatisticsTable 1 }

 WsAssociatedClientTsStatisticsEntry ::=
     SEQUENCE {
      wsAssociatedClientTsPktsRecvd            Counter64,
      wsAssociatedClientTsPktsTransmitted      Counter64,
      wsAssociatedClientTsBytesRecvd           Counter64,
      wsAssociatedClientTsBytesTransmitted     Counter64
 }

 wsAssociatedClientTsPktsRecvd OBJECT-TYPE
     SYNTAX       Counter64
     MAX-ACCESS   not-accessible
     STATUS       current
     DESCRIPTION
        "Total packets received from the client station for the
         traffic stream belonging to the specified access category.

         This object is only valid when the wsAssociatedClientTsDirection
         is either uplink(1) or bidirectional(3)."
     ::= { wsAssociatedClientTsStatisticsEntry 1 }

 wsAssociatedClientTsPktsTransmitted OBJECT-TYPE
     SYNTAX       Counter64
     MAX-ACCESS   not-accessible
     STATUS       current
     DESCRIPTION
        "Total packets transmitted to the client station for the
         traffic stream belonging to the specified access category.

         This object is only valid when the wsAssociatedClientTsDirection
         is either downlink(2) or bidirectional(3)."
     ::= { wsAssociatedClientTsStatisticsEntry 2 }

 wsAssociatedClientTsBytesRecvd OBJECT-TYPE
     SYNTAX       Counter64
     MAX-ACCESS   not-accessible
     STATUS       current
     DESCRIPTION
        "Total bytes received from the client station for the
         traffic stream belonging to the specified access category.

         This object is only valid when the wsAssociatedClientTsDirection
         is either uplink(1) or bidirectional(3)."
     ::= { wsAssociatedClientTsStatisticsEntry 3 }

 wsAssociatedClientTsBytesTransmitted OBJECT-TYPE
     SYNTAX       Counter64
     MAX-ACCESS   not-accessible
     STATUS       current
     DESCRIPTION
        "Total bytes transmitted to the client station for the
         traffic stream belonging to the specified access category.

         This object is only valid when the wsAssociatedClientTsDirection
         is either downlink(2) or bidirectional(3)."
     ::= { wsAssociatedClientTsStatisticsEntry 4 }

--**************************************************************************************
-- tspec (status and statistics) Ends
--**************************************************************************************

--******************************************************************************
-- provisioning Starts
--******************************************************************************
--
--  wsAPProvisioningTable
--
    wsAPProvisioningTable   OBJECT-TYPE
        SYNTAX          SEQUENCE OF WsAPProvisioningEntry
        MAX-ACCESS      not-accessible
        STATUS          current
        DESCRIPTION
          "This table contains data for provisioning access points and also the
           AP provisioning status information."
        ::= { provisioning 1 }

    wsAPProvisioningEntry OBJECT-TYPE
        SYNTAX          WsAPProvisioningEntry
        MAX-ACCESS      not-accessible
        STATUS          current
        DESCRIPTION
          "Each entry has parameters that indicate AP provisioned values and
           also parameters to configure new provisioning information."
        INDEX    { wsAPProvMacAddress }
        ::= { wsAPProvisioningTable 1 }

    WsAPProvisioningEntry ::=
        SEQUENCE {
          wsAPProvMacAddress                MacAddress,
          wsAPProvIPAddress                 IpAddress,
          wsAPProvPrimarySwitchIP           IpAddress,
          wsAPProvBackupSwitchIP            IpAddress,
          wsAPProvMutualAuthMode            INTEGER,
          wsAPProvUnmanagedAPReprovMode     INTEGER,
          wsAPProvAge                       TimeTicks,
          wsAPProvNewPrimarySwitchIP        IpAddress,
          wsAPProvNewBackupSwitchIP         IpAddress,
          wsAPProvNewProfileId              Integer32,
          wsAPProvCommand                   INTEGER,
          wsAPProvStatus                    INTEGER,
          wsAPProvCertProfileTxStatus       INTEGER,
          wsAPProvEntryPurge                INTEGER
        }

    wsAPProvMacAddress  OBJECT-TYPE
        SYNTAX              MacAddress
        MAX-ACCESS          not-accessible
        STATUS              current
        DESCRIPTION
          "MAC address of an AP."
        ::= { wsAPProvisioningEntry 1 }

     wsAPProvIPAddress  OBJECT-TYPE
        SYNTAX              IpAddress
        MAX-ACCESS          not-accessible
        STATUS              current
        DESCRIPTION
          "Network IP address of the AP."
        ::= { wsAPProvisioningEntry 2 }

     wsAPProvPrimarySwitchIP  OBJECT-TYPE
        SYNTAX              IpAddress
        MAX-ACCESS          not-accessible
        STATUS              current
        DESCRIPTION
          "Provisioned primary controller IP address on the AP."
        ::= { wsAPProvisioningEntry 3 }

     wsAPProvBackupSwitchIP OBJECT-TYPE
        SYNTAX              IpAddress
        MAX-ACCESS          not-accessible
        STATUS              current
        DESCRIPTION
          "Provisioned backup controller IP address on the AP."
        ::= { wsAPProvisioningEntry 4 }

    wsAPProvMutualAuthMode  OBJECT-TYPE
        SYNTAX              INTEGER {
                              enable(1),
                              disable(2)
                            }
        MAX-ACCESS          not-accessible
        STATUS              current
        DESCRIPTION
          "The mutual authentication mode configured in the AP."
        ::= { wsAPProvisioningEntry 5 }

    wsAPProvUnmanagedAPReprovMode  OBJECT-TYPE
        SYNTAX              INTEGER {
                              enable(1),
                              disable(2)
                            }
        MAX-ACCESS          not-accessible
        STATUS              current
        DESCRIPTION
          "The configured AP re-provisioning mode when in unmanaged state in
           the AP."
        ::= { wsAPProvisioningEntry 6 }

    wsAPProvAge         OBJECT-TYPE
        SYNTAX              TimeTicks
        MAX-ACCESS          not-accessible
        STATUS              current
        DESCRIPTION
          "Time since any information has been received from this AP."
        ::= { wsAPProvisioningEntry 7 }

     wsAPProvNewPrimarySwitchIP OBJECT-TYPE
        SYNTAX              IpAddress
        MAX-ACCESS          not-accessible
        STATUS              current
        DESCRIPTION
          "The IP address of the primary controller which the adminstrator wants to
           provision the AP."
        ::= { wsAPProvisioningEntry 8 }

     wsAPProvNewBackupSwitchIP  OBJECT-TYPE
        SYNTAX              IpAddress
        MAX-ACCESS          not-accessible
        STATUS              current
        DESCRIPTION
          "The IP address of the backup controller which the administrator wants to
           provision the AP."
        ::= { wsAPProvisioningEntry 9 }

    wsAPProvNewProfileId  OBJECT-TYPE
        SYNTAX              Integer32(0..16)
        MAX-ACCESS          not-accessible
        STATUS              current
        DESCRIPTION
          "Profile ID to be configured in the local Valid AP database of the
           primary and backup controllers."
        ::= { wsAPProvisioningEntry 10 }

    wsAPProvCommand     OBJECT-TYPE
        SYNTAX              INTEGER {
                              none(0),
                              initiate(1)
                            }
        MAX-ACCESS          not-accessible
        STATUS              current
        DESCRIPTION
          "This parameter triggers the AP provisioning process for this AP."
        ::= { wsAPProvisioningEntry 11 }

    wsAPProvStatus      OBJECT-TYPE
        SYNTAX              INTEGER {
                              not-started(1),
                              requested(2),
                              success(3),
                              in-progress(4),
                              provisioning-rejected(5),
                              timed-out(6)
                            }
        MAX-ACCESS          not-accessible
        STATUS              current
        DESCRIPTION
          "Status of the most recently issued AP provisioning command."
        ::= { wsAPProvisioningEntry 12 }

    wsAPProvCertProfileTxStatus OBJECT-TYPE
        SYNTAX              INTEGER {
                              not-started(1),
                              success(2),
                              failed(3)
                            }
        MAX-ACCESS          not-accessible
        STATUS              current
        DESCRIPTION
          "Status of the last AP profile and X.509 certificate distribution to
           primary and backup controllers."
        ::= { wsAPProvisioningEntry 13 }

    wsAPProvEntryPurge OBJECT-TYPE
        SYNTAX              INTEGER {
                              enable(1),
                              disable(2)
                            }
        MAX-ACCESS          not-accessible
        STATUS              current
        DESCRIPTION
          "This is an action object. Setting this object to enable will delete
           the AP entry if it is unmanaged. Reads on this object will always return
           disabled."
        ::= { wsAPProvisioningEntry 14 }

    wsAPProvisioningInitiateAll  OBJECT-TYPE
        SYNTAX                  INTEGER {
                                  none(0),
                                  initiate(1)
                                }

        MAX-ACCESS              not-accessible
        STATUS                  current
        DESCRIPTION
          "Start provisioning of all the APs in the database."
        ::= { provisioning 2 }

    wsAPProvisioningDeleteAll  OBJECT-TYPE
        SYNTAX                  INTEGER {
                                  enable(1),
                                  disable(2)
                                }
        MAX-ACCESS              not-accessible
        STATUS                  current
        DESCRIPTION
          "Delete all unmanaged AP provisioning entries"
        ::= { provisioning 3 }

    wsNetworkExchangeCertificates OBJECT-TYPE
        SYNTAX                  INTEGER {
                                  none(0),
                                  initiate(1)
                                }
        MAX-ACCESS              not-accessible
        STATUS                  current
        DESCRIPTION
          "Trigger the wireless controllers and APs to exchange X.509 certificates.
           This command can be triggered only when mutual authentication is
           already enabled on the network."
        ::= { provisioning 4 }

     wsSwitchProvIPAddress OBJECT-TYPE
        SYNTAX              IpAddress
        MAX-ACCESS          not-accessible
        STATUS              current
        DESCRIPTION
          "IP address of the controller from which this controller
          obtains the provisioning information."
        ::= { provisioning 5 }

    wsSwitchProvStatus    OBJECT-TYPE
        SYNTAX              INTEGER {
                              not-started(1),
                              requested(2),
                              in-progress(3),
                              provisioning-failed(4),
                              connection-failed(5),
                              success(6)
                            }
        MAX-ACCESS          not-accessible
        STATUS              current
        DESCRIPTION
          "Status of controller provisioning activity."
        ::= { provisioning 6 }

     wsSwitchCertReqTarget OBJECT-TYPE
        SYNTAX              IpAddress
        MAX-ACCESS          not-accessible
        STATUS              current
        DESCRIPTION
          "IP address of the wireless controller from which
          this controller requests an X.509 certificate"
        ::= { provisioning 7 }

    wsSwitchCertReqStatus OBJECT-TYPE
        SYNTAX              INTEGER {
                              not-started(1),
                              requested(2),
                              in-progress(3),
                              invalid-ip(4),
                              timed-out(5),
                              success(6)
                            }
        MAX-ACCESS          not-accessible
        STATUS              current
        DESCRIPTION
          "Status of X.509 certificate request status."
        ::= { provisioning 8 }

    wsSwitchProvisioningCommand OBJECT-TYPE
        SYNTAX            INTEGER {
                            none(0),
                            initiate(1)
                          }
        MAX-ACCESS        not-accessible
        STATUS            current
        DESCRIPTION
          "This parameter triggers the controller provisioning with
           the controller specified in the Provisioning controller IP address"
        ::= {provisioning 9 }

    wsSwitchCertReqCommand  OBJECT-TYPE
        SYNTAX            INTEGER {
                            none(0),
                            initiate(1)
                          }
        MAX-ACCESS        not-accessible
        STATUS            current
        DESCRIPTION
          "This parameter initiates the X.509 certificate request from
           the controller specified in the Certificate Request Target."
        ::= { provisioning 10 }

--******************************************************************************
-- provisioning Ends
--******************************************************************************

--******************************************************************************
-- wdsManagedAP Starts
--******************************************************************************
--
--  wsWDSAPGroupTable
--
  wsWDSAPGroupTable OBJECT-TYPE
    SYNTAX          SEQUENCE OF WsWDSAPGroupEntry
    MAX-ACCESS      not-accessible
    STATUS          current
    DESCRIPTION
        "The following "
     ::= { wdsManagedAP 1 }

  wsWDSAPGroupEntry OBJECT-TYPE
    SYNTAX          WsWDSAPGroupEntry
    MAX-ACCESS      not-accessible
    STATUS          current
    DESCRIPTION
         "Each entry "
    INDEX    { wsWDSAPGroupId }
    ::= { wsWDSAPGroupTable 1 }

  WsWDSAPGroupEntry ::=
    SEQUENCE {
      wsWDSAPGroupId                    Integer32,
      wsWDSAPGroupName                  DisplayString,
      wsWDSAPGroupSpanningTree          INTEGER,
      wsWDSAPGroupPassword              DisplayString,
      wsWDSAPGroupRowStatus             RowStatus
    }

  wsWDSAPGroupId OBJECT-TYPE
    SYNTAX          Integer32(1..2)
    MAX-ACCESS      read-only
    STATUS          current
    DESCRIPTION
        "Unique WDS Group Id for each entry."
    ::= { wsWDSAPGroupEntry 1 }

  wsWDSAPGroupName OBJECT-TYPE
    SYNTAX          DisplayString(SIZE(0..32))
    MAX-ACCESS      read-only
    STATUS          current
    DESCRIPTION
        "AP configuration profile name."
    ::= { wsWDSAPGroupEntry 2 }

  wsWDSAPGroupSpanningTree OBJECT-TYPE
    SYNTAX      INTEGER {
                enable(1),
                disable(2)
                }
    MAX-ACCESS  not-accessible
    STATUS      current
    DESCRIPTION
        "This varible allows the spanning tree mode enabling or disabling in a Managed AP Group."
         DEFVAL      { disable }
    ::= { wsWDSAPGroupEntry 3 }

  wsWDSAPGroupPassword OBJECT-TYPE
     SYNTAX       DisplayString(SIZE(8..63))
     MAX-ACCESS   read-only
     STATUS       current
     DESCRIPTION
        "Indicates password to be used to form WDS links among
         the APs in a Managed AP Group. If password is
         configured, read on this object will return '*****'."
     ::= { wsWDSAPGroupEntry 4 }

  wsWDSAPGroupRowStatus OBJECT-TYPE
    SYNTAX          RowStatus
    MAX-ACCESS      read-only
    STATUS          current
    DESCRIPTION
        "This variable is used to create or delete entries in the table."
    ::= { wsWDSAPGroupEntry 5 }

--
--  wsWDSAPGroupAPTable
--

   wsWDSAPGroupAPTable OBJECT-TYPE
         SYNTAX      SEQUENCE OF WsWDSAPGroupAPEntry
         MAX-ACCESS  not-accessible
         STATUS      current
         DESCRIPTION
                     "List of the AP MAC addresses in the AP Group"
         ::= { wdsManagedAP 2}

    wsWDSAPGroupAPEntry OBJECT-TYPE
         SYNTAX      WsWDSAPGroupAPEntry
         MAX-ACCESS  not-accessible
         STATUS      current
         DESCRIPTION
                     "Per Group Group Id and MAC address of the AP."
         INDEX       { wsWDSAPGroupId, wsWDSAPGroupAPMacAddress }
         ::= { wsWDSAPGroupAPTable 1 }

    WsWDSAPGroupAPEntry ::=
         SEQUENCE {
             wsWDSAPGroupAPMacAddress
                 MacAddress,
             wsWDSAPGroupAPStpPriority
                 Integer32,
             wsWDSAPGroupAPEntryRowStatus
                 RowStatus
         }

    wsWDSAPGroupAPMacAddress OBJECT-TYPE
         SYNTAX   MacAddress
         MAX-ACCESS  read-only
         STATUS      current
         DESCRIPTION
             "AP MAC address in the WDS AP Group"
         ::= { wsWDSAPGroupAPEntry 1 }

    wsWDSAPGroupAPStpPriority OBJECT-TYPE
         SYNTAX          Integer32(0..61440)
         MAX-ACCESS  not-accessible
         STATUS      current
         DESCRIPTION
             "AP's STP priority in the WDS AP Group"
         ::= { wsWDSAPGroupAPEntry 2 }

    wsWDSAPGroupAPEntryRowStatus OBJECT-TYPE
         SYNTAX      RowStatus
         MAX-ACCESS  read-only
         STATUS      current
         DESCRIPTION
             "This variable is used to create or delete entries in the table."
         ::= { wsWDSAPGroupAPEntry 3 }
--
-- wsWDSAPLinkTable
--

  wsWDSAPLinkTable OBJECT-TYPE
    SYNTAX          SEQUENCE OF WsWDSAPLinkEntry
    MAX-ACCESS      not-accessible
    STATUS          current
    DESCRIPTION
        "This table contains the WDS AP Links created on the
         controller."
     ::= { wdsManagedAP 3 }

  wsWDSAPLinkEntry OBJECT-TYPE
    SYNTAX          WsWDSAPLinkEntry
    MAX-ACCESS      not-accessible
    STATUS          current
    DESCRIPTION
         "Each entry in this table contains parameters for the WDS link
          of WDS AP Group in the Wireless network."
    INDEX    { wsWDSAPGroupId, wsWDSAPLinkSourceMacAddr, wsWDSAPLinkSourceRadio, wsWDSAPLinkDestMacAddr, wsWDSAPLinkDestRadio }
    ::= { wsWDSAPLinkTable 1 }

  WsWDSAPLinkEntry ::=
    SEQUENCE {
      wsWDSAPLinkSourceMacAddr                MacAddress,
      wsWDSAPLinkSourceRadio                  Integer32,
      wsWDSAPLinkDestMacAddr                  MacAddress,
      wsWDSAPLinkDestRadio                    Integer32,
      wsWDSAPLinkPathCost                     Integer32,
      wsWDSAPLinkRowStatus                    RowStatus
}
  wsWDSAPLinkSourceMacAddr OBJECT-TYPE
    SYNTAX          MacAddress
    MAX-ACCESS      read-only
    STATUS          current
    DESCRIPTION
        "MAC Address of one End-Point of WDS link."
    ::= { wsWDSAPLinkEntry 1 }

  wsWDSAPLinkSourceRadio OBJECT-TYPE
    SYNTAX          Integer32(1..2)
    MAX-ACCESS      read-only
    STATUS          current
    DESCRIPTION
        "Radio Number of the WDS Link End-Point on the Source AP."
    ::= { wsWDSAPLinkEntry 2 }

  wsWDSAPLinkDestMacAddr OBJECT-TYPE
    SYNTAX          MacAddress
    MAX-ACCESS      read-only
    STATUS          current
    DESCRIPTION
        "MAC Address of another End-Point of WDS link."
    ::= { wsWDSAPLinkEntry 3 }

  wsWDSAPLinkDestRadio OBJECT-TYPE
    SYNTAX          Integer32(1..2)
    MAX-ACCESS      read-only
    STATUS          current
    DESCRIPTION
        "Radio Number of the WDS Link End-Point on the Destination AP."
    ::= { wsWDSAPLinkEntry 4 }

  wsWDSAPLinkPathCost     OBJECT-TYPE
    SYNTAX          Integer32(0..255)
    MAX-ACCESS      not-accessible
    STATUS          current
    DESCRIPTION
        "Spanning Tree path cost for the WDS AP Link."
    ::= { wsWDSAPLinkEntry 5 }

  wsWDSAPLinkRowStatus    OBJECT-TYPE
    SYNTAX      RowStatus
    MAX-ACCESS  read-only
    STATUS      current
    DESCRIPTION
        "This variable is used to create or delete entries in the table."
     ::= { wsWDSAPLinkEntry 6 }

--
-- wsWDSAPGroupStatusTable
--
  wsWDSAPGroupStatusTable OBJECT-TYPE
    SYNTAX          SEQUENCE OF WsWDSAPGroupStatusEntry
    MAX-ACCESS      not-accessible
    STATUS          current
    DESCRIPTION
        "This table contains status parameters for the WDS APs created on the
         controller."
     ::= { wdsManagedAP 4 }

  wsWDSAPGroupStatusEntry OBJECT-TYPE
    SYNTAX          WsWDSAPGroupStatusEntry
    MAX-ACCESS      not-accessible
    STATUS          current
    DESCRIPTION
         "Each entry in this table contains status parameters for the WDS Group
          configured in WDS group database."
    INDEX    { wsWDSAPGroupId }
    ::= { wsWDSAPGroupStatusTable 1 }

  WsWDSAPGroupStatusEntry ::=
    SEQUENCE {
      wsWDSConfigAPCount              Integer32,
      wsWDSConnectedAPCount           Integer32,
      wsWDSRootAPCount                Integer32,
      wsWDSSatelliteAPCount           Integer32,
      wsWDSAPRootBridge               MacAddress,
      wsWDSAPRootDeviceType           INTEGER,
      wsWDSConfigWDSLinkCount         Integer32,
      wsWDSDetectedWDSLinkCount       Integer32,
      wsWDSBlockedWDSLinkCount        Integer32,
      wsWDSGroupNewPassword           DisplayString,
      wsWDSGroupChangePasswdStart     INTEGER,
      wsWDSGroupChangePasswdStatus    INTEGER
  }

  wsWDSConfigAPCount OBJECT-TYPE
    SYNTAX          Integer32(0..4)
    MAX-ACCESS      read-only
    STATUS          current
    DESCRIPTION
        "Number of APs configured by the Administrator in this WDS AP Group."
    ::= { wsWDSAPGroupStatusEntry 1 }

  wsWDSConnectedAPCount OBJECT-TYPE
    SYNTAX          Integer32(0..4)
    MAX-ACCESS      read-only
    STATUS          current
    DESCRIPTION
        "Number of APs managed by the controller that are members of this WDS AP Group."
    ::= { wsWDSAPGroupStatusEntry 2 }

  wsWDSRootAPCount OBJECT-TYPE
    SYNTAX          Integer32(0..4)
    MAX-ACCESS      read-only
    STATUS          current
    DESCRIPTION
        "Number of Root APs managed by the controller that are members of this WDS AP Group."
    ::= { wsWDSAPGroupStatusEntry 3 }

  wsWDSSatelliteAPCount OBJECT-TYPE
    SYNTAX          Integer32(0..4)
    MAX-ACCESS      read-only
    STATUS          current
    DESCRIPTION
        "Number of Satellite APs managed by the controller that are members of this WDS AP Group."
    ::= { wsWDSAPGroupStatusEntry 4 }

  wsWDSAPRootBridge OBJECT-TYPE
    SYNTAX          MacAddress
    MAX-ACCESS      not-accessible
    STATUS          current
    DESCRIPTION
        "MAC Address of the device elected as the Spanning Tree Root Bridge."
    ::= { wsWDSAPGroupStatusEntry 5 }

  wsWDSAPRootDeviceType OBJECT-TYPE
    SYNTAX          INTEGER{
                      none(0),
                      root-ap(1),
                      satellite-ap(2),
                      external-device(3)
                    }
    MAX-ACCESS      read-only
    STATUS          current
    DESCRIPTION
        "The type of device elected as the Spanning Tree Root bridge."
    DEFVAL      { none }
    ::= { wsWDSAPGroupStatusEntry 6}

  wsWDSConfigWDSLinkCount OBJECT-TYPE
    SYNTAX          Integer32(0..6)
    MAX-ACCESS      read-only
    STATUS          current
    DESCRIPTION
        "Number of configured bidirectional links in the WDS AP Group."
    ::= { wsWDSAPGroupStatusEntry 7}

 wsWDSDetectedWDSLinkCount OBJECT-TYPE
    SYNTAX          Integer32(0..6)
    MAX-ACCESS      read-only
    STATUS          current
    DESCRIPTION
        "Number of WDS links detected in the system."
    ::= { wsWDSAPGroupStatusEntry 8}

 wsWDSBlockedWDSLinkCount OBJECT-TYPE
    SYNTAX          Integer32(0..6)
    MAX-ACCESS      read-only
    STATUS          current
    DESCRIPTION
        "Number of WDS links blocked by the spanning tree protocol."
    ::= { wsWDSAPGroupStatusEntry 9}

  wsWDSGroupNewPassword OBJECT-TYPE
     SYNTAX       DisplayString(SIZE(8..63))
     MAX-ACCESS   read-only
     STATUS       current
     DESCRIPTION
        "This Password is sent to all controllers and APs when the Change-Password
         command is initiadted by the administrator for this WDS Group.
         When passwod is configured this object will always
         return '*****'."
     ::= {wsWDSAPGroupStatusEntry 10}

  wsWDSGroupChangePasswdStart    OBJECT-TYPE
         SYNTAX      INTEGER {
                       none(1),
                       start(2)
                     }
         MAX-ACCESS  read-only
         STATUS      current
         DESCRIPTION
             "This action object is used to:
                - start - Start the WDS Group password change for the peer controllers and the
                  managed APs.
                - Read on this object will always return none."
         DEFVAL      { none }
         ::= { wsWDSAPGroupStatusEntry 11 }

  wsWDSGroupChangePasswdStatus OBJECT-TYPE
        SYNTAX              INTEGER {
                              not-started(1),
                              requested(2),
                              success(3),
                              invalid-password(4),
                              in-progress(5),
                              timed-out(6),
                              failed(7)
                            }
        MAX-ACCESS          read-only
        STATUS              current
        DESCRIPTION
          "Status of the last invocation of the password change protocol."
        ::= {wsWDSAPGroupStatusEntry 12}

--
-- wsWDSAPStatusTable
--
  wsWDSAPStatusTable OBJECT-TYPE
    SYNTAX          SEQUENCE OF WsWDSAPStatusEntry
    MAX-ACCESS      not-accessible
    STATUS          current
    DESCRIPTION
        "This table contains status parameters for the WDS APs created on the
         controller."
     ::= { wdsManagedAP 5 }

  wsWDSAPStatusEntry OBJECT-TYPE
    SYNTAX          WsWDSAPStatusEntry
    MAX-ACCESS      not-accessible
    STATUS          current
    DESCRIPTION
         "Each entry in this table contains status parameters for the WDS AP
          configured in WDS group database."
    INDEX    { wsWDSAPGroupId, wsWDSAPMacAddr}
    ::= { wsWDSAPStatusTable 1 }

  WsWDSAPStatusEntry ::=
    SEQUENCE {
      wsWDSAPMacAddr                  MacAddress,
      wsWDSAPConnectionStatus         INTEGER,
      wsWDSAPSatelliteMode            INTEGER,
      wsWDSAPSTPRootMode              INTEGER,
      wsWDSAPSTPCost                  Unsigned32,
      wsWDSAPEthPortSTPStatus         INTEGER,
      wsWDSAPEthPortMode              INTEGER,
      wsWDSAPEthPortLinkState         INTEGER
  }

  wsWDSAPMacAddr OBJECT-TYPE
    SYNTAX          MacAddress
    MAX-ACCESS      read-only
    STATUS          current
    DESCRIPTION
        "MAC Address of the WDS AP."
    ::= { wsWDSAPStatusEntry 1 }

  wsWDSAPConnectionStatus OBJECT-TYPE
    SYNTAX          INTEGER {
                      not-connected(0),
                      connected(1)
                    }
    MAX-ACCESS      read-only
    STATUS          current
    DESCRIPTION
        "Flag indicating whether the AP is currently being managed by one of the
         Wireless controllers in the cluster."
    DEFVAL      { not-connected }
    ::= { wsWDSAPStatusEntry 2 }

   wsWDSAPSatelliteMode OBJECT-TYPE
    SYNTAX          INTEGER {
                      none(0),
                      wired(1),
                      satellite(2)
                    }
    MAX-ACCESS      read-only
    STATUS          current
    DESCRIPTION
        "Flag indicating whether the AP is a Satellite AP connected via WDS link or a Root AP connected via the wire to the campus network."
    DEFVAL      { none }
    ::= { wsWDSAPStatusEntry 3 }

   wsWDSAPSTPRootMode OBJECT-TYPE
    SYNTAX          INTEGER {
                      not-stp-root(0),
                      stp-root(1)
                    }
    MAX-ACCESS      not-accessible
    STATUS          current
    DESCRIPTION
        "Flag indicating whether the AP is the root of the spanning tree."
    DEFVAL      { not-stp-root }
    ::= { wsWDSAPStatusEntry 4 }

  wsWDSAPSTPCost OBJECT-TYPE
    SYNTAX          Unsigned32
    MAX-ACCESS      not-accessible
    STATUS          current
    DESCRIPTION
        "Spanning Tree Path Cost to the root."
    ::= { wsWDSAPStatusEntry 5 }

  wsWDSAPEthPortSTPStatus OBJECT-TYPE
    SYNTAX          INTEGER {
                      disabled(0),
                      forwarding(1),
                      learning(2),
                      listening(3),
                      blocking(4)
                    }
    MAX-ACCESS      not-accessible
    STATUS          current
    DESCRIPTION
        "Spanning Tree Status of the Ethernet Port."
    DEFVAL      { disabled }
    ::= { wsWDSAPStatusEntry 6 }

   wsWDSAPEthPortMode OBJECT-TYPE
     SYNTAX          INTEGER {
                      disabled(0),
                      enabled(1)
                    }
    MAX-ACCESS      read-only
    STATUS          current
    DESCRIPTION
        "Ethernet Port Mode."
    DEFVAL      { disabled }
    ::= { wsWDSAPStatusEntry 7 }

   wsWDSAPEthPortLinkState OBJECT-TYPE
     SYNTAX          INTEGER {
                      down(0),
                      up(1)
                    }
    MAX-ACCESS      read-only
    STATUS          current
    DESCRIPTION
        "Link State of Ethernet Port."
    DEFVAL      { down }
    ::= { wsWDSAPStatusEntry 8 }

--
-- wsWDSLinkStatusTable
--
  wsWDSLinkStatusTable OBJECT-TYPE
    SYNTAX          SEQUENCE OF WsWDSLinkStatusEntry
    MAX-ACCESS      not-accessible
    STATUS          current
    DESCRIPTION
        "This table contains status parameters for the WDS Links created on the
         controller."
     ::= { wdsManagedAP 6 }

  wsWDSLinkStatusEntry OBJECT-TYPE
    SYNTAX          WsWDSLinkStatusEntry
    MAX-ACCESS      not-accessible
    STATUS          current
    DESCRIPTION
         "Each entry in this table contains status parameters for the WDS link
          created on the Wireless network."
    INDEX    { wsWDSAPGroupId, wsWDSSourceMacAddr, wsWDSSourceRadio, wsWDSDestMacAddr, wsWDSDestRadio }
    ::= { wsWDSLinkStatusTable 1 }

  WsWDSLinkStatusEntry ::=
    SEQUENCE {
      wsWDSSourceMacAddr                MacAddress,
      wsWDSSourceRadio                  Integer32,
      wsWDSDestMacAddr                  MacAddress,
      wsWDSDestRadio                    Integer32,
      wsWDSLinkSourceEndPointDetected   INTEGER,
      wsWDSLinkDestEndPointDetected     INTEGER,
      wsWDSLinkSourceSTPState           INTEGER,
      wsWDSLinkDestSTPState             INTEGER,
      wsWDSLinkAggregationMode          INTEGER
  }

  wsWDSSourceMacAddr OBJECT-TYPE
    SYNTAX          MacAddress
    MAX-ACCESS      not-accessible
    STATUS          current
    DESCRIPTION
        "MAC Address of one End-Point of WDS link."
    ::= { wsWDSLinkStatusEntry 1 }

  wsWDSSourceRadio OBJECT-TYPE
    SYNTAX          Integer32(1..2)
    MAX-ACCESS      not-accessible
    STATUS          current
    DESCRIPTION
        "Radio Number of the WDS Link End-Point on the Source AP."
    ::= { wsWDSLinkStatusEntry 2 }

  wsWDSDestMacAddr OBJECT-TYPE
    SYNTAX          MacAddress
    MAX-ACCESS      not-accessible
    STATUS          current
    DESCRIPTION
        "MAC Address of another End-Point of WDS link."
    ::= { wsWDSLinkStatusEntry 3 }

  wsWDSDestRadio OBJECT-TYPE
    SYNTAX          Integer32(1..2)
    MAX-ACCESS      not-accessible
    STATUS          current
    DESCRIPTION
        "Radio Number of the WDS Link End-Point on the Destination AP."
    ::= { wsWDSLinkStatusEntry 4 }

  wsWDSLinkSourceEndPointDetected OBJECT-TYPE
    SYNTAX          INTEGER {
                      not-detected(0),
                      detected(1)
                    }
    MAX-ACCESS      read-only
    STATUS          current
    DESCRIPTION
        "Flag indicating whether AP specified by the Destination MAC detected
         the AP specified by the source MAC."
    DEFVAL      { not-detected }
    ::= { wsWDSLinkStatusEntry 5 }

  wsWDSLinkDestEndPointDetected OBJECT-TYPE
    SYNTAX          INTEGER {
                      not-detected(0),
                      detected(1)
                    }
    MAX-ACCESS      read-only
    STATUS          current
    DESCRIPTION
        "Flag indicating whether AP specified by the Source MAC detected the AP
         specified by the Destination MAC."
    DEFVAL      { not-detected }
    ::= { wsWDSLinkStatusEntry 6 }

  wsWDSLinkSourceSTPState OBJECT-TYPE
    SYNTAX          INTEGER {
                      disabled(0),
                      forwarding(1),
                      learning(2),
                      listening(3),
                      blocking(4)
                    }
    MAX-ACCESS      not-accessible
    STATUS          current
    DESCRIPTION
        "Spanning Tree State of the link on the source AP."
    DEFVAL      { disabled }
    ::= { wsWDSLinkStatusEntry 7 }

  wsWDSLinkDestSTPState OBJECT-TYPE
    SYNTAX          INTEGER {
                      disabled(0),
                      forwarding(1),
                      learning(2),
                      listening(3),
                      blocking(4)
                    }
    MAX-ACCESS      not-accessible
    STATUS          current
    DESCRIPTION
        "Spanning Tree State of the link on the destination AP."
    DEFVAL      { disabled }
    ::= { wsWDSLinkStatusEntry 8 }

  wsWDSLinkAggregationMode OBJECT-TYPE
    SYNTAX          INTEGER {
                      not-aggregated(0),
                      aggregated(1)
                    }
    MAX-ACCESS      read-only
    STATUS          current
    DESCRIPTION
        "When parallel links are defined between two APs, this parameter
         indicates whether this link is part of the aggregation link pair."
    DEFVAL      { not-aggregated }
    ::= { wsWDSLinkStatusEntry 9 }

--
-- wsWDSLinkStatisticsTable
--
  wsWDSLinkStatisticsTable OBJECT-TYPE
    SYNTAX       SEQUENCE OF WsWDSLinkStatisticsEntry
    MAX-ACCESS   not-accessible
    STATUS       current
    DESCRIPTION
        "This table contains statistics available for each AP
         managed by the controller."
    ::= { wdsManagedAP 7 }

  wsWDSLinkStatisticsEntry OBJECT-TYPE
    SYNTAX       WsWDSLinkStatisticsEntry
    MAX-ACCESS   not-accessible
    STATUS       current
    DESCRIPTION
        "Each entry in this table contain statistics available for each AP
         managed by the controller."
    AUGMENTS { wsWDSLinkStatusEntry }
    ::= { wsWDSLinkStatisticsTable 1 }

  WsWDSLinkStatisticsEntry ::=
    SEQUENCE {
      wsWDSLinkSourceAPPktsSent                 Counter64,
      wsWDSLinkSourceAPBytesSent                Counter64,
      wsWDSLinkSourceAPPktsRcvd                 Counter64,
      wsWDSLinkSourceAPBytesRcvd                Counter64,
      wsWDSLinkDestAPPktsSent                   Counter64,
      wsWDSLinkDestAPBytesSent                  Counter64,
      wsWDSLinkDestAPPktsRcvd                   Counter64,
      wsWDSLinkDestAPBytesRcvd                  Counter64
    }

  wsWDSLinkSourceAPPktsSent    OBJECT-TYPE
    SYNTAX          Counter64
    MAX-ACCESS      read-only
    STATUS          current
    DESCRIPTION
      "Total number of packets transmitted by the Source AP on the WDS link."
    ::= { wsWDSLinkStatisticsEntry 1 }

  wsWDSLinkSourceAPBytesSent    OBJECT-TYPE
    SYNTAX          Counter64
    MAX-ACCESS      read-only
    STATUS          current
    DESCRIPTION
      "Total number of bytes transmitted by the source AP on the link."
    ::= { wsWDSLinkStatisticsEntry 2 }

  wsWDSLinkSourceAPPktsRcvd    OBJECT-TYPE
    SYNTAX          Counter64
    MAX-ACCESS      read-only
    STATUS          current
    DESCRIPTION
      "Total number of packets received by the Source AP on the WDS link."
    ::= { wsWDSLinkStatisticsEntry 3 }

  wsWDSLinkSourceAPBytesRcvd    OBJECT-TYPE
    SYNTAX          Counter64
    MAX-ACCESS      read-only
    STATUS          current
    DESCRIPTION
      "Total number of bytes received by the Source AP on the WDS link."
    ::= { wsWDSLinkStatisticsEntry 4 }

  wsWDSLinkDestAPPktsSent    OBJECT-TYPE
    SYNTAX          Counter64
    MAX-ACCESS      read-only
    STATUS          current
    DESCRIPTION
      "Total number of packets transmitted by the Destination AP on the WDS
       link."
    ::= { wsWDSLinkStatisticsEntry 5 }

  wsWDSLinkDestAPBytesSent    OBJECT-TYPE
    SYNTAX          Counter64
    MAX-ACCESS      read-only
    STATUS          current
    DESCRIPTION
      "Total number of bytes transmitted by the Destination AP on the WDS link."
    ::= { wsWDSLinkStatisticsEntry 6 }

  wsWDSLinkDestAPPktsRcvd    OBJECT-TYPE
    SYNTAX          Counter64
    MAX-ACCESS      read-only
    STATUS          current
    DESCRIPTION
      "Total number of packets received by the Destination AP on the WDS link."
    ::= { wsWDSLinkStatisticsEntry 7 }

  wsWDSLinkDestAPBytesRcvd    OBJECT-TYPE
    SYNTAX          Counter64
    MAX-ACCESS      read-only
    STATUS          current
    DESCRIPTION
      "Total Number of bytes received by the Destination AP on the WDS link."
    ::= { wsWDSLinkStatisticsEntry 8 }

  wsWDSGroupConfigRequestAction    OBJECT-TYPE
         SYNTAX      INTEGER {
                       none(1),
                       start(2)
                     }
         MAX-ACCESS  read-only
         STATUS      current
         DESCRIPTION
             "This action object is used to:
                - start - Start the WDS Group config push to the peer controllers and the
           managed APs.
                - Read on this object will always return none."
         DEFVAL      { none }
         ::= { wdsManagedAP 8 }

--******************************************************************************
-- wdsManagedAP End
--******************************************************************************
--******************************************************************************
-- deviceLocation Starts
--******************************************************************************
--
-- wsDevLocBldngTable
--
   wsDevLocBldngTable OBJECT-TYPE
        SYNTAX           SEQUENCE OF WsDevLocBldngEntry
        MAX-ACCESS       not-accessible
        STATUS           current
        DESCRIPTION
          "This table contains data for configuration parameters for device location."
        ::= { deviceLocation 1 }

   wsDevLocBldngEntry OBJECT-TYPE
     SYNTAX       WsDevLocBldngEntry
     MAX-ACCESS   not-accessible
     STATUS       current
     DESCRIPTION
          "Each entry in this table contains building parameters."
     INDEX    { wsDevLocBldngNum }
     ::= { wsDevLocBldngTable 1 }

   WsDevLocBldngEntry ::=
     SEQUENCE {
      wsDevLocBldngNum          Integer32,
      wsDevLocBldngDesc         DisplayString,
      wsDevLocFlrCount          INTEGER,
      wsDevLocApCount           INTEGER,
      wsDevLocBldngRowStatus    RowStatus
   }

   wsDevLocBldngNum  OBJECT-TYPE
     SYNTAX          Integer32(1..8)
     MAX-ACCESS      read-only
     STATUS          current
     DESCRIPTION
        "Indicates building number for a particular building."
     ::= { wsDevLocBldngEntry 1 }

   wsDevLocBldngDesc  OBJECT-TYPE
     SYNTAX           DisplayString(SIZE(0..64))
     MAX-ACCESS       read-only
     STATUS           current
     DESCRIPTION
         "The building description for a particular building."
     ::= { wsDevLocBldngEntry 2 }

   wsDevLocFlrCount  OBJECT-TYPE
     SYNTAX          INTEGER(0..20)
     MAX-ACCESS      read-only
     STATUS          current
     DESCRIPTION
        "Indicates floor count for a particular building."

     DEFVAL      { 0 }
     ::= { wsDevLocBldngEntry 3 }

   wsDevLocApCount   OBJECT-TYPE
     SYNTAX          INTEGER(0..192)
     MAX-ACCESS      read-only
     STATUS          current
     DESCRIPTION
        "Indicates AP count for a particular building."
     DEFVAL      { 0 }
     ::= { wsDevLocBldngEntry 4 }

    wsDevLocBldngRowStatus OBJECT-TYPE
     SYNTAX                RowStatus
     MAX-ACCESS            read-only
     STATUS                current
     DESCRIPTION
        "This variable is used to create and delete entries
         in the table."
     ::= { wsDevLocBldngEntry 5 }

--
-- wsDevLocBldngFlrTable
--
   wsDevLocBldngFlrTable OBJECT-TYPE
      SYNTAX           SEQUENCE OF WsDevLocBldngFlrEntry
      MAX-ACCESS       not-accessible
      STATUS           current
      DESCRIPTION
      "This table contains data for configuration parameters for device location
       building and floor."
       ::= { deviceLocation 2 }

   wsDevLocBldngFlrEntry OBJECT-TYPE
     SYNTAX       WsDevLocBldngFlrEntry
     MAX-ACCESS   not-accessible
     STATUS       current
     DESCRIPTION
          "Each entry in this table contains building floor parameters."
     INDEX    { wsDevLocBldngNum,
                wsDevLocBldngFlrNum }
     ::= { wsDevLocBldngFlrTable 1 }

   WsDevLocBldngFlrEntry ::=
     SEQUENCE {
      wsDevLocBldngFlrNum      Integer32,
      wsDevLocBldngFlrDesc     DisplayString,
      wsDevLocBldngFlrApCount  INTEGER,
      wsDevLocFlrRowStatus     RowStatus
   }

   wsDevLocBldngFlrNum  OBJECT-TYPE
     SYNTAX             Integer32(1..20)
     MAX-ACCESS         not-accessible
     STATUS             current
     DESCRIPTION
        "Indicates floor number for a particular building."
     ::= { wsDevLocBldngFlrEntry 1 }

   wsDevLocBldngFlrDesc  OBJECT-TYPE
     SYNTAX              DisplayString(SIZE(0..64))
     MAX-ACCESS          read-only
     STATUS              current
     DESCRIPTION
         "The floor description for a particular floor."
     ::= { wsDevLocBldngFlrEntry 2 }

   wsDevLocBldngFlrApCount   OBJECT-TYPE
     SYNTAX                  INTEGER(0..192)
     MAX-ACCESS              read-only
     STATUS                  current
     DESCRIPTION
        "Indicates AP count for a particular building-floor."
     DEFVAL      { 0 }
     ::= { wsDevLocBldngFlrEntry 3 }

   wsDevLocFlrRowStatus OBJECT-TYPE
     SYNTAX             RowStatus
     MAX-ACCESS         read-only
     STATUS             current
     DESCRIPTION
        "This variable is used to create and delete entries
         in the table."
     ::= { wsDevLocBldngFlrEntry 4 }

--
-- wsDevLocManagedApTable
--
   wsDevLocManagedApTable OBJECT-TYPE
      SYNTAX           SEQUENCE OF WsDevLocManagedApEntry
      MAX-ACCESS       not-accessible
      STATUS           current
      DESCRIPTION
      "This table contains data for configuration parameters for device location
       building, floor and AP."
        ::= { deviceLocation 3 }

   wsDevLocManagedApEntry OBJECT-TYPE
     SYNTAX       WsDevLocManagedApEntry
     MAX-ACCESS   not-accessible
     STATUS       current
     DESCRIPTION
          "Each entry in this table contains building floor parameters."
     INDEX    { wsDevLocBldngNum,
                wsDevLocBldngFlrNum,
                wsDevLocManagedApMac }
     ::= { wsDevLocManagedApTable 1 }

   WsDevLocManagedApEntry ::=
     SEQUENCE {
      wsDevLocManagedApMac        MacAddress,
      wsDevLocMeasurementUnit     INTEGER,
      wsDevLocManagedApXCoord     Integer32,
      wsDevLocManagedApYCoord     Integer32,
      wsDevLocManagedApRowStatus  RowStatus
   }

  wsDevLocManagedApMac  OBJECT-TYPE
    SYNTAX            MacAddress
    MAX-ACCESS        read-only
    STATUS            current
    DESCRIPTION
       "The MAC address of the AP."
     ::= {wsDevLocManagedApEntry 1 }

  wsDevLocMeasurementUnit OBJECT-TYPE
      SYNTAX                INTEGER {
                                    meters(1),
                                    feet(2)
                                    }
      MAX-ACCESS            read-only
      STATUS                current
      DESCRIPTION
      "Measurement Units in Meters/Feet."
      ::= { wsDevLocManagedApEntry 2 }

  wsDevLocManagedApXCoord  OBJECT-TYPE
   SYNTAX                 Integer32(-3000..3000)
   MAX-ACCESS             read-only
   STATUS                 current
   DESCRIPTION
       "This indicates the X-coordinate of the AP."
     ::= {wsDevLocManagedApEntry 3 }

  wsDevLocManagedApYCoord  OBJECT-TYPE
   SYNTAX                 Integer32(-3000..3000)
   MAX-ACCESS             read-only
   STATUS                 current
   DESCRIPTION
       "This indicates the Y-coordinate of the AP."
    ::= {wsDevLocManagedApEntry 4 }

 wsDevLocManagedApRowStatus OBJECT-TYPE
     SYNTAX                 RowStatus
     MAX-ACCESS             read-only
     STATUS                 current
     DESCRIPTION
        "This variable is used to create and delete entries
         in the table. AP entry should be created with Measurement
         Unit and XY-Coordinates."
     ::= { wsDevLocManagedApEntry 5 }

   wsOnDemandTrigger                            OBJECT IDENTIFIER ::= { deviceLocation 4 }
   wsOnDemandTriggerGlobalStatus                OBJECT IDENTIFIER ::= { deviceLocation 5 }
   wsOnDemandTriggerFloorStatus                 OBJECT IDENTIFIER ::= { deviceLocation 6 }

--
-- wsOnDemandTrigger
--
  wsOnDemandTriggerDeviceType    OBJECT-TYPE
    SYNTAX          INTEGER {
                        ap(1),
                         client(2)
                    }
    MAX-ACCESS read-only
    STATUS     current
    DESCRIPTION
        "Type of the device to be located."
    DEFVAL      { ap }
    ::= { wsOnDemandTrigger 1 }

  wsOnDemandTriggerDeviceMACAddress    OBJECT-TYPE
    SYNTAX          MacAddress
    MAX-ACCESS      read-only
    STATUS          current
    DESCRIPTION
        "AP or Client MAC address whose location the Administrator
         want to find."
    ::= { wsOnDemandTrigger 2 }

  wsOnDemandTriggerBuildingNumber    OBJECT-TYPE
    SYNTAX          Unsigned32(0..8)
    MAX-ACCESS      read-only
    STATUS          current
    DESCRIPTION
        "Building number in which to search for the target device.
         Please note that only configured buildings will be accepted.
         Buildings with no configured floors are not accepted.
         Value 0 is used to indicate search in all of the buildings
         in the system. Value 0 is accepted only if there exists any
         configured building-floor.
         Setting building to 0 will automatically reset floor value to 0."
    DEFVAL      { 0 }
    ::= { wsOnDemandTrigger 3 }

  wsOnDemandTriggerFloorNumber    OBJECT-TYPE
    SYNTAX          Unsigned32(0..20)
    MAX-ACCESS      read-only
    STATUS          current
    DESCRIPTION
        "Floor Number on which to search. Please note that only
         configured floor numbers for the specified building will be
         accepted.
         Value 0 is used to indicate search in all of the floors
         in the specified building. Value 0 is accepted only if there
         exists any configured floor in the current building."
    DEFVAL      { 0 }
    ::= { wsOnDemandTrigger 4 }

  wsOnDemandTriggerUseRadios    OBJECT-TYPE
    SYNTAX          INTEGER {
                         sentry(1),
                         sentryAndOperational(2)
                    }
     MAX-ACCESS     read-only
     STATUS         current
     DESCRIPTION
        "This object Indicates if the network should use only
         sentry radios to do the search or both sentry and
         operational mode radios."
    DEFVAL      { sentry }
    ::= { wsOnDemandTrigger 5 }

  wsOnDemandTriggerStatus    OBJECT-TYPE
    SYNTAX          INTEGER {
                         notInProgress(1),
                         inProgress(2)
                    }
    MAX-ACCESS      read-only
    STATUS          current
    DESCRIPTION
        "Status of the last invoked On-Demand location procedure."
    DEFVAL      { notInProgress }
    ::= { wsOnDemandTrigger 6 }

  wsOnDemandTriggerNumOfAPs    OBJECT-TYPE
    SYNTAX          Unsigned32
    MAX-ACCESS      read-only
    STATUS          current
    DESCRIPTION
        "Number of managed APs that are available for locating the
         target device in the building/floor/sentry scope specified
         by the administrator."
    DEFVAL      { 0 }
    ::= { wsOnDemandTrigger 7 }

  wsOnDemandTriggerStart    OBJECT-TYPE
    SYNTAX          INTEGER {
                         none(0),
                         start(1)
                    }
    MAX-ACCESS      read-only
    STATUS          current
    DESCRIPTION
        "Trigger new On-Demand location procedure for the device
         specified in the configured building and floors.
         If On-Demand procedure is already running then setting
         this parameter has no effect.A read on this object will always return none."
    DEFVAL      { none }
    ::= { wsOnDemandTrigger 8 }

--
-- wsOnDemandTriggerGlobalStatus
--
  wsOnDemandTriggerGlobalStatusDeviceType    OBJECT-TYPE
    SYNTAX          INTEGER {
                         ap(1),
                         client(2)
                    }
    MAX-ACCESS      read-only
    STATUS          current
    DESCRIPTION
        "Flag indicating whether the device is an AP or
         a Wireless Client."
    DEFVAL      { ap }
    ::= { wsOnDemandTriggerGlobalStatus 1 }

  wsOnDemandTriggerGlobalStatusDeviceMACAddress    OBJECT-TYPE
    SYNTAX          MacAddress
    MAX-ACCESS      read-only
    STATUS          current
    DESCRIPTION
        "AP or Client MAC address whose location was requested."
    ::= { wsOnDemandTriggerGlobalStatus 2 }

  wsOnDemandTriggerGlobalStatusBuildingNumber    OBJECT-TYPE
    SYNTAX          Unsigned32(0..8)
    MAX-ACCESS      read-only
    STATUS          current
    DESCRIPTION
        "Building number in which to search for the target device
         was done.
         Value 0 is used to indicate search in all of the buildings
         in the system."
    DEFVAL      { 0 }
    ::= { wsOnDemandTriggerGlobalStatus 3 }

  wsOnDemandTriggerGlobalStatusFloorNumber    OBJECT-TYPE
    SYNTAX          Unsigned32(0..20)
    MAX-ACCESS      read-only
    STATUS          current
    DESCRIPTION
        "Floor Number on which the search was done.
         Value 0 is used to indicate search in all of the floors
         in the specified building."
    DEFVAL      { 0 }
    ::= { wsOnDemandTriggerGlobalStatus 4 }

  wsOnDemandTriggerGlobalStatusUsedRadios    OBJECT-TYPE
    SYNTAX          INTEGER {
                         sentry(1),
                         sentryAndOperational(2)
                    }
    MAX-ACCESS      read-only
    STATUS          current
    DESCRIPTION
        "Flag indicating whether the network used only sentry radios
         to do the search or both sentry and operational mode radios."
    DEFVAL      { sentry }
    ::= { wsOnDemandTriggerGlobalStatus 5 }

  wsOnDemandTriggerGlobalStatusCurrentStatus    OBJECT-TYPE
    SYNTAX          INTEGER {
                         notStarted(1),
                         inProgress(2),
                         deviceLocated(3),
                         deviceNotLocated(4),
                         noAPsAvailable(5)
                    }
    MAX-ACCESS      read-only
    STATUS          current
    DESCRIPTION
        "Current status of the last invocation of the On-Demand
         Location Procedure. "
    DEFVAL      { notStarted }
    ::= { wsOnDemandTriggerGlobalStatus 6 }

  wsOnDemandTriggerGlobalStatusSearchTime  OBJECT-TYPE
    SYNTAX       TimeTicks
    MAX-ACCESS   read-only
    STATUS       current
    DESCRIPTION
        "Time since the On-Demand Location triggered."
    ::= { wsOnDemandTriggerGlobalStatus 7 }

  wsOnDemandTriggerGlobalStatusNumOfLocatorAPs    OBJECT-TYPE
    SYNTAX          Unsigned32
    MAX-ACCESS      read-only
    STATUS          current
    DESCRIPTION
        "Number of managed APs that were used for locating
         the target device."
    DEFVAL      { 0 }
    ::= { wsOnDemandTriggerGlobalStatus 8 }

  wsOnDemandTriggerGlobalStatusNumOfDetectedAPs    OBJECT-TYPE
    SYNTAX          Unsigned32
    MAX-ACCESS      read-only
    STATUS          current
    DESCRIPTION
        "Number of managed APs that detected the device."
    DEFVAL      { 0 }
    ::= { wsOnDemandTriggerGlobalStatus 9 }

  wsOnDemandTriggerGlobalStatusNumOfDetectedBuildings    OBJECT-TYPE
    SYNTAX          Unsigned32
    MAX-ACCESS      read-only
    STATUS          current
    DESCRIPTION
        "Number of buildings where managed APs detected
         the target device."
    DEFVAL      { 0 }
    ::= { wsOnDemandTriggerGlobalStatus 10 }

  wsOnDemandTriggerGlobalStatusNumOfDetectedFloors    OBJECT-TYPE
    SYNTAX          Unsigned32
    MAX-ACCESS      read-only
    STATUS          current
    DESCRIPTION
        "Number of building floors where managed APs detected
         the target device. Floors from different buildings
         may be included in this status."
    DEFVAL      { 0 }
    ::= { wsOnDemandTriggerGlobalStatus 11 }

  wsOnDemandTriggerGlobalStatusHighestSignalFoundBuilding    OBJECT-TYPE
    SYNTAX          Unsigned32
    MAX-ACCESS      read-only
    STATUS          current
    DESCRIPTION
        "Building number in which the target device was detected
         by a managed AP with the highest RSSI.
         Value of 0 for this object indicates that device is
         not detected in any of the buildings."
    DEFVAL      { 0 }
    ::= { wsOnDemandTriggerGlobalStatus 12 }

  wsOnDemandTriggerGlobalStatusHighestSignalFoundFloor    OBJECT-TYPE
    SYNTAX      Unsigned32
    MAX-ACCESS  read-only
    STATUS      current
    DESCRIPTION
        "Floor number on which the target device was detected
         by a managed AP with the highest RSSI.
         Value of 0 for this object indicates that device is
         not detected in any of the floors."
    DEFVAL      { 0 }
    ::= { wsOnDemandTriggerGlobalStatus 13 }

--
--  wsOnDemandTriggerFloorStatusTable
--
  wsOnDemandTriggerFloorStatusTable OBJECT-TYPE
    SYNTAX          SEQUENCE OF WsOnDemandTriggerFloorStatusEntry
    MAX-ACCESS      not-accessible
    STATUS          current
    DESCRIPTION
        "This table contains the location record for each building floor."
    ::= { wsOnDemandTriggerFloorStatus 1 }

  wsOnDemandTriggerFloorStatusEntry OBJECT-TYPE
    SYNTAX          WsOnDemandTriggerFloorStatusEntry
    MAX-ACCESS      not-accessible
    STATUS          current
    DESCRIPTION
        "Location record. Each entry contains location status of the
         target device with respect to building anf floor numbers."
    INDEX    { wsOnDemandTriggerFloorStatusBuildingNum,
               wsOnDemandTriggerFloorStatusFloorNum }
    ::= { wsOnDemandTriggerFloorStatusTable 1 }

  WsOnDemandTriggerFloorStatusEntry ::=
    SEQUENCE {
        wsOnDemandTriggerFloorStatusBuildingNum           Unsigned32,
        wsOnDemandTriggerFloorStatusFloorNum              Unsigned32,
        wsOnDemandTriggerFloorStatusDeviceFound           INTEGER,
        wsOnDemandTriggerFloorStatusNumOfAPs              Unsigned32,
        wsOnDemandTriggerFloorStatusSolutionType          INTEGER,
        wsOnDemandTriggerFloorStatusXCoordinate           INTEGER,
        wsOnDemandTriggerFloorStatusYCoordinate           INTEGER,
        wsOnDemandTriggerFloorStatusCircleRadius          Unsigned32,
        wsOnDemandTriggerFloorStatusSigma                 INTEGER
  }

  wsOnDemandTriggerFloorStatusBuildingNum OBJECT-TYPE
    SYNTAX          Unsigned32
    MAX-ACCESS      read-only
    STATUS          current
    DESCRIPTION
        "Building number."
    ::= { wsOnDemandTriggerFloorStatusEntry 1 }

  wsOnDemandTriggerFloorStatusFloorNum OBJECT-TYPE
    SYNTAX          Unsigned32
    MAX-ACCESS      read-only
    STATUS          current
    DESCRIPTION
        "Floor number"
    ::= { wsOnDemandTriggerFloorStatusEntry 2 }

  wsOnDemandTriggerFloorStatusDeviceFound OBJECT-TYPE
    SYNTAX          INTEGER {
                         notFound(1),
                         found(2)
                    }
    MAX-ACCESS      read-only
    STATUS          current
    DESCRIPTION
        "Flag indicating whether the device is found on this floor."
    ::= { wsOnDemandTriggerFloorStatusEntry 3 }

   wsOnDemandTriggerFloorStatusNumOfAPs OBJECT-TYPE
    SYNTAX          Unsigned32
    MAX-ACCESS      read-only
    STATUS          current
    DESCRIPTION
        "Number of APs located on this floor that detected the
         device."
    ::= { wsOnDemandTriggerFloorStatusEntry 4 }

  wsOnDemandTriggerFloorStatusSolutionType OBJECT-TYPE
    SYNTAX          INTEGER {
                         noSolution(1),
                         circle(2),
                         point(3)
                    }
    MAX-ACCESS      read-only
    STATUS          current
    DESCRIPTION
        "Flag indicating whether the probability map is
         a circle around the managed AP, or the solution is an X,Y
         coordinate."
    ::= { wsOnDemandTriggerFloorStatusEntry 5 }

  wsOnDemandTriggerFloorStatusXCoordinate OBJECT-TYPE
    SYNTAX          INTEGER
    MAX-ACCESS      read-only
    STATUS          current
    DESCRIPTION
        "X-axis offset. The parameter is applicable to the Circle
         and Point solution."
    ::= { wsOnDemandTriggerFloorStatusEntry 6 }

  wsOnDemandTriggerFloorStatusYCoordinate OBJECT-TYPE
    SYNTAX          INTEGER
    MAX-ACCESS      read-only
    STATUS          current
    DESCRIPTION
        "Y-axis offset. The parameter is applicable to the Circle
         and Point solution."
    ::= { wsOnDemandTriggerFloorStatusEntry 7 }

  wsOnDemandTriggerFloorStatusCircleRadius OBJECT-TYPE
    SYNTAX          Unsigned32
    MAX-ACCESS      read-only
    STATUS          current
    DESCRIPTION
        "For the Circle solution this parameter represents the radius
         from the X,Y coordinate where the device is most likely to be
         located. For the Point solution this value is not applicable
         and is set to 0."
    ::= { wsOnDemandTriggerFloorStatusEntry 8 }

  wsOnDemandTriggerFloorStatusSigma OBJECT-TYPE
    SYNTAX          INTEGER
    MAX-ACCESS      read-only
    STATUS          current
    DESCRIPTION
        "The standard deviation for the location. The parameter is
         applicable to Circle and Point solutions. For the Circle
         solution the Sigma represents the offset from Circle Radius.
         For the Point solution the sigma represents the radius from
         the X,Y coordinate."
    ::= { wsOnDemandTriggerFloorStatusEntry 9 }

--
-- wsTriangulationLocStatusTable
--

  wsTriangulationLocStatusTable OBJECT-TYPE
      SYNTAX           SEQUENCE OF WsTriangulationLocStatusEntry
      MAX-ACCESS       not-accessible
      STATUS           current
      DESCRIPTION
      "This table contains data for triangulation location and
       status information."
        ::= { deviceLocation 7 }

   wsTriangulationLocStatusEntry OBJECT-TYPE
     SYNTAX                      WsTriangulationLocStatusEntry
     MAX-ACCESS                  not-accessible
     STATUS                      current
     DESCRIPTION
          "Each entry has parameters that indicate triangulation location
           status values."
     INDEX    {wsTriangLocMacAddress }
     ::= { wsTriangulationLocStatusTable 1 }

   WsTriangulationLocStatusEntry ::=
     SEQUENCE {
      wsTriangLocMacAddress        MacAddress,
      wsTriangLocDataType          INTEGER,
      wsTriangLocStatus            INTEGER,
      wsTriangLocDeviceType        INTEGER,
      wsTriangLocAge               TimeTicks,
      wsTriangLocBldng             Integer32,
      wsTriangLocFlr               Integer32,
      wsTriangLocXCoord            Integer32,
      wsTriangLocYCoord            Integer32
   }

   wsTriangLocMacAddress  OBJECT-TYPE
        SYNTAX              MacAddress
        MAX-ACCESS          read-only
        STATUS              current
        DESCRIPTION
          "MAC address of an AP or Client."
        ::= { wsTriangulationLocStatusEntry 1}

   wsTriangLocDataType   OBJECT-TYPE
        SYNTAX              INTEGER {
                              not-present(0),
                              present(1)
                            }
        MAX-ACCESS          read-only
        STATUS              current
        DESCRIPTION
          "This parameter indicates whether the location data
            is present for this device."
        ::= { wsTriangulationLocStatusEntry 2}

   wsTriangLocStatus     OBJECT-TYPE
        SYNTAX              INTEGER {
                              not-executed(1),
                              success(2),
                              failure(3)
                            }
        MAX-ACCESS          read-only
        STATUS              current
        DESCRIPTION
          "The status of the last iteration of the location computation algorithm."
        ::= { wsTriangulationLocStatusEntry 3 }

   wsTriangLocDeviceType   OBJECT-TYPE
        SYNTAX              INTEGER {
                              ap(1),
                              client(2)
                            }
        MAX-ACCESS          read-only
        STATUS              current
        DESCRIPTION
          "This parameter indicates device type whether AP or Client."
        ::= { wsTriangulationLocStatusEntry 4}

   wsTriangLocAge       OBJECT-TYPE
        SYNTAX              TimeTicks
        MAX-ACCESS          read-only
        STATUS              current
        DESCRIPTION
          "Time since the last successful location computation."
        ::= { wsTriangulationLocStatusEntry 5 }

   wsTriangLocBldng     OBJECT-TYPE
         SYNTAX          Integer32(1..8)
         MAX-ACCESS      read-only
         STATUS          current
         DESCRIPTION
           "Indicates building number in which device is detected."
         ::= { wsTriangulationLocStatusEntry 6 }

    wsTriangLocFlr      OBJECT-TYPE
         SYNTAX          Integer32(1..20)
         MAX-ACCESS      read-only
         STATUS          current
         DESCRIPTION
           "Indicates floor number in which device is detected."
         ::= { wsTriangulationLocStatusEntry 7 }

    wsTriangLocXCoord    OBJECT-TYPE
         SYNTAX           Integer32(-3000..3000)
         MAX-ACCESS       read-only
         STATUS           current
         DESCRIPTION
           "This indicates the X axis offset of the device from
            some arbitrary 0,0 point on the building floor."
         ::= {wsTriangulationLocStatusEntry 8 }

     wsTriangLocYCoord    OBJECT-TYPE
         SYNTAX           Integer32(-3000..3000)
         MAX-ACCESS       read-only
         STATUS           current
         DESCRIPTION
           "This indicates the Y axis offset of the device from
            some arbitrary 0,0 point on the building floor."
         ::= {wsTriangulationLocStatusEntry 9 }

--******************************************************************************
-- deviceLocation Ends
--******************************************************************************


--**************************************************************************************
-- authenticatedClient
--**************************************************************************************
--
--   wsAuthenticatedClientStatusTable
--

 wsAuthenticatedClientStatusTable OBJECT-TYPE
     SYNTAX       SEQUENCE OF WsAuthenticatedClientStatusEntry
     MAX-ACCESS   not-accessible
     STATUS       current
     DESCRIPTION
           "This table contains status parameters of clients that are
            currently associated with managed APs."
     ::= { authenticatedClient 1 }

    wsAuthenticatedClientStatusEntry OBJECT-TYPE
     SYNTAX       WsAuthenticatedClientStatusEntry
     MAX-ACCESS   not-accessible
     STATUS       current
     DESCRIPTION
          "Each entry in this table contain client status parameters
           assocaited with the WS managed AP."
     INDEX    { wsAuthenticatedClientMacAddress }
     ::= { wsAuthenticatedClientStatusTable 1 }

 WsAuthenticatedClientStatusEntry ::=
     SEQUENCE {
      wsAuthenticatedClientMacAddress                MacAddress,
      wsAuthenticatedClientTunnelIpAddress           IpAddress,
      wsAuthenticatedClientUserName                  DisplayString,
      wsAuthenticatedClientSSID                      DisplayString,
      wsAuthenticatedClientVLAN                      Integer32,
      wsAuthenticatedClientStatus                    INTEGER,
      wsAuthenticatedClientTxDataRate                Integer32,
      wsAuthenticatedClientInactivePeriod            TimeTicks,
      wsAuthenticatedClientDisassociateAction        INTEGER,
      wsAuthenticatedClientAge                       TimeTicks,
      wsAuthenticatedClientNwTime                    TimeTicks,
      wsAuthenticatedClientAssociatingSwitch         INTEGER,
      wsAuthenticatedClientSwitchMacAddress          MacAddress,
      wsAuthenticatedClientSwitchIpAddress           IpAddress,
      wsAuthenticatedClientDot11nCapable             INTEGER,
      wsAuthenticatedClientStbcCapable             INTEGER,
      wsAuthenticatedClientDistTunnelStatus          INTEGER,
      wsAuthenticatedClientDistTunnelRoamStatus      INTEGER,
      wsAuthenticatedClientDistTunnelHomeAPMac       MacAddress,
      wsAuthenticatedClientDistTunnelAssocAPMac      MacAddress,
      wsAuthenticatedClientAPMacAddress              MacAddress,
      wsAuthenticatedClientBSSID                     MacAddress,
      wsAuthenticatedClientRadioInterface            Integer32,
      wsAuthenticatedClientChannel                   Integer32,
      wsAuthenticatedClientIpAddress                 IpAddress,
      wsAuthenticatedClientNetBiosName               DisplayString,
      wsAuthenticatedClientRRMSupported              INTEGER,
      wsAuthenticatedClientRRMLocationReportSupported  INTEGER,
      wsAuthenticatedClientRRMBeaconTableMeasurementSupported  INTEGER,
      wsAuthenticatedClientRRMBeaconActiveMeasurementSupported  INTEGER,
      wsAuthenticatedClientRRMBeaconPassiveMeasurementSupported  INTEGER,
      wsAuthenticatedClientRRMChannelLoadMeasurementSupported  INTEGER,
      wsAuthenticatedClientDot11acCapable             INTEGER
 }

 wsAuthenticatedClientMacAddress  OBJECT-TYPE
     SYNTAX       MacAddress
     MAX-ACCESS   read-only
     STATUS       current
     DESCRIPTION
        "Authenticated client MAC address."
     ::= {wsAuthenticatedClientStatusEntry  1 }

 wsAuthenticatedClientTunnelIpAddress OBJECT-TYPE
     SYNTAX       IpAddress
     MAX-ACCESS   not-accessible
     STATUS       current
     DESCRIPTION
        "Indicates network IP address of the client station, 0.0.0.0 indicates unknown.
         Tunnel IP subnet is present only for clients authenticated with tunneled VAPs."
     ::= {wsAuthenticatedClientStatusEntry  2 }

 wsAuthenticatedClientUserName OBJECT-TYPE
     SYNTAX       DisplayString(SIZE(0..32))
     MAX-ACCESS   read-only
     STATUS       current
     DESCRIPTION
        "Indicates user name of the client that have authenticated via
         802.1x, clients on networks with other security modes will
         not have a user name."
     ::= { wsAuthenticatedClientStatusEntry 3 }

 wsAuthenticatedClientSSID OBJECT-TYPE
     SYNTAX       DisplayString(SIZE(0..32))
     MAX-ACCESS   read-only
     STATUS       current
     DESCRIPTION
        "Indicates the network on which the client is connected."
     ::= { wsAuthenticatedClientStatusEntry 4 }

 wsAuthenticatedClientVLAN OBJECT-TYPE
     SYNTAX       Integer32(0..4094)
     MAX-ACCESS   read-only
     STATUS       current
     DESCRIPTION
        "If client is on VAP using VLAN data forwarding mode,
         indicates current assigned VLAN."
     ::= { wsAuthenticatedClientStatusEntry 5 }

 wsAuthenticatedClientStatus OBJECT-TYPE
     SYNTAX       INTEGER {
                       authenticated(1),
                       associated(2),
                       disassociated(3)
                  }
     MAX-ACCESS   read-only
     STATUS       current
     DESCRIPTION
        "This object indicates client's status."
     ::= { wsAuthenticatedClientStatusEntry 6 }

 wsAuthenticatedClientTxDataRate OBJECT-TYPE
     SYNTAX       Integer32(2..1200)
     MAX-ACCESS   read-only
     STATUS       current
     DESCRIPTION
       "Indicates the data rate, AP will actually support
        in setting up communications with client stations
        represented by a count from 2 - 1200, corresponding
        to data rates in multiples of 500 kbit/s from 1 Mbit/s
        to 600 Mbit/s.
        Supported Data Rate          Mbps
            2                          1
            4                          2
            11                         5.5
            12                         6
            18                         9 and so on. "
     ::= { wsAuthenticatedClientStatusEntry 7 }

 wsAuthenticatedClientInactivePeriod    OBJECT-TYPE
     SYNTAX      TimeTicks
     MAX-ACCESS  read-only
     STATUS      current
     DESCRIPTION
         "For a current association, period of time that
          the AP has not seen any traffic for the client."
     ::= { wsAuthenticatedClientStatusEntry 8 }

 wsAuthenticatedClientDisassociateAction    OBJECT-TYPE
     SYNTAX      INTEGER {
                   none(1),
                   start(2)
                 }
     MAX-ACCESS  read-only
     STATUS      current
     DESCRIPTION
        "This is an action object. Setting this object to start
         will initiate the disassociation of associated client.
         Read on this object will always return none."
     ::= { wsAuthenticatedClientStatusEntry 9 }

 wsAuthenticatedClientAge OBJECT-TYPE
     SYNTAX       TimeTicks
     MAX-ACCESS   read-only
     STATUS       current
     DESCRIPTION
        "Indicates time since the controller has received new data for
         this client."
     ::= { wsAuthenticatedClientStatusEntry 10 }

 wsAuthenticatedClientAssociatingSwitch OBJECT-TYPE
     SYNTAX       INTEGER {
                    local-switch(1),
                    peer-switch(2)
                  }
     MAX-ACCESS   read-only
     STATUS       current
     DESCRIPTION
        "This object indicates whether the client is associated
         to an AP managed by  this controller or peer-controller."
     ::= {wsAuthenticatedClientStatusEntry 11}

 wsAuthenticatedClientSwitchMacAddress  OBJECT-TYPE
     SYNTAX       MacAddress
     MAX-ACCESS   read-only
     STATUS       current
     DESCRIPTION
        "MAC address of the WS associating the client."
     ::= {wsAuthenticatedClientStatusEntry 12}

 wsAuthenticatedClientSwitchIpAddress OBJECT-TYPE
     SYNTAX       IpAddress
     MAX-ACCESS   read-only
     STATUS       current
     DESCRIPTION
        "IP address of the WS associating the client."
     ::= {wsAuthenticatedClientStatusEntry 13}

 wsAuthenticatedClientDot11nCapable OBJECT-TYPE
     SYNTAX       INTEGER {
                    yes(1),
                    no(2)
                  }
     MAX-ACCESS   read-only
     STATUS       current
     DESCRIPTION
        "Flag indicating whether this client is capable of 802.11n operation."
     ::= {wsAuthenticatedClientStatusEntry 14}

 wsAuthenticatedClientStbcCapable OBJECT-TYPE
     SYNTAX       INTEGER {
                    yes(1),
                    no(2)
                  }
     MAX-ACCESS   not-accessible
     STATUS       current
     DESCRIPTION
        "Flag indicating whether this client is capable of Space Time Block Code (STBC) operation."
     ::= {wsAuthenticatedClientStatusEntry 15}

 wsAuthenticatedClientDistTunnelStatus         OBJECT-TYPE
     SYNTAX     INTEGER{
                 enable(1),
                 disable(2)
                       }
     MAX-ACCESS        read-only
     STATUS            current
     DESCRIPTION
         "Indicates whether L2 Distributed Tunneling is Enabled or Disabled"
     ::= {wsAuthenticatedClientStatusEntry   16 }


 wsAuthenticatedClientDistTunnelRoamStatus     OBJECT-TYPE
    SYNTAX     INTEGER{
                 associated(0),
                 home(1)
                      }
    MAX-ACCESS   read-only
    STATUS       current
    DESCRIPTION
         "Indicates whether the client is using the distrubuted tunnel or not.
          Also indicates if it is a roamed client or not."
    ::= {wsAuthenticatedClientStatusEntry  17 }


 wsAuthenticatedClientDistTunnelHomeAPMac       OBJECT-TYPE
   SYNTAX          MacAddress
   MAX-ACCESS      read-only
   STATUS          current
   DESCRIPTION
        "Indicates MAC Address of the client's Home AP. Here the client should be
         associated with the network on which the L2 Distributed Tunneling is enabled."
   ::= {wsAuthenticatedClientStatusEntry  18 }


 wsAuthenticatedClientDistTunnelAssocAPMac     OBJECT-TYPE
   SYNTAX          MacAddress
   MAX-ACCESS      read-only
   STATUS          current
   DESCRIPTION
        "MAC Address of the client's Association AP to which the client has roamed to."
  ::= {wsAuthenticatedClientStatusEntry   19 }

 wsAuthenticatedClientAPMacAddress     OBJECT-TYPE
   SYNTAX          MacAddress
   MAX-ACCESS      read-only
   STATUS          current
   DESCRIPTION
        "MAC Address of the AP to which client is Authenticated."
  ::= {wsAuthenticatedClientStatusEntry   20 }

 wsAuthenticatedClientBSSID     OBJECT-TYPE
   SYNTAX          MacAddress
   MAX-ACCESS      read-only
   STATUS          current
   DESCRIPTION
        "BSSID of the VAP to which client is associated."
  ::= {wsAuthenticatedClientStatusEntry   21 }

 wsAuthenticatedClientRadioInterface  OBJECT-TYPE
     SYNTAX       Integer32(1..2)
     MAX-ACCESS   read-only
     STATUS       current
     DESCRIPTION
         "Indicates the radio interface on which client is associated."
     ::= {wsAuthenticatedClientStatusEntry  22 }

 wsAuthenticatedClientChannel  OBJECT-TYPE
     SYNTAX       Integer32(1..165)
     MAX-ACCESS   read-only
     STATUS       current
     DESCRIPTION
       "Indicates channel for associated client entry."
     ::= {wsAuthenticatedClientStatusEntry  23 }

 wsAuthenticatedClientNwTime OBJECT-TYPE
      SYNTAX       TimeTicks
      MAX-ACCESS   read-only
      STATUS       current
      DESCRIPTION
          "Indicates time since this client first authenticated with
           the network."
      ::= { wsAuthenticatedClientStatusEntry 24 }

 wsAuthenticatedClientIpAddress OBJECT-TYPE
     SYNTAX       IpAddress
     MAX-ACCESS   read-only
     STATUS       current
     DESCRIPTION
        "Indicates network IPv4 address of the client station detetecd through ARP snooping, 0.0.0.0 indicates unknown."
     ::= {wsAuthenticatedClientStatusEntry  25 }

 wsAuthenticatedClientNetBiosName OBJECT-TYPE
     SYNTAX       DisplayString(SIZE(0..15))
     MAX-ACCESS   read-only
     STATUS       current
     DESCRIPTION
        "NetBios Name of the client."
     ::= { wsAuthenticatedClientStatusEntry 26 }

 wsAuthenticatedClientRRMSupported       OBJECT-TYPE
     SYNTAX     INTEGER{
                 enabled(1),
                 supported(2),
                 unsupported(3)
                       }
     MAX-ACCESS        not-accessible
     STATUS            current
     DESCRIPTION
         "Indicates if the Radio Resource Management (RRM) portion of the
          IEEE 802.11k standard is supported by client and RRM is enabled is on
          the AP Profile.
          Value 2 indicates the client supports RRM portion and
          RRM Mode is not enabled on AP Profile.
          Value 3 indicates client doesnot support RRM "
     ::= {wsAuthenticatedClientStatusEntry   27 }

 wsAuthenticatedClientRRMLocationReportSupported       OBJECT-TYPE
     SYNTAX     INTEGER{
                 supported(1),
                 unsupported(2)
                       }
     MAX-ACCESS        not-accessible
     STATUS            current
     DESCRIPTION
         "Indicates if the client can support RRM location report requests."
     ::= {wsAuthenticatedClientStatusEntry   28 }

 wsAuthenticatedClientRRMBeaconTableMeasurementSupported       OBJECT-TYPE
     SYNTAX     INTEGER{
                 supported(1),
                 unsupported(2)
                       }
     MAX-ACCESS        not-accessible
     STATUS            current
     DESCRIPTION
         "Indicates if the client can detect APs via RRM beacon table reports."
     ::= {wsAuthenticatedClientStatusEntry   29 }

 wsAuthenticatedClientRRMBeaconActiveMeasurementSupported       OBJECT-TYPE
     SYNTAX     INTEGER{
                 supported(1),
                 unsupported(2)
                       }
     MAX-ACCESS        not-accessible
     STATUS            current
     DESCRIPTION
         "Indicates if the client supports active scan capability."
     ::= {wsAuthenticatedClientStatusEntry   30 }

 wsAuthenticatedClientRRMBeaconPassiveMeasurementSupported       OBJECT-TYPE
     SYNTAX     INTEGER{
                 supported(1),
                 unsupported(2)
                       }
     MAX-ACCESS        not-accessible
     STATUS            current
     DESCRIPTION
         "Indicates if the client supports passive scan capability."
     ::= {wsAuthenticatedClientStatusEntry   31 }

 wsAuthenticatedClientRRMChannelLoadMeasurementSupported       OBJECT-TYPE
     SYNTAX     INTEGER{
                 supported(1),
                 unsupported(2)
                       }
     MAX-ACCESS        not-accessible
     STATUS            current
     DESCRIPTION
         "Indicates if the client supports RRM channel load measurement."
     ::= {wsAuthenticatedClientStatusEntry   32 }

 wsAuthenticatedClientDot11acCapable OBJECT-TYPE
     SYNTAX       INTEGER {
                    yes(1),
                    no(2)
                  }
     MAX-ACCESS   read-only
     STATUS       current
     DESCRIPTION
        "Flag indicating whether this client is capable of 802.11ac operation."
     ::= {wsAuthenticatedClientStatusEntry 33}

--
-- wsAuthenticatedClientStatisticsTable
--
 wsAuthenticatedClientStatisticsTable OBJECT-TYPE
     SYNTAX       SEQUENCE OF  WsAuthenticatedClientStatisticsEntry
     MAX-ACCESS   not-accessible
     STATUS       current
     DESCRIPTION
         "This table contains statistics available for each client
          associated to a WS managed AP."
     ::= { authenticatedClient 2 }

    wsAuthenticatedClientStatisticsEntry OBJECT-TYPE
     SYNTAX       WsAuthenticatedClientStatisticsEntry
     MAX-ACCESS   not-accessible
     STATUS       current
     DESCRIPTION
          "Each entry in this table contain statistics available for each
           client associated a WS managed AP."
     AUGMENTS { wsAuthenticatedClientStatusEntry }
     ::= { wsAuthenticatedClientStatisticsTable 1 }

 WsAuthenticatedClientStatisticsEntry ::=
     SEQUENCE {
      wsAuthenticatedClientPktsRecvd                 Counter64,
      wsAuthenticatedClientBytesRecvd                Counter64,
      wsAuthenticatedClientPktsTransmitted           Counter64,
      wsAuthenticatedClientBytesTransmitted          Counter64,
      wsAuthenticatedClientDuplicatePktsRecvd        Counter32,
      wsAuthenticatedClientFragmentedPktsRecvd       Counter32,
      wsAuthenticatedClientFragmentedPktsTransmitted Counter32,
      wsAuthenticatedClientTransmitRetryCount        Counter32,
      wsAuthenticatedClientTransmitRetryFailedCount  Counter32,
      wsAuthenticatedClientPktsRecvDropped           Counter64,
      wsAuthenticatedClientBytesRecvDropped          Counter64,
      wsAuthenticatedClientPktsTransmitDropped       Counter64,
      wsAuthenticatedClientBytesTransmitDropped      Counter64,
      wsAuthenticatedClientTsViolatePktsRecvd        Counter32,
      wsAuthenticatedClientTsViolatePktsTransmitted  Counter32
 }

    wsAuthenticatedClientPktsRecvd    OBJECT-TYPE
         SYNTAX      Counter64
         MAX-ACCESS  read-only
         STATUS      current
         DESCRIPTION
             "Total packets received by a managed AP from
              the client station."
         ::= { wsAuthenticatedClientStatisticsEntry 1 }

    wsAuthenticatedClientBytesRecvd    OBJECT-TYPE
         SYNTAX      Counter64
         MAX-ACCESS  read-only
         STATUS      current
         DESCRIPTION
             "Total bytes received by a managed AP from the
              client station."
         ::= { wsAuthenticatedClientStatisticsEntry 2 }

    wsAuthenticatedClientPktsTransmitted    OBJECT-TYPE
         SYNTAX      Counter64
         MAX-ACCESS  read-only
         STATUS      current
         DESCRIPTION
             "Total packets transmitted by a managed AP to
              the client station."
         ::= { wsAuthenticatedClientStatisticsEntry 3 }

    wsAuthenticatedClientBytesTransmitted    OBJECT-TYPE
         SYNTAX      Counter64
         MAX-ACCESS  read-only
         STATUS      current
         DESCRIPTION
             "Total bytes transmitted by a managed AP to
              the client station."
         ::= { wsAuthenticatedClientStatisticsEntry 4 }

    wsAuthenticatedClientDuplicatePktsRecvd    OBJECT-TYPE
         SYNTAX      Counter32
         MAX-ACCESS  read-only
         STATUS      current
         DESCRIPTION
             "Total duplicate packets received from the
              client station."
         ::= { wsAuthenticatedClientStatisticsEntry 5 }

    wsAuthenticatedClientFragmentedPktsRecvd    OBJECT-TYPE
         SYNTAX      Counter32
         MAX-ACCESS  read-only
         STATUS      current
         DESCRIPTION
             "Total fragmented packets received from the
              client station."
         ::= { wsAuthenticatedClientStatisticsEntry 6 }

    wsAuthenticatedClientFragmentedPktsTransmitted    OBJECT-TYPE
         SYNTAX      Counter32
         MAX-ACCESS  read-only
         STATUS      current
         DESCRIPTION
             "Total fragmented packets transmitted to
              the client station."
         ::= { wsAuthenticatedClientStatisticsEntry 7 }

    wsAuthenticatedClientTransmitRetryCount    OBJECT-TYPE
         SYNTAX      Counter32
         MAX-ACCESS  read-only
         STATUS      current
         DESCRIPTION
             "Indicates number of times transmits to client station
              succeeded after one or more retries."
         ::= { wsAuthenticatedClientStatisticsEntry 8 }

    wsAuthenticatedClientTransmitRetryFailedCount    OBJECT-TYPE
         SYNTAX      Counter32
         MAX-ACCESS  read-only
         STATUS      current
         DESCRIPTION
             "Number of times transmits to client station
              failed after one or more retries."
         ::= { wsAuthenticatedClientStatisticsEntry 9 }

    wsAuthenticatedClientPktsRecvDropped    OBJECT-TYPE
         SYNTAX      Counter64
         MAX-ACCESS  not-accessible
         STATUS      current
         DESCRIPTION
             "Total packets dropped in the receive direction by a managed AP
              from the client station.  This is due to client QoS actions
              affecting the wireless up (inbound) direction from client to AP."
         ::= { wsAuthenticatedClientStatisticsEntry 10 }

    wsAuthenticatedClientBytesRecvDropped    OBJECT-TYPE
         SYNTAX      Counter64
         MAX-ACCESS  not-accessible
         STATUS      current
         DESCRIPTION
             "Total bytes dropped in the receive direction by a managed AP
              from the client station.  This is due to client QoS actions
              affecting the wireless up (inbound) direction from client to AP."
         ::= { wsAuthenticatedClientStatisticsEntry 11 }

    wsAuthenticatedClientPktsTransmitDropped    OBJECT-TYPE
         SYNTAX      Counter64
         MAX-ACCESS  not-accessible
         STATUS      current
         DESCRIPTION
             "Total packets dropped in the transmit direction by a managed AP
              to the client station.  This is due to client QoS actions
              affecting the wireless down (outbound) direction from AP to client."
         ::= { wsAuthenticatedClientStatisticsEntry 12 }

    wsAuthenticatedClientBytesTransmitDropped    OBJECT-TYPE
         SYNTAX      Counter64
         MAX-ACCESS  not-accessible
         STATUS      current
         DESCRIPTION
             "Total bytes dropped in the transmit direction by a managed AP
              to the client station.  This is due to client QoS actions
              affecting the wireless down (outbound) direction from AP to client."
         ::= { wsAuthenticatedClientStatisticsEntry 13 }

    wsAuthenticatedClientTsViolatePktsRecvd    OBJECT-TYPE
         SYNTAX      Counter32
         MAX-ACCESS  not-accessible
         STATUS      current
         DESCRIPTION
             "Number of packets received by the AP from a client station that are in excess
              of the client's alotted traffic stream (TS) uplink bandwidth, or are for an
              access category requiring admission control to which the client station
              has not been admitted."
         ::= { wsAuthenticatedClientStatisticsEntry 14 }

    wsAuthenticatedClientTsViolatePktsTransmitted    OBJECT-TYPE
         SYNTAX      Counter32
         MAX-ACCESS  not-accessible
         STATUS      current
         DESCRIPTION
             "Number of packets transmitted by the AP to a client station that are in excess
              of the client's alotted traffic stream (TS) downlink bandwidth, or are for an
              access category requiring admission control to which the client station
              has not been admitted."
         ::= { wsAuthenticatedClientStatisticsEntry 15 }

--
--   wsAuthenticatedClientNeighborManagedAPStatusTable
--
  wsAuthenticatedClientNeighborManagedAPStatusTable OBJECT-TYPE
     SYNTAX       SEQUENCE OF WsAuthenticatedClientNeighborManagedAPStatusEntry
     MAX-ACCESS   not-accessible
     STATUS       current
     DESCRIPTION
          "This table is maintained to lookup all WS managed APs
           detected, client can see in its RF area."
     ::= { authenticatedClient 3 }

    wsAuthenticatedClientNeighborManagedAPStatusEntry OBJECT-TYPE
     SYNTAX       WsAuthenticatedClientNeighborManagedAPStatusEntry
     MAX-ACCESS   not-accessible
     STATUS       current
     DESCRIPTION
          "Each entry in this table contain WS managed APs that can
           be seen by client in its RF area."
     INDEX    { wsAuthenticatedClientStationMacAddress,
                wsAuthenticatedClientNeighborWSManagedAPMacAddress,
                wsAuthenticatedClientNeighborWSManagedAPRadioInterface }
     ::= { wsAuthenticatedClientNeighborManagedAPStatusTable 1 }

 WsAuthenticatedClientNeighborManagedAPStatusEntry ::=
     SEQUENCE {
      wsAuthenticatedClientStationMacAddress    MacAddress,
      wsAuthenticatedClientNeighborWSManagedAPMacAddress     MacAddress,
      wsAuthenticatedClientNeighborWSManagedAPRadioInterface Integer32,
      wsAuthenticatedClientStationDiscoveryReason            BITS
 }

 wsAuthenticatedClientStationMacAddress  OBJECT-TYPE
     SYNTAX       MacAddress
     MAX-ACCESS   read-only
     STATUS       current
     DESCRIPTION
       "The Ethernet address of a client station."
     ::= {wsAuthenticatedClientNeighborManagedAPStatusEntry  1 }

 wsAuthenticatedClientNeighborWSManagedAPMacAddress  OBJECT-TYPE
     SYNTAX       MacAddress
     MAX-ACCESS   read-only
     STATUS       current
     DESCRIPTION
       "The Ethernet address of a WS managed AP."
     ::= {wsAuthenticatedClientNeighborManagedAPStatusEntry  2 }

 wsAuthenticatedClientNeighborWSManagedAPRadioInterface  OBJECT-TYPE
     SYNTAX       Integer32(1..2)
     MAX-ACCESS   read-only
     STATUS       current
     DESCRIPTION
       "The radio interface of Managed AP."
     ::= {wsAuthenticatedClientNeighborManagedAPStatusEntry  3 }

wsAuthenticatedClientStationDiscoveryReason  OBJECT-TYPE
    SYNTAX        BITS   {
                     none(0),
                     rfscan-discovered(1),
                     neighbor-ap-associated(2),
                     current-ap-associated(3),
                     probe-request-discovered(4),
                     ad-hoc-rogue(5),
                     associated-to-peer-ap(6)
                     }
    MAX-ACCESS   read-only
    STATUS       current
    DESCRIPTION
      "Indicates the client status with respect to the
       Managed AP it is refering. One or more flags can
       be enabled at the same time."
    ::= {wsAuthenticatedClientNeighborManagedAPStatusEntry  4 }
--
--   wsVAPAuthenticatedClientStatusTable
--
  wsVAPAuthenticatedClientStatusTable OBJECT-TYPE
     SYNTAX       SEQUENCE OF WsVAPAuthenticatedClientStatusEntry
     MAX-ACCESS   not-accessible
     STATUS       current
     DESCRIPTION
          " This table is maintained to lookup clients associated
            to a specific VAP on a WS managed AP."
     ::= { authenticatedClient 4 }

    wsVAPAuthenticatedClientStatusEntry OBJECT-TYPE
     SYNTAX       WsVAPAuthenticatedClientStatusEntry
     MAX-ACCESS   not-accessible
     STATUS       current
     DESCRIPTION
          "Each entry in this table contain clients associated
           to each VAP."
     INDEX    { wsAuthenticatedVAPMacAddress, wsVAPAuthenticatedClientMacAddress }
     ::= { wsVAPAuthenticatedClientStatusTable 1 }

 WsVAPAuthenticatedClientStatusEntry ::=
     SEQUENCE {
      wsAuthenticatedVAPMacAddress                   MacAddress,
      wsVAPAuthenticatedClientMacAddress   MacAddress
 }

 wsAuthenticatedVAPMacAddress  OBJECT-TYPE
     SYNTAX       MacAddress
     MAX-ACCESS   read-only
     STATUS       current
     DESCRIPTION
       "The Ethernet address assigned to a VAP to which the client is associated."
     ::= {wsVAPAuthenticatedClientStatusEntry  1 }

 wsVAPAuthenticatedClientMacAddress  OBJECT-TYPE
     SYNTAX       MacAddress
     MAX-ACCESS   read-only
     STATUS       current
     DESCRIPTION
       "The Ethernet address of associated client station."
     ::= {wsVAPAuthenticatedClientStatusEntry  2 }

--
--   wsSSIDAuthenticatedClientStatusTable
--
  wsSSIDAuthenticatedClientStatusTable OBJECT-TYPE
     SYNTAX       SEQUENCE OF WsSSIDAuthenticatedClientStatusEntry
     MAX-ACCESS   not-accessible
     STATUS       current
     DESCRIPTION
          " This table is maintained to lookup all clients
            associated to a particular network."
     ::= { authenticatedClient 5 }

    wsSSIDAuthenticatedClientStatusEntry OBJECT-TYPE
     SYNTAX       WsSSIDAuthenticatedClientStatusEntry
     MAX-ACCESS   not-accessible
     STATUS       current
     DESCRIPTION
          "Each entry in this table contain clients
           associated to a particular network."
     INDEX    { wsSSIDAuthenticatedClientMacAddress }
     ::= { wsSSIDAuthenticatedClientStatusTable 1 }

 WsSSIDAuthenticatedClientStatusEntry ::=
     SEQUENCE {
      wsAuthenticatedSSID                   DisplayString,
      wsSSIDAuthenticatedClientMacAddress   MacAddress
 }

 wsAuthenticatedSSID  OBJECT-TYPE
     SYNTAX       DisplayString(SIZE(1..32))
     MAX-ACCESS   read-only
     STATUS       current
     DESCRIPTION
       "Indicates the network on which the client is connected."
     ::= {wsSSIDAuthenticatedClientStatusEntry  1 }

 wsSSIDAuthenticatedClientMacAddress  OBJECT-TYPE
     SYNTAX       MacAddress
     MAX-ACCESS   read-only
     STATUS       current
     DESCRIPTION
        "The Ethernet address of the client station."
     ::= {wsSSIDAuthenticatedClientStatusEntry  2 }


--
--   wsSwitchAuthenticatedClientStatusTable
--
  wsSwitchAuthenticatedClientStatusTable OBJECT-TYPE
     SYNTAX       SEQUENCE OF WsSwitchAuthenticatedClientStatusEntry
     MAX-ACCESS   not-accessible
     STATUS       current
     DESCRIPTION
          " This table is maintained to lookup clients associated
            to the APs managed by the specific controller."
     ::= { authenticatedClient 6 }

    wsSwitchAuthenticatedClientStatusEntry OBJECT-TYPE
     SYNTAX       WsSwitchAuthenticatedClientStatusEntry
     MAX-ACCESS   not-accessible
     STATUS       current
     DESCRIPTION
          "Each entry in this table contain client associated
           to each controller."
     INDEX    { wsSwitchIPAddress, wsSwitchAuthenticatedClientMacAddress }
     ::= { wsSwitchAuthenticatedClientStatusTable 1 }

 WsSwitchAuthenticatedClientStatusEntry ::=
     SEQUENCE {
      wsAuthenticatedClientSwitchIPAddress    IpAddress,
      wsSwitchAuthenticatedClientMacAddress   MacAddress
 }

 wsAuthenticatedClientSwitchIPAddress OBJECT-TYPE
     SYNTAX       IpAddress
     MAX-ACCESS   read-only
     STATUS       current
     DESCRIPTION
        "IP address of the WS associating the client."
     ::= {wsSwitchAuthenticatedClientStatusEntry 1}

 wsSwitchAuthenticatedClientMacAddress  OBJECT-TYPE
     SYNTAX       MacAddress
     MAX-ACCESS   read-only
     STATUS       current
     DESCRIPTION
       "Ethernet address of the associated client station."
     ::= {wsSwitchAuthenticatedClientStatusEntry  2 }


--
-- wsAuthenticatedClientQosStatusTable
--
 wsAuthenticatedClientQosStatusTable OBJECT-TYPE
     SYNTAX       SEQUENCE OF WsAuthenticatedClientQosStatusEntry
     MAX-ACCESS   not-accessible
     STATUS       current
     DESCRIPTION
        "This table contains client QoS status parameters of clients that are
         currently associated with managed APs.  These objects represent the
         actual operational status values in effect for the clients."
      ::= { authenticatedClient 7 }

 wsAuthenticatedClientQosStatusEntry OBJECT-TYPE
     SYNTAX       WsAuthenticatedClientQosStatusEntry
     MAX-ACCESS   not-accessible
     STATUS       current
     DESCRIPTION
         "Each entry in this table contains client QoS status parameters
          for a client associated with the WS managed AP."
     AUGMENTS { wsAuthenticatedClientStatusEntry }
     ::= { wsAuthenticatedClientQosStatusTable 1 }

 WsAuthenticatedClientQosStatusEntry ::=
     SEQUENCE {
         wsAuthenticatedClientQosBandwidthLimitDown         Unsigned32,
         wsAuthenticatedClientQosBandwidthLimitUp           Unsigned32,
         wsAuthenticatedClientQosAccessControlDownType      INTEGER,
         wsAuthenticatedClientQosAccessControlDownName      DisplayString,
         wsAuthenticatedClientQosAccessControlUpType        INTEGER,
         wsAuthenticatedClientQosAccessControlUpName        DisplayString,
         wsAuthenticatedClientQosDiffservPolicyDownType     INTEGER,
         wsAuthenticatedClientQosDiffservPolicyDownName     DisplayString,
         wsAuthenticatedClientQosDiffservPolicyUpType       INTEGER,
         wsAuthenticatedClientQosDiffservPolicyUpName       DisplayString,
         wsAuthenticatedClientQosOperStatus                 INTEGER
     }

 wsAuthenticatedClientQosBandwidthLimitDown OBJECT-TYPE
      SYNTAX      Unsigned32
      MAX-ACCESS  not-accessible
      STATUS      current
      DESCRIPTION
               "Maximum bandwidth rate allowed for the wireless down (outbound)
                direction from AP to client, thus controlling the maximum
                receive rate from the AP for this wireless client.  This
                parameter is specified in bits-per-second (bps).

                The displayed value represents the actual bandwidth rate in use
                for the client, which may differ from the configured value since
                the AP rounds down to the nearest 64000 bps.  A value of 0 indicates
                bandwidth limiting is disabled in this direction for the client."
      ::= { wsAuthenticatedClientQosStatusEntry 1 }

 wsAuthenticatedClientQosBandwidthLimitUp OBJECT-TYPE
      SYNTAX      Unsigned32
      MAX-ACCESS  not-accessible
      STATUS      current
      DESCRIPTION
               "Maximum bandwidth rate allowed for the wireless up (inbound)
                direction from client to AP, thus controlling the maximum
                send rate from this wireless client to the AP.  This
                parameter is specified in bits-per-second (bps).

                The displayed value represents the actual bandwidth rate in use
                for the client, which may differ from the configured value since
                the AP rounds down to the nearest 64000 bps.  A value of 0 indicates
                bandwidth limiting is disabled in this direction for the client."
      ::= { wsAuthenticatedClientQosStatusEntry 2 }

 wsAuthenticatedClientQosAccessControlDownType OBJECT-TYPE
     SYNTAX       INTEGER {
                    none(1),
                    ip(2),
                    mac(3),
                    ipv6(4)
                  }
     MAX-ACCESS   not-accessible
     STATUS       current
     DESCRIPTION
        "Access list type used for the wireless down (outbound) direction from
         the AP to this client.  The wsAuthenticatedClientQosAccessControlDownName
         object identifies the access list."
     ::= { wsAuthenticatedClientQosStatusEntry 3 }

 wsAuthenticatedClientQosAccessControlDownName OBJECT-TYPE
     SYNTAX       DisplayString(SIZE(1..31))
     MAX-ACCESS   not-accessible
     STATUS       current
     DESCRIPTION
       "Name of the access list in use in accordance with the
        wsAuthenticatedClientQosAccessControlDownType as follows:

        none(1) - This object is not displayed.

        ip(2)   - This specifies an IP access list number in the range
                  1-199, or an IP access list name as defined by the
                  aclName object in the aclTable in the FASTPATH-QOS-ACL-MIB.
        mac(3)  - This is an alphanumeric string from 1-31 characters, beginning
                  with a letter.  This must be a valid MAC access list name,
                  as defined by the aclMacName object in the FASTPATH-QOS-ACL-MIB.
        ipv6(4) - This is an alphanumeric string from 1-31 characters, beginning
                  with a letter.  This must be a valid IPV6 access list name,
                  as defined by the aclIpv6Name object in the FASTPATH-QOS-ACL-MIB.

        Note that numbered IP access lists are displayed here using a character
        string notation instead of an integer."
        ::= { wsAuthenticatedClientQosStatusEntry 4 }

 wsAuthenticatedClientQosAccessControlUpType OBJECT-TYPE
     SYNTAX       INTEGER {
                    none(1),
                    ip(2),
                    mac(3),
                    ipv6(4)
                  }
     MAX-ACCESS   not-accessible
     STATUS       current
     DESCRIPTION
        "Access list type used for the wireless up (inbound) direction from
         this client to the AP.  The wsAuthenticatedClientQosAccessControlUpName
         object identifies the access list."
     ::= { wsAuthenticatedClientQosStatusEntry 5 }

 wsAuthenticatedClientQosAccessControlUpName OBJECT-TYPE
     SYNTAX       DisplayString(SIZE(1..31))
     MAX-ACCESS   not-accessible
     STATUS       current
     DESCRIPTION
       "Name of the access list in use in accordance with the
        wsAuthenticatedClientQosAccessControlUpType as follows:

        none(1) - This object is not displayed.

        ip(2)   - This specifies an IP access list number in the range
                  1-199, or an IP access list name as defined by the
                  aclName object in the aclTable in the FASTPATH-QOS-ACL-MIB.

        Note that numbered IP access lists are displayed here using a character
        string notation instead of an integer."
        ::= { wsAuthenticatedClientQosStatusEntry 6 }

 wsAuthenticatedClientQosDiffservPolicyDownType OBJECT-TYPE
     SYNTAX       INTEGER {
                    none(1),
                    in(2)
                  }
     MAX-ACCESS   not-accessible
     STATUS       current
     DESCRIPTION
        "DiffServ policy type used for the wireless down (outbound) direction from
         the AP to this client.  The wsAuthenticatedClientQosDiffservPolicyDownName
         object identifies the DiffServ policy."
     ::= { wsAuthenticatedClientQosStatusEntry 7 }

 wsAuthenticatedClientQosDiffservPolicyDownName OBJECT-TYPE
     SYNTAX       DisplayString(SIZE(1..31))
     MAX-ACCESS   not-accessible
     STATUS       current
     DESCRIPTION
       "Name of the DiffServ policy in use in accordance with the
        wsAuthenticatedClientQosDiffservPolicyDownType as follows:

        none(1) - This object is not displayed.

        in(2)   - This specifies a DiffServ policy name, as defined by the
                  agentDiffServPolicyName object in the FASTPATH-QOS-DIFFSERV-PRIVATE-MIB.

        Note that only DiffServ policy defintions of type 'in' are supported for
        wireless client QoS operation."
        ::= { wsAuthenticatedClientQosStatusEntry 8 }

 wsAuthenticatedClientQosDiffservPolicyUpType OBJECT-TYPE
     SYNTAX       INTEGER {
                    none(1),
                    in(2)
                  }
     MAX-ACCESS   not-accessible
     STATUS       current
     DESCRIPTION
        "DiffServ policy type used for the wireless up (inbound) direction from
         this client to the AP.  The wsAuthenticatedClientQosDiffservPolicyUpName
         object identifies the DiffServ policy."
     ::= { wsAuthenticatedClientQosStatusEntry 9 }

 wsAuthenticatedClientQosDiffservPolicyUpName OBJECT-TYPE
     SYNTAX       DisplayString(SIZE(1..31))
     MAX-ACCESS   not-accessible
     STATUS       current
     DESCRIPTION
       "Name of the DiffServ policy in use in accordance with the
        wsAuthenticatedClientQosDiffservPolicyUpType as follows:

        none(1) - This object is not displayed.

        in(2)   - This specifies a DiffServ policy name, as defined by the
                  agentDiffServPolicyName object in the FASTPATH-QOS-DIFFSERV-PRIVATE-MIB.

        Note that only DiffServ policy defintions of type 'in' are supported for
        wireless client QoS operation."
        ::= { wsAuthenticatedClientQosStatusEntry 10 }


 wsAuthenticatedClientQosOperStatus OBJECT-TYPE
     SYNTAX        INTEGER {
                      enable(1),
                      disable(2)
                   }
     MAX-ACCESS   not-accessible
     STATUS       current
     DESCRIPTION
        "Designates the AP quality-of-service operational status for
        this wireless client.  This represents the combined states of
        the wsApClientQosMode object and the wsNetworkClientQosMode
        object for the wireless network to which this client is associated."
     ::= { wsAuthenticatedClientQosStatusEntry 11 }

--
-- wsAuthenticatedClientSessionStatisticsTable
--
 wsAuthenticatedClientSessionStatisticsTable OBJECT-TYPE
     SYNTAX       SEQUENCE OF  WsAuthenticatedClientSessionStatisticsEntry
     MAX-ACCESS   not-accessible
     STATUS       current
     DESCRIPTION
         "This table contains statistics available for each client
          associated to a WS managed AP, but accumulated for the duration
          of the entire WLAN session, inclusive of client roaming."
     ::= { authenticatedClient 8 }

    wsAuthenticatedClientSessionStatisticsEntry OBJECT-TYPE
     SYNTAX       WsAuthenticatedClientSessionStatisticsEntry
     MAX-ACCESS   not-accessible
     STATUS       current
     DESCRIPTION
          "Each entry in this table contain statistics available for each
           client associated a WS managed AP, but accumulated for the duration
           of the entire WLAN session, inclusive of client roaming."
     AUGMENTS { wsAuthenticatedClientStatusEntry }
     ::= { wsAuthenticatedClientSessionStatisticsTable 1 }

 WsAuthenticatedClientSessionStatisticsEntry ::=
     SEQUENCE {
      wsAuthenticatedClientSessionPktsRecvd                 Counter64,
      wsAuthenticatedClientSessionBytesRecvd                Counter64,
      wsAuthenticatedClientSessionPktsTransmitted           Counter64,
      wsAuthenticatedClientSessionBytesTransmitted          Counter64,
      wsAuthenticatedClientSessionDuplicatePktsRecvd        Counter32,
      wsAuthenticatedClientSessionFragmentedPktsRecvd       Counter32,
      wsAuthenticatedClientSessionFragmentedPktsTransmitted Counter32,
      wsAuthenticatedClientSessionTransmitRetryCount        Counter32,
      wsAuthenticatedClientSessionTransmitRetryFailedCount  Counter32,
      wsAuthenticatedClientSessionPktsRecvDropped           Counter64,
      wsAuthenticatedClientSessionBytesRecvDropped          Counter64,
      wsAuthenticatedClientSessionPktsTransmitDropped       Counter64,
      wsAuthenticatedClientSessionBytesTransmitDropped      Counter64,
      wsAuthenticatedClientSessionTSViolatePktsRecvd        Counter32,
      wsAuthenticatedClientSessionTSViolatePktsTransmitted  Counter32
 }

    wsAuthenticatedClientSessionPktsRecvd    OBJECT-TYPE
         SYNTAX      Counter64
         MAX-ACCESS  read-only
         STATUS      current
         DESCRIPTION
             "Total packets received by managed APs from the client station
              throughout the duration of the current WLAN session."
         ::= { wsAuthenticatedClientSessionStatisticsEntry 1 }

    wsAuthenticatedClientSessionBytesRecvd    OBJECT-TYPE
         SYNTAX      Counter64
         MAX-ACCESS  read-only
         STATUS      current
         DESCRIPTION
             "Total bytes received by managed APs from the client station
              throughout the duration of the current WLAN session."
         ::= { wsAuthenticatedClientSessionStatisticsEntry 2 }

    wsAuthenticatedClientSessionPktsTransmitted    OBJECT-TYPE
         SYNTAX      Counter64
         MAX-ACCESS  read-only
         STATUS      current
         DESCRIPTION
             "Total packets transmitted by managed APs to the client station
              throughout the duration of the current WLAN session."
         ::= { wsAuthenticatedClientSessionStatisticsEntry 3 }

    wsAuthenticatedClientSessionBytesTransmitted    OBJECT-TYPE
         SYNTAX      Counter64
         MAX-ACCESS  read-only
         STATUS      current
         DESCRIPTION
             "Total bytes transmitted by managed APs to the client station
              throughout the duration of the current WLAN session."
         ::= { wsAuthenticatedClientSessionStatisticsEntry 4 }

    wsAuthenticatedClientSessionDuplicatePktsRecvd    OBJECT-TYPE
         SYNTAX      Counter32
         MAX-ACCESS  read-only
         STATUS      current
         DESCRIPTION
             "Total duplicate packets received from the client station
              throughout the duration of the current WLAN session."
         ::= { wsAuthenticatedClientSessionStatisticsEntry 5 }

    wsAuthenticatedClientSessionFragmentedPktsRecvd    OBJECT-TYPE
         SYNTAX      Counter32
         MAX-ACCESS  read-only
         STATUS      current
         DESCRIPTION
             "Total fragmented packets received from the client station.
              throughout the duration of the current WLAN session."
         ::= { wsAuthenticatedClientSessionStatisticsEntry 6 }

    wsAuthenticatedClientSessionFragmentedPktsTransmitted    OBJECT-TYPE
         SYNTAX      Counter32
         MAX-ACCESS  read-only
         STATUS      current
         DESCRIPTION
             "Total fragmented packets transmitted to the client station
              throughout the duration of the current WLAN session."
         ::= { wsAuthenticatedClientSessionStatisticsEntry 7 }

    wsAuthenticatedClientSessionTransmitRetryCount    OBJECT-TYPE
         SYNTAX      Counter32
         MAX-ACCESS  read-only
         STATUS      current
         DESCRIPTION
             "Indicates number of times transmits to client station
              succeeded after one or more retries throughout the
              duration of the current WLAN session."
         ::= { wsAuthenticatedClientSessionStatisticsEntry 8 }

    wsAuthenticatedClientSessionTransmitRetryFailedCount    OBJECT-TYPE
         SYNTAX      Counter32
         MAX-ACCESS  read-only
         STATUS      current
         DESCRIPTION
             "Number of times transmits to client station
              failed after one or more retries throughout the
              duration of the current WLAN session."
         ::= { wsAuthenticatedClientSessionStatisticsEntry 9 }

    wsAuthenticatedClientSessionPktsRecvDropped    OBJECT-TYPE
         SYNTAX      Counter64
         MAX-ACCESS  not-accessible
         STATUS      current
         DESCRIPTION
             "Total packets dropped in the receive direction by managed APs
              from the client station throughout the duration of the current
              WLAN session.  This is due to client QoS actions affecting the
              wireless up (inbound) direction from client to AP."
         ::= { wsAuthenticatedClientSessionStatisticsEntry 10 }

    wsAuthenticatedClientSessionBytesRecvDropped    OBJECT-TYPE
         SYNTAX      Counter64
         MAX-ACCESS  not-accessible
         STATUS      current
         DESCRIPTION
             "Total bytes dropped in the receive direction by managed APs
              from the client station throughout the duration of the current
              WLAN session.  This is due to client QoS actions affecting the
              wireless up (inbound) direction from client to AP."
         ::= { wsAuthenticatedClientSessionStatisticsEntry 11 }

    wsAuthenticatedClientSessionPktsTransmitDropped    OBJECT-TYPE
         SYNTAX      Counter64
         MAX-ACCESS  not-accessible
         STATUS      current
         DESCRIPTION
             "Total packets dropped in the transmit direction by managed APs
              to the client station throughout the duration of the current
              WLAN session.  This is due to client QoS actions affecting the
              wireless down (outbound) direction from AP to client."
         ::= { wsAuthenticatedClientSessionStatisticsEntry 12 }

    wsAuthenticatedClientSessionBytesTransmitDropped    OBJECT-TYPE
         SYNTAX      Counter64
         MAX-ACCESS  not-accessible
         STATUS      current
         DESCRIPTION
             "Total bytes dropped in the transmit direction by managed APs
              to the client station throughout the duration of the current
              WLAN session.  This is due to client QoS actions affecting the
              wireless down (outbound) direction from AP to client."
         ::= { wsAuthenticatedClientSessionStatisticsEntry 13 }

    wsAuthenticatedClientSessionTSViolatePktsRecvd    OBJECT-TYPE
         SYNTAX      Counter32
         MAX-ACCESS  not-accessible
         STATUS      current
         DESCRIPTION
             "Number of packets received by managed APs from a client station
              throughout the duration of the current WLAN session that are in excess
              of the client's alotted traffic stream (TS) uplink bandwidth, or are for an
              access category requiring admission control to which the client station
              has not been admitted."
         ::= { wsAuthenticatedClientSessionStatisticsEntry 14 }

    wsAuthenticatedClientSessionTSViolatePktsTransmitted    OBJECT-TYPE
         SYNTAX      Counter32
         MAX-ACCESS  not-accessible
         STATUS      current
         DESCRIPTION
             "Number of packets transmitted by managed APs to a client station
              throughout the duration of the current WLAN session that are in excess
              of the client's alotted traffic stream (TS) downlink bandwidth, or are for an
              access category requiring admission control to which the client station
              has not been admitted."
         ::= { wsAuthenticatedClientSessionStatisticsEntry 15 }

--
-- wsAuthenticatedClientQosCachedStatusTable
--
 wsAuthenticatedClientQosCachedStatusTable OBJECT-TYPE
     SYNTAX       SEQUENCE OF WsAuthenticatedClientQosCachedStatusEntry
     MAX-ACCESS   not-accessible
     STATUS       current
     DESCRIPTION
        "This table contains cached client QoS status parameters of clients that are
         currently associated with managed APs.  These objects represent values
         that were retrieved from a RADIUS server for this client.  See the
         wsAuthenticatedClientQosStatusTable for the current set of operational
         values in use for this client."
      ::= { authenticatedClient 9 }

 wsAuthenticatedClientQosCachedStatusEntry OBJECT-TYPE
     SYNTAX       WsAuthenticatedClientQosCachedStatusEntry
     MAX-ACCESS   not-accessible
     STATUS       current
     DESCRIPTION
         "Each entry in this table contains client QoS cached status parameters
          for a client associated with the WS managed AP.  Only those parameters
          successfully retrieved from a RADIUS server via 802.1X authentication
          on behalf of a wireless client are displayed."
     AUGMENTS { wsAuthenticatedClientStatusEntry }
     ::= { wsAuthenticatedClientQosCachedStatusTable 1 }

 WsAuthenticatedClientQosCachedStatusEntry ::=
     SEQUENCE {
         wsAuthenticatedClientQosCachedBandwidthLimitDown         Unsigned32,
         wsAuthenticatedClientQosCachedBandwidthLimitUp           Unsigned32,
         wsAuthenticatedClientQosCachedAccessControlDownType      INTEGER,
         wsAuthenticatedClientQosCachedAccessControlDownName      DisplayString,
         wsAuthenticatedClientQosCachedAccessControlUpType        INTEGER,
         wsAuthenticatedClientQosCachedAccessControlUpName        DisplayString,
         wsAuthenticatedClientQosCachedDiffservPolicyDownType     INTEGER,
         wsAuthenticatedClientQosCachedDiffservPolicyDownName     DisplayString,
         wsAuthenticatedClientQosCachedDiffservPolicyUpType       INTEGER,
         wsAuthenticatedClientQosCachedDiffservPolicyUpName       DisplayString
     }

 wsAuthenticatedClientQosCachedBandwidthLimitDown OBJECT-TYPE
      SYNTAX      Unsigned32
      MAX-ACCESS  not-accessible
      STATUS      current
      DESCRIPTION
          "Maximum bandwidth rate allowed for the wireless down (outbound)
           direction from AP to client, thus controlling the maximum
           receive rate from the AP for this wireless client.  This
           parameter is specified in bits-per-second (bps).

           A value of 0 indicates bandwidth limiting is disabled in this
           direction for the client."
      ::= { wsAuthenticatedClientQosCachedStatusEntry 1 }

 wsAuthenticatedClientQosCachedBandwidthLimitUp OBJECT-TYPE
      SYNTAX      Unsigned32
      MAX-ACCESS  not-accessible
      STATUS      current
      DESCRIPTION
          "Maximum bandwidth rate allowed for the wireless up (inbound)
           direction from client to AP, thus controlling the maximum
           send rate from this wireless client to the AP.  This
           parameter is specified in bits-per-second (bps).

           A value of 0 indicates bandwidth limiting is disabled in this
           direction for the client."
      ::= { wsAuthenticatedClientQosCachedStatusEntry 2 }

 wsAuthenticatedClientQosCachedAccessControlDownType OBJECT-TYPE
     SYNTAX       INTEGER {
                    none(1),
                    ip(2),
                    mac(3),
                    ipv6(4)
                  }
     MAX-ACCESS   read-only
     STATUS       current
     DESCRIPTION
        "Access list type used for the wireless down (outbound) direction from
         the AP to this client.  The wsAuthenticatedClientQosCachedAccessControlDownName
         object identifies the access list."
     ::= { wsAuthenticatedClientQosCachedStatusEntry 3 }

 wsAuthenticatedClientQosCachedAccessControlDownName OBJECT-TYPE
     SYNTAX       DisplayString(SIZE(1..31))
     MAX-ACCESS   not-accessible
     STATUS       current
     DESCRIPTION
       "Name of the access list in use in accordance with the
        wsAuthenticatedClientQosCachedAccessControlDownType as follows:

        none(1) - This object is not displayed.

        ip(2)   - This specifies an IP access list number in the range
                  1-199, or an IP access list name as defined by the
                  aclName object in the aclTable in the FASTPATH-QOS-ACL-MIB.
        mac(3)  - This is an alphanumeric string from 1-31 characters, beginning
                  with a letter.  This must be a valid MAC access list name,
                  as defined by the aclMacName object in the FASTPATH-QOS-ACL-MIB.
        ipv6(4) - This is an alphanumeric string from 1-31 characters, beginning
                  with a letter.  This must be a valid IPV6 access list name,
                  as defined by the aclIpv6Name object in the FASTPATH-QOS-ACL-MIB.

        Note that numbered IP access lists are displayed here using a character
        string notation instead of an integer."
        ::= { wsAuthenticatedClientQosCachedStatusEntry 4 }

 wsAuthenticatedClientQosCachedAccessControlUpType OBJECT-TYPE
     SYNTAX       INTEGER {
                    none(1),
                    ip(2),
                    mac(3),
                    ipv6(4)
                  }
     MAX-ACCESS   not-accessible
     STATUS       current
     DESCRIPTION
        "Access list type used for the wireless up (inbound) direction from
         this client to the AP.  The wsAuthenticatedClientQosCachedAccessControlUpName
         object identifies the access list."
     ::= { wsAuthenticatedClientQosCachedStatusEntry 5 }

 wsAuthenticatedClientQosCachedAccessControlUpName OBJECT-TYPE
     SYNTAX       DisplayString(SIZE(1..31))
     MAX-ACCESS   not-accessible
     STATUS       current
     DESCRIPTION
       "Name of the access list in use in accordance with the
        wsAuthenticatedClientQosCachedAccessControlUpType as follows:

        none(1) - This object is not displayed.

        ip(2)   - This specifies an IP access list number in the range
                  1-199, or an IP access list name as defined by the
                  aclName object in the aclTable in the FASTPATH-QOS-ACL-MIB.
        mac(3)  - This is an alphanumeric string from 1-31 characters, beginning
                  with a letter.  This must be a valid MAC access list name,
                  as defined by the aclMacName object in the FASTPATH-QOS-ACL-MIB.
        ipv6(4) - This is an alphanumeric string from 1-31 characters, beginning
                  with a letter.  This must be a valid IPV6 access list name,
                  as defined by the aclIpv6Name object in the FASTPATH-QOS-ACL-MIB.

        Note that numbered IP access lists are displayed here using a character
        string notation instead of an integer."
        ::= { wsAuthenticatedClientQosCachedStatusEntry 6 }

 wsAuthenticatedClientQosCachedDiffservPolicyDownType OBJECT-TYPE
     SYNTAX       INTEGER {
                    none(1),
                    in(2)
                  }
     MAX-ACCESS   not-accessible
     STATUS       current
     DESCRIPTION
        "DiffServ policy type used for the wireless down (outbound) direction from
         the AP to this client.  The wsAuthenticatedClientQosCachedDiffservPolicyDownName
         object identifies the DiffServ policy."
     ::= { wsAuthenticatedClientQosCachedStatusEntry 7 }

 wsAuthenticatedClientQosCachedDiffservPolicyDownName OBJECT-TYPE
     SYNTAX       DisplayString(SIZE(1..31))
     MAX-ACCESS   not-accessible
     STATUS       current
     DESCRIPTION
       "Name of the DiffServ policy in use in accordance with the
        wsAuthenticatedClientQosCachedDiffservPolicyDownType as follows:

        none(1) - This object is not displayed.

        in(2)   - This specifies a DiffServ policy name, as defined by the
                  agentDiffServPolicyName object in the FASTPATH-QOS-DIFFSERV-PRIVATE-MIB.

        Note that only DiffServ policy defintions of type 'in' are supported for
        wireless client QoS operation."
        ::= { wsAuthenticatedClientQosCachedStatusEntry 8 }

 wsAuthenticatedClientQosCachedDiffservPolicyUpType OBJECT-TYPE
     SYNTAX       INTEGER {
                    none(1),
                    in(2)
                  }
     MAX-ACCESS   not-accessible
     STATUS       current
     DESCRIPTION
        "DiffServ policy type used for the wireless up (inbound) direction from
         this client to the AP.  The wsAuthenticatedClientQosCachedDiffservPolicyUpName
         object identifies the DiffServ policy."
     ::= { wsAuthenticatedClientQosCachedStatusEntry 9 }

 wsAuthenticatedClientQosCachedDiffservPolicyUpName OBJECT-TYPE
     SYNTAX       DisplayString(SIZE(1..31))
     MAX-ACCESS   not-accessible
     STATUS       current
     DESCRIPTION
       "Name of the DiffServ policy in use in accordance with the
        wsAuthenticatedClientQosCachedDiffservPolicyUpType as follows:

        none(1) - This object is not displayed.

        in(2)   - This specifies a DiffServ policy name, as defined by the
                  agentDiffServPolicyName object in the FASTPATH-QOS-DIFFSERV-PRIVATE-MIB.

        Note that only DiffServ policy defintions of type 'in' are supported for
        wireless client QoS operation."
        ::= { wsAuthenticatedClientQosCachedStatusEntry 10 }


END

--
-- at-uwc-wlan-switch.mib
--
