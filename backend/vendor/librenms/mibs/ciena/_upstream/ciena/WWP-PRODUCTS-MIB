WWP-PRODUCTS-MIB DEFINITIONS ::= BEGIN

	IMPORTS
		enterprises, MODULE-IDENTITY, OBJECT-IDENTITY
			FROM SNMPv2-SMI
		wwpProducts, wwpModules
			FROM WWP-SMI;

--
-- Node definitions
--
	-- 1.3.6.1.4.1.6141.1.1
	wwpLe21 OBJECT IDENTIFIER ::= { wwpProducts 1 }

	-- 1.3.6.1.4.1.6141.1.2
	wwpLe22 OBJECT IDENTIFIER ::= { wwpProducts 2 }

	-- 1.3.6.1.4.1.6141.1.3
	wwpLe31 OBJECT IDENTIFIER ::= { wwpProducts 3 }

	-- 1.3.6.1.4.1.6141.1.4
	wwpLe32 OBJECT IDENTIFIER ::= { wwpProducts 4 }

	-- 1.3.6.1.4.1.6141.1.5
	wwpLe41 OBJECT IDENTIFIER ::= { wwpProducts 5 }

	-- 1.3.6.1.4.1.6141.1.6
	wwpLe42 OBJECT IDENTIFIER ::= { wwpProducts 6 }

	-- 1.3.6.1.4.1.6141.1.7
	wwpLe200 OBJECT IDENTIFIER ::= { wwpProducts 7 }

	-- 1.3.6.1.4.1.6141.1.8
	wwpLe210 OBJECT IDENTIFIER ::= { wwpProducts 8 }

	-- 1.3.6.1.4.1.6141.1.9
	wwpLe220 OBJECT IDENTIFIER ::= { wwpProducts 9 }

	-- 1.3.6.1.4.1.6141.1.10
	wwpLe410 OBJECT IDENTIFIER ::= { wwpProducts 10 }

	-- 1.3.6.1.4.1.6141.1.11
	wwpLe3700 OBJECT IDENTIFIER ::= { wwpProducts 11 }

	-- 1.3.6.1.4.1.6141.1.12
	wwpLe4400 OBJECT IDENTIFIER ::= { wwpProducts 12 }

	-- 1.3.6.1.4.1.6141.1.13
	wwpLe211 OBJECT IDENTIFIER ::= { wwpProducts 13 }

	-- 1.3.6.1.4.1.6141.1.14
	wwpLe211H OBJECT IDENTIFIER ::= { wwpProducts 14 }

	-- 1.3.6.1.4.1.6141.1.15
	wwpLe216 OBJECT IDENTIFIER ::= { wwpProducts 15 }

	-- 1.3.6.1.4.1.6141.1.16
	wwpLe216H OBJECT IDENTIFIER ::= { wwpProducts 16 }

	-- 1.3.6.1.4.1.6141.1.17
	wwpLe218 OBJECT IDENTIFIER ::= { wwpProducts 17 }

	-- 1.3.6.1.4.1.6141.1.18
	wwpLe218H OBJECT IDENTIFIER ::= { wwpProducts 18 }

	-- 1.3.6.1.4.1.6141.1.19
	wwpLe410H OBJECT IDENTIFIER ::= { wwpProducts 19 }

	-- 1.3.6.1.4.1.6141.1.20
	wwpLe22H OBJECT IDENTIFIER ::= { wwpProducts 20 }

	-- 1.3.6.1.4.1.6141.1.21
	wwpLe32H OBJECT IDENTIFIER ::= { wwpProducts 21 }

	-- 1.3.6.1.4.1.6141.1.22
	wwpLe36 OBJECT IDENTIFIER ::= { wwpProducts 22 }

	-- 1.3.6.1.4.1.6141.1.23
	wwpLe36H OBJECT IDENTIFIER ::= { wwpProducts 23 }

	-- 1.3.6.1.4.1.6141.1.24
	wwpLe217 OBJECT IDENTIFIER ::= { wwpProducts 24 }

	-- 1.3.6.1.4.1.6141.1.25
	wwpLe217H OBJECT IDENTIFIER ::= { wwpProducts 25 }

	-- 1.3.6.1.4.1.6141.1.26
	wwpLe217DC OBJECT IDENTIFIER ::= { wwpProducts 26 }

	-- 1.3.6.1.4.1.6141.1.27
	wwpLe410DC OBJECT IDENTIFIER ::= { wwpProducts 27 }

	-- 1.3.6.1.4.1.6141.1.28
	wwpLe317 OBJECT IDENTIFIER ::= { wwpProducts 28 }

	-- 1.3.6.1.4.1.6141.1.29
	wwpLe317H OBJECT IDENTIFIER ::= { wwpProducts 29 }

	-- 1.3.6.1.4.1.6141.1.30
	wwpLe317DC OBJECT IDENTIFIER ::= { wwpProducts 30 }

	-- 1.3.6.1.4.1.6141.1.31
	wwpLe38 OBJECT IDENTIFIER ::= { wwpProducts 31 }

	-- 1.3.6.1.4.1.6141.1.32
	wwpLe46 OBJECT IDENTIFIER ::= { wwpProducts 32 }

	-- 1.3.6.1.4.1.6141.1.33
	wwpLe46Voip OBJECT IDENTIFIER ::= { wwpProducts 33 }

	-- 1.3.6.1.4.1.6141.1.34
	wwpLe42H OBJECT IDENTIFIER ::= { wwpProducts 34 }

	-- 1.3.6.1.4.1.6141.1.35
	wwpLe42HVoip OBJECT IDENTIFIER ::= { wwpProducts 35 }

	-- 1.3.6.1.4.1.6141.1.36
	wwpLe407 OBJECT IDENTIFIER ::= { wwpProducts 36 }

	-- 1.3.6.1.4.1.6141.1.37
	wwpLe427 OBJECT IDENTIFIER ::= { wwpProducts 37 }

	-- 1.3.6.1.4.1.6141.1.38
	wwpLe307 OBJECT IDENTIFIER ::= { wwpProducts 38 }

	-- 1.3.6.1.4.1.6141.1.39
	wwpLe327 OBJECT IDENTIFIER ::= { wwpProducts 39 }

	-- 1.3.6.1.4.1.6141.1.40
	wwpLe337 OBJECT IDENTIFIER ::= { wwpProducts 40 }

	-- 1.3.6.1.4.1.6141.1.41
	wwpLe22P0100 OBJECT IDENTIFIER ::= { wwpProducts 41 }

	-- 1.3.6.1.4.1.6141.1.42
	wwpLe46H OBJECT IDENTIFIER ::= { wwpProducts 42 }

	-- 1.3.6.1.4.1.6141.1.43
	wwpLe46HVoip OBJECT IDENTIFIER ::= { wwpProducts 43 }

	-- 1.3.6.1.4.1.6141.1.44
	wwpLe42Voip OBJECT IDENTIFIER ::= { wwpProducts 44 }

	-- 1.3.6.1.4.1.6141.1.45
	wwpLe17 OBJECT IDENTIFIER ::= { wwpProducts 45 }

	-- 1.3.6.1.4.1.6141.1.46
	wwpLe17Voip OBJECT IDENTIFIER ::= { wwpProducts 46 }

	-- 1.3.6.1.4.1.6141.1.47
	wwpLe311 OBJECT IDENTIFIER ::= { wwpProducts 47 }

	-- 1.3.6.1.4.1.6141.1.48
	wwpLe38Sfp OBJECT IDENTIFIER ::= { wwpProducts 48 }

	-- 1.3.6.1.4.1.6141.1.49
	wwpLe38SfpVoip OBJECT IDENTIFIER ::= { wwpProducts 49 }

	-- 1.3.6.1.4.1.6141.1.70
	wwpLe311v OBJECT IDENTIFIER ::= { wwpProducts 70 }

	-- 1.3.6.1.4.1.6141.1.71
	wwpLe310 OBJECT IDENTIFIER ::= { wwpProducts 71 }

	-- 1.3.6.1.4.1.6141.1.72
	wwpLe135 OBJECT IDENTIFIER ::= { wwpProducts 72 }

	-- 1.3.6.1.4.1.6141.1.73
	wwpLe3300 OBJECT IDENTIFIER ::= { wwpProducts 73 }

	-- 1.3.6.1.4.1.6141.1.74
	wwpLe3300Rev2 OBJECT IDENTIFIER ::= { wwpProducts 74 }

	-- 1.3.6.1.4.1.6141.1.75
	wwpLe3300FanTray OBJECT IDENTIFIER ::= { wwpProducts 75 }

	-- 1.3.6.1.4.1.6141.1.76
	wwpLe58H OBJECT IDENTIFIER ::= { wwpProducts 76 }

	-- 1.3.6.1.4.1.6141.1.77
	cn3920 OBJECT IDENTIFIER ::= { wwpProducts 77 }

	-- 1.3.6.1.4.1.6141.1.78
	cn3911 OBJECT IDENTIFIER ::= { wwpProducts 78 }

	-- 1.3.6.1.4.1.6141.1.79
	cn3940 OBJECT IDENTIFIER ::= { wwpProducts 79 }

	-- 1.3.6.1.4.1.6141.1.80
	cn5150 OBJECT IDENTIFIER ::= { wwpProducts 80 }

	-- 1.3.6.1.4.1.6141.1.81
	cn3960 OBJECT IDENTIFIER ::= { wwpProducts 81 }

	-- 1.3.6.1.4.1.6141.1.82
	cn5140 OBJECT IDENTIFIER ::= { wwpProducts 82 }

	-- 1.3.6.1.4.1.6141.1.83
	cn5305 OBJECT IDENTIFIER ::= { wwpProducts 83 }

	-- 1.3.6.1.4.1.6141.1.84
	cn3916 OBJECT IDENTIFIER ::= { wwpProducts 84 }

	-- 1.3.6.1.4.1.6141.1.85
	cn3930 OBJECT IDENTIFIER ::= { wwpProducts 85 }

	-- 1.3.6.1.4.1.6141.1.86
	cn3931 OBJECT IDENTIFIER ::= { wwpProducts 86 }

	-- 1.3.6.1.4.1.6141.1.94
	cn3902 OBJECT IDENTIFIER ::= { wwpProducts 94 }

	-- 1.3.6.1.4.1.6141.1.95
	cn3932 OBJECT IDENTIFIER ::= { wwpProducts 95 }

	-- 1.3.6.1.4.1.6141.1.96
	cn5142 OBJECT IDENTIFIER ::= { wwpProducts 96 }

	-- 1.3.6.1.4.1.6141.1.97
	cn5160 OBJECT IDENTIFIER ::= { wwpProducts 97 }

	-- 1.3.6.1.4.1.6141.1.98
	cn3942 OBJECT IDENTIFIER ::= { wwpProducts 98 }

	-- 1.3.6.1.4.1.6141.1.99
	cn3903 OBJECT IDENTIFIER ::= { wwpProducts 99 }

	-- 1.3.6.1.4.1.6141.1.100
	cn3904 OBJECT IDENTIFIER ::= { wwpProducts 100 }

	-- 1.3.6.1.4.1.6141.1.101
	cn3905 OBJECT IDENTIFIER ::= { wwpProducts 101 }

	-- 1.3.6.1.4.1.6141.1.102
	cn3938 OBJECT IDENTIFIER ::= { wwpProducts 102 }

	-- 1.3.6.1.4.1.6141.1.103
	cn3906 OBJECT IDENTIFIER ::= { wwpProducts 103 }

	-- 1.3.6.1.4.1.6141.2.1
	wwpProductsMIB MODULE-IDENTITY
		LAST-UPDATED "200507280000Z"		-- July 28, 2005 at 00:00 GMT (200507280000Z)
		ORGANIZATION
			"Ciena, Inc"
		CONTACT-INFO
			"Mib Meister
			115 North Sullivan Road
			Spokane Valley, WA 99037
			   	USA		 		
			   	Phone:  +1 509 242 9000
			Email:  support@ciena.com"
		DESCRIPTION
			"This module defines the object identifiers that are
			assigned to WWP products and platforms.  It is these
			OID values that are returned in sysObjectID."
		REVISION "200507280000Z"		-- July 28, 2005 at 00:00 GMT (200507280000Z)
		DESCRIPTION
			"Initial creation."
	::= { wwpModules 1 }

END
