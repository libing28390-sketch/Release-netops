CTRON-WAN-IMUX-MIB DEFINITIONS ::= BEGIN

        --  ctron-wan-imux-mib.txt  The Cabletron Wide area Inverse Mux MIB.
        --  Revision: 01.00.03
        --  Part Number: 
        --  Date:  August 22, 1997

        --  Cabletron Systems, Inc.
        --  35 Industrial Way, P.O. Box 5005
        --  Rochester, NH 03867-0505
        --  (603) 332-9400
        --  support@ctron.com

        --  This module provides authoritative definitions for part
        --  of the naming tree below:
        --
        --              cabletron { enterprises 52 }
        --
        --  This module will be extended, as additional sub-sections
        --  of this naming tree are defined.
        --

        --  Cabletron Systems reserves the right to make changes in 
        --  specification and other information contained in this document 
        --  without prior notice.  The reader should consult Cabletron Systems
        --  to determine whether any such changes have been made.
        --
        --  In no event shall Cabletron Systems be liable for any incidental, 
        --  indirect, special, or consequential damages whatsoever (including 
        --  but not limited to lost profits) arising out of or related to this
        --  document or the information contained in it, even if Cabletron
        --  Systems has been advised of, known, or should have known, the 
        --  possibility of such damages.
        --
        --  Cabletron grants vendors, end-users, and other interested parties
        --  a non-exclusive license to use this Specification in connection
        --  with the management of Cabletron products.

        --  Copyright August 95 Cabletron Systems


    IMPORTS
            OBJECT-TYPE             FROM RFC-1212
            ctWanServices           FROM CTRON-MIB-NAMES;

--====================================================================
    -- Groups

    ctWanMux        OBJECT IDENTIFIER   ::= { ctWanServices 1 }

--
-- Wan Inverse Multiplexer Group
-- This group is required for any platforms that support
-- Cabletron's Ethernet to WAN Inverse Multiplexer Application
--

--
-- Inverse Multiplexer General Variables
--
--      These parameters apply globally to the Wan Inverse
--      multiplexer entity.
--

        ctWANMuxGeneralGroup OBJECT IDENTIFIER ::= { ctWanMux 1 }

        ctWANMuxMaxNumGroups    OBJECT-TYPE
                SYNTAX  INTEGER 
                ACCESS  read-only
                STATUS  mandatory
                DESCRIPTION
                        "Get the maximum number of Inverse Multiplexer groups
                        allowed to be programmed for this device.  This value
                        is the number of physical WAN connections, divided by
                        the minimum number of channels for a single mux
                        to be operational (2).  However, some devices may only
                        support a single inverse multiplexer group."
                ::= { ctWANMuxGeneralGroup 1}

        ctWanMuxAdmin   OBJECT-TYPE
                SYNTAX  INTEGER {
                        disabled(1),
                        enabled(2)
                        }
                ACCESS  read-write
                STATUS  mandatory
                DESCRIPTION
                        "Used to enable and disable the Inverse Multiplexer
                        Application.  This object is used to enable/disable
                        Inverse Multiplexing for the entire device.  Inverse
                        Multiplexer Groups may be enabled/disabled independently
                        using ctWanMuxGroupAdmin.  This object must be set to 
                        enabled for any inverse multiplexing to occur on the 
                        device."
                ::= { ctWANMuxGeneralGroup 2}

--
-- Inverse Multiplexer Group Table
--
--      The group structure contains information concerning
--      each specific multiplexing group contained within the
--      inverse multiplexing entity.
--

        ctWanMuxGroupTable OBJECT-TYPE
                SYNTAX      SEQUENCE OF CtWanMuxGroupEntry
                ACCESS      not-accessible
                STATUS      mandatory
                DESCRIPTION
                        "Information describing the configured parameters
                        of one of the Inverse Multiplexer groups."
                ::= { ctWanMux 2 }
        
        ctWanMuxGroupEntry OBJECT-TYPE
                SYNTAX      CtWanMuxGroupEntry
                ACCESS      not-accessible
                STATUS      mandatory
                DESCRIPTION
                        "A description of a single Inverse Multiplexer group 
                        entry."
                INDEX       { ctWanMuxGroupId }
                ::= { ctWanMuxGroupTable 1 }
        
        CtWanMuxGroupEntry ::=
                SEQUENCE {
                        ctWanMuxGroupId
                        INTEGER,
                        ctWanMuxGroupAdmin
                        INTEGER,
                        ctWanMuxGroupNumChannels
                        INTEGER,
                        ctWanMuxGroupAddChannel
                        INTEGER,
                        ctWanMuxGroupDelChannel
                        INTEGER
                        }
        
        ctWanMuxGroupId    OBJECT-TYPE
                SYNTAX      INTEGER (1..65535)
                ACCESS      read-only
                STATUS      mandatory
                DESCRIPTION
                        "A unique value identifying an element in a sequence of
                        groups which belong to the WAN Inverse Multiplexer.  
                        This value ranges from 1 to the maximum number of 
                        programmable groups as described by
                        ctWANMuxMaxNumGroups."
                ::= { ctWanMuxGroupEntry 1 }
        
        ctWanMuxGroupAdmin      OBJECT-TYPE
                SYNTAX  INTEGER {
                        disabled(1),
                        enabled(2)
                        }
                ACCESS  read-write
                STATUS  mandatory
                DESCRIPTION
                        "Used to enable and disable an Inverse Multiplexer
                        group which evenly distributes data traffic in a
                        properly sequenced fashion, over two or more single 
                        channel Wide Area Network connections such as DS1, 
                        E1, DDS, or SYNC.  Each of the single channel 
                        connections must be configured with an appropriate 
                        datalink protocol. A minimum of two channels, each 
                        assigned to it's own physical interface, is required
                        before the Inverse Multiplexer group can be enabled."
                ::= { ctWanMuxGroupEntry 2}

        ctWanMuxGroupNumChannels        OBJECT-TYPE
                SYNTAX  INTEGER 
                ACCESS  read-only
                STATUS  mandatory
                DESCRIPTION
                        "Get the number of channels currently
                        associated with this Inverse Multiplexer group. A 
                        minimum of two channels, each assigned to it's own
                        physical interface, is required before the Inverse 
                        Multiplexer group can be enabled."
                ::= { ctWanMuxGroupEntry 3}

        ctWanMuxGroupAddChannel   OBJECT-TYPE
                SYNTAX      INTEGER
                ACCESS      read-write
                STATUS      mandatory
                DESCRIPTION
                        "Add a channel to the channel list used by this Inverse
                        Multiplexer group.  Before a channel is added, the 
                        channel must be assigned a MIB II ifindex, and an
                        acceptable Datalink Protocol. When this object is set,
                        it is set with the ifindex value. This object is always
                        read as a 1."
                REFERENCE
                        "rfc-1213"
                ::= { ctWanMuxGroupEntry 4 }
          
        ctWanMuxGroupDelChannel   OBJECT-TYPE
                SYNTAX      INTEGER
                ACCESS      read-write
                STATUS      mandatory
                DESCRIPTION
                        "Delete a channel to the channel list used by this 
                        Inverse Multiplexer group.  Before a channel is
                        deleted, the channel must exist in the Inverse
                        Multiplexer group's channel table.  When this object
                        is set, it is set with the ifindex value of the channel
                        the user wishes to delete from the channel table. This 
                        object is always read as a 1."
                REFERENCE
                        "rfc-1213"
                ::= { ctWanMuxGroupEntry 5 }
          
--
-- Inverse Multiplexer Channel Table
--
--      The channel structure contains information concerning
--      specific channels contained within an
--      inverse multiplexing group.
--
        ctWanMuxChannelTable OBJECT-TYPE
                SYNTAX      SEQUENCE OF CtWanMuxChannelEntry
                ACCESS      not-accessible
                STATUS      mandatory
                DESCRIPTION
                        "Table containing ifindex values, representing WAN 
                        channels, used by the Inverse Multiplexer. The table 
                        also contains statistics reported about each channel."
                ::= { ctWanMux 3 }
        
        ctWanMuxChannelEntry OBJECT-TYPE
                SYNTAX      CtWanMuxChannelEntry
                ACCESS      not-accessible
                STATUS      mandatory
                DESCRIPTION
                        "A description of a single entry."
                INDEX       { ctWanMuxChannelGroupId, ctWanMuxChannelId }
                ::= { ctWanMuxChannelTable 1 }
        
        CtWanMuxChannelEntry ::=
                SEQUENCE {
                        ctWanMuxChannelGroupId
                        INTEGER,
                        ctWanMuxChannelId
                        INTEGER,
                        ctWanMuxChannelIfIndex
                        INTEGER,
                        ctWanMuxChannelPhysNum
                        INTEGER,
                        ctWanMuxChannelBwAvail
                        INTEGER,
                        ctWanMuxChannelByteCount
                        INTEGER,
                        ctWanMuxChannelStatus
                        INTEGER
                        }
        
        ctWanMuxChannelGroupId    OBJECT-TYPE
                SYNTAX      INTEGER (1..65535)
                ACCESS      read-only
                STATUS      mandatory
                DESCRIPTION
                        "A unique value identifying an element in a sequence 
                        of groups which belong to the WAN Inverse Multiplexer.
                        This value ranges from 1 to the maximum number of 
                        programmable groups as described by
                        ctWANMuxMaxNumGroups."
                ::= { ctWanMuxChannelEntry 1 }
        
        ctWanMuxChannelId    OBJECT-TYPE
                SYNTAX      INTEGER (1..65535)
                ACCESS      read-only
                STATUS      mandatory
                DESCRIPTION
                        "A unique value identifying an element in a sequence of
                        member channel ifindex values which belong to a WAN 
                        Inverse Multiplexer group."
                ::= { ctWanMuxChannelEntry 2 }
          
        ctWanMuxChannelIfIndex    OBJECT-TYPE
                SYNTAX      INTEGER
                ACCESS      read-only
                STATUS      mandatory
                DESCRIPTION
                        "Returns an ifindex associated with a WAN
                        channel used for Inverse Multiplexing."
                ::= { ctWanMuxChannelEntry 3 }

        ctWanMuxChannelPhysNum    OBJECT-TYPE
                SYNTAX      INTEGER
                ACCESS      read-only
                STATUS      mandatory
                DESCRIPTION
                        "Returns a unique physical connection identifier 
                        associated with this channel's physical WAN
                        connection."
                ::= { ctWanMuxChannelEntry 4 }

        ctWanMuxChannelBwAvail    OBJECT-TYPE
                SYNTAX      INTEGER
                ACCESS      read-only
                STATUS      mandatory
                DESCRIPTION
                        "Returns a value which represents the available 
                        bandwidth for transmitting data existing for the 
                        physical WAN connection associated with this channel.
                        The value is represented in bits/sec."
                ::= { ctWanMuxChannelEntry 5 }

        ctWanMuxChannelByteCount    OBJECT-TYPE
                SYNTAX      INTEGER
                ACCESS      read-only
                STATUS      mandatory
                DESCRIPTION
                        "Returns a value which represents a cumulative count
                        of bytes transmitted out from this interface.  The 
                        count includes any bytes transmitted across the
                        physical medium, less physical medium framing."
                ::= { ctWanMuxChannelEntry 6 }

        ctWanMuxChannelStatus    OBJECT-TYPE
                SYNTAX  INTEGER {
                        inactive(1),
                        active(2)
                        }
                ACCESS      read-only
                STATUS      mandatory
                DESCRIPTION
                        "Returns the current status of the channel associated
                        with an inverse multiplexer group.  The channel is 
                        active when the group admin status is enabled, and 
                        the channel is operational.  The channel is inactive 
                        when either the group admin status is disabled, or 
                        the channel is not operational."
                ::= { ctWanMuxChannelEntry 7 }

END
