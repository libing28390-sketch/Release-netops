TROPIC-OPTICALPORT-MIB DEFINITIONS ::= BEGIN

-- (c) Copyright 2023 Nokia Networks.  All rights reserved.
-- This software is the confidential and proprietary property of
-- Nokia and may only be used in accordance with the terms of the
-- license agreement provided with this software.

IMPORTS
      SnmpAdminString                         FROM SNMP-FRAMEWORK-MIB
      OBJECT-TYPE, MODULE-IDENTITY,
      Unsigned32, Integer32, Counter64        FROM SNMPv2-SMI
      MODULE-COMPLIANCE, OBJECT-GROUP         FROM SNMPv2-CONF
      TEXTUAL-CONVENTION,
      TruthValue                              FROM SNMPv2-TC
      InterfaceIndex, InterfaceIndexOrZero,
      ifIndex                                 FROM IF-MIB
      InetAddress                             FROM INET-ADDRESS-MIB
      TnSfpType,
      TnApsGroupId, TnSfpModuleState,
      AluWdmTnIfType,
      TropicCardCLEI,
      TropicCardManufacturingPartNumber,
      TropicCardSerialNumber,
      AluWdmDisabledEnabled,
      AluWdmEnabledDisabled,
      TnCommand,
      AluWdmTtiStatus,
      AluWdmDMInfoCurrentStatus,
      AluWdmFecMode,
      AluWdmPortOchOtuRate,
      NokiaAmpPortTargetPowerWidth            FROM TROPIC-TC
      tnChannel, tnDirection                  FROM TROPIC-WAVEKEY-MIB
      tnPortModules, tnOpticalPortMIB         FROM TROPIC-GLOBAL-REG
      AluPortYcableMode                       FROM TROPIC-L1SERVICE-MIB
      PortList                                FROM IEEE8023-LAG-MIB;

  tnOpticalPortMibModules MODULE-IDENTITY
      LAST-UPDATED    "202303031200Z"
      ORGANIZATION    "Nokia"
      CONTACT-INFO    "Nokia
                       Attn: Jeff Donnelly
                       600 Mountain Avenue
                       New Providence, NJ 07974

                       Phone: +1 732 221 6408
                       Email: jeff.donnelly@nokia.com"

      DESCRIPTION "Optical Port MIB types."

      REVISION    "202303031200Z"
      DESCRIPTION "Marked the following as deprecated:
                   tnAscPortConfigPowerGainL."

      REVISION    "202302241200Z"
      DESCRIPTION "Added the following to tnDwdmCmnPortXfpType:
                   ctSWR1GO(240)
                   ctSWL12O(241)."

      REVISION    "202302031200Z"
      DESCRIPTION "Added the following to tnMonOcmPortConfigTable:
                   tnMonOcmPortAssociatedOlpOpsRx
                   tnMonOcmPortAssociatedOlpOpsTx."

      REVISION    "202301201200Z"
      DESCRIPTION "Modified DESCRIPTION of the following:
                   tnFwPortModuleType."

      REVISION    "202301131200Z"
      DESCRIPTION "Added the following to tnPtpctlPortConfigTable:
                   tnPtpctlPortConfigFiberConnectPort."

      REVISION    "202211181200Z"
      DESCRIPTION "Added the following to tnDwdmCmnPortXfpType:
                   ctQ28P2CS(239)."

      REVISION    "202211041200Z"
      DESCRIPTION "1) Added the following to tnDwdmCmnPortXfpType:
                      ctBMDCO12(238).
                   2) Added the following to tnDwdmCmnClientPortConfigTable:
                      tnDwdmCmnClientPortSSFOnOCIAction."

      REVISION    "202210211200Z"
      DESCRIPTION "Modified DESCRIPTION of the following:
                   tnFwPortModuleType."

      REVISION    "202210141200Z"
      DESCRIPTION "Added the following to tnDwdmCmnPortXfpType:
                   ctBMDCO6E(236)
                   ctBMDCO6L(237)."

      REVISION    "202209301200Z"
      DESCRIPTION "Added the following to tnAscPortInfoTable:
                   tnAscPortInputToOutputGain."

      REVISION    "202209161200Z"
      DESCRIPTION "Added the following to tnGnssModuleTable:
                   tnGnssModuleAlmProfName."

      REVISION    "202208121200Z"
      DESCRIPTION "Added the following to tnOtPortInfoTable:
                   tnOtPortRxQmargin30s
                   tnOtPortRxQmargin5s
                   tnOtPortRxQfactor30s
                   tnOtPortRxQfactor5s
                   tnOtPortNEQfactor1s
                   tnOtPortFEQfactor1s
                   tnOtPortTuningSynchroStateRx
                   tnOtPortTuningSynchroStateTx."

      REVISION    "202208051200Z"
      DESCRIPTION "Added the following to tnMonOcmPortConfigTable:
                   tnMonOcmPortAssociatedFirstRoadmTx
                   tnMonOcmPortAssociatedSecondRoadmTx
                   tnMonOcmPortAssociatedFirstRoadmRx
                   tnMonOcmPortAssociatedSecondRoadmRx."

      REVISION    "202207151200Z"
      DESCRIPTION "Added the following card:
                   Opsuml."

      REVISION    "202207011200Z"
      DESCRIPTION "Added the following to tnDwdmCmnPortXfpType:
                   ctQ28LR1E(234)
                   ctQ56DR4(235)."

      REVISION    "202206031200Z"
      DESCRIPTION "1) Added the following to tnNetworkPortConfigTable:
                      tnNwPortRxFineOffSet
                      tnNwPortTxFineOffSet.
                   2) Added the following to tnNwPortProgrammedITUNumOffsetGridStepSize:
                      gridStep0Pt10GHz(3).
                   3) Added the following to tnDwdmCmnPortXfpType:
                      ctQ56LR4(233)."

      REVISION    "202205131200Z"
      DESCRIPTION "Added the following to tnDwdmCmnPortXfpType:
                   ctGeBx80U(231)
                   ctGeBx80D(232)."

      REVISION    "202205061200Z"
      DESCRIPTION "1) Added the following textual convention:
                      NokiaPtpClockIdentifier.
                   2) Added the following table:
                      tnGnssModuleTable."

      REVISION    "202204291200Z"
      DESCRIPTION "1) Added the following to tnDwdmCmnPortXfpType:
                      ctC2DCO4OD(230).
                   2) Added the following cards:
                      Ir32AW
                      EilaAW
                      18ce300."

      REVISION    "202203041200Z"
      DESCRIPTION "Added the following cards:
                   Sfd48
                   Sfd64."

      REVISION    "202202111200Z"
      DESCRIPTION "Added the following table:
                   tnFwPortModuleTable."

      REVISION    "202201281200Z"
      DESCRIPTION "1) Added the following to tnAscPortConfigTable:
                      tnAscPortConfigVoaSet.
                   2) Added the following to tnAscPortInfoTable:
                      tnAscPortInfoVoaCurrent."

      REVISION    "202201141200Z"
      DESCRIPTION "Added the following to tnAscPortConfigTable:
                   tnAscPortConfigAmpEnable."

      REVISION    "202112241200Z"
      DESCRIPTION "Added the following card:
                   Asc2."

      REVISION    "202112171200Z"
      DESCRIPTION "Added the following card:
                   Ir4."

      REVISION    "202112101200Z"
      DESCRIPTION "1) Added the following to tnSfpPortConfigTable:
                      tnSfpPortModuleDescription.
                   2) Added the following to tnDwdmCmnPortXfpType:
                      ctBMDCO6EL(229)."

      REVISION    "202111261200Z"
      DESCRIPTION "1) Added the following to tnSfpPortConfigTable:
                      tnSfpPortModuleCustomerLifeCycleState
                      tnSfpPortCircuitId
                      tnSfpPortIdModuleXponder.
                   2) Added the following to tnDwdmCmnPortConfigTable:
                      tnDwdmCmnPortCustomerLifeCycleState."

      REVISION    "202111121200Z"
      DESCRIPTION "Added the following to tnDwdmCmnPortXfpType:
                   ctC2DCO4O(228)."

      REVISION    "202110221200Z"
      DESCRIPTION "1) Added the following to tnDwdmCmnLinePortConfigTable:
                      tnDwdmCmnLinePortDegPrefecThr.
                   2) Added the following card:
                      Mxn1624."

      REVISION    "202109171200Z"
      DESCRIPTION "1) Added the following to tnSfpPortInfoTable:
                      tnSfpPortMaximumPowerConsumption.
                   2) Added the following to tnDwdmCmnLinePortInfoTable:
                      tnDwdmCmnLinePortDisruptionTime.
                   3) Added the following to tnDwdmCmnClientPortInfoTable:
                      tnDwdmCmnClientPortEthPrefec
                      tnDwdmCmnClientPortEthPostfec.
                   4) Added the following to tnOtPortInfoTable:
                      tnOtPortSupplyVoltage
                      tnOtPortSupplyCurrent
                      tnOtPortSupplyPower
                      tnOtPortTxLaserAge
                      tnOtPortLaserTemp."

      REVISION    "202108061200Z"
      DESCRIPTION "Added the following to tnAutoTurnUpTable:
                   tnAutoTurnUpTxSpanLoss."

      REVISION    "202107301200Z"
      DESCRIPTION "Added the following table:
                   tnAutoTurnUpOmsTable."

      REVISION    "202107231200Z"
      DESCRIPTION "1) Changed SYNTAX of the following from Integer32 (-2000..0)
                      to Integer32 (-2000..300):
                      tnIroadmPortConfigDropExpressTargetPower
                      tnWr20tfPortConfigExpressTargetPower
                      tnWr20tfmPortConfigExpressTargetPower.
                   2) Changed DEFVAL of the following from -900 to -800:
                      tnWr20tfPortConfigExpressTargetPower.
                   3) Changed DESCRIPTION of the following:
                      tnIroadmPortConfigDropExpressTargetPower
                      tnWr20tfPortConfigExpressTargetPower
                      tnWr20tfmPortConfigExpressTargetPower.
                   4) Added the following to tnDwdmCmnLinePortInfoTable:
                      tnDwdmCmnLinePortOtsigModuleCapabilityFileName."

      REVISION    "202107161200Z"
      DESCRIPTION "1) Added the following to tnAutoTurnUpTable:
                      tnAutoTurnUpOtsIngressCardType
                      tnAutoTurnUpOtsIngressSubType
                      tnAutoTurnUpOtsRamanCardType.
                   2) Added the following to tnOpsPortInfoTable:
                      tnOpsPortInfoExpectedInputPowerDev.
                   3) Added the following to tnMxnPortInfoTable:
                      tnMxnPortInfoAddExpectedPower
                      tnMxnPortInfoExpectedPowerDev.
                   4) Added the following to tnAscPortInfoTable:
                      tnAscPortInfoExpectedPowerDev."

      REVISION    "202107091200Z"
      DESCRIPTION "1) Added the following to tnOtsConfigTable:
                      tnOtsConfigOscInExternal.
                   2) Added the following to tnOpsPortInfoTable:
                      tnOpsPortInfoChanMeasuredPower."

      REVISION    "202107021200Z"
      DESCRIPTION "1) Added the following to tnAutoTurnUpTable:
                      tnAutoTurnUpResetOtsLinks
                      tnAutoTurnUpHoldOff.
                   2) Added the following to tnOpsPortConfigTable:
                      tnOpsPortConfigExpectedInputPower."

      REVISION    "202106181200Z"
      DESCRIPTION "1) Added the following to tnPtpioctlPortConfigTable:
                      tnPtpioctlPortConfigFiberConnectPort.
                   2) Added the following to tnAscPortInfoTable:
                      tnAscPortInfoChanTargetPower."

      REVISION    "202105281200Z"
      DESCRIPTION "1) Added the following to tnAutoTurnUpStatus:
                      topoInComplete(6).
                   2) Added the following to tnOpsPortConfigTable:
                      tnOpsPortConfigChannelFreq
                      tnOpsPortConfigSwitchingThresholdPsd.
                   3) Added the following to tnOpsPortInfoTable:
                      tnOpsPortInfoChannelMeasuredPsd."

      REVISION    "202105211200Z"
      DESCRIPTION "Modified description of the following:
                   tnPSS8xExpectedAmps
                   tnPSS12xExpectedAmps
                   tnPSS96ExpectedAmps."

      REVISION    "202105141200Z"
      DESCRIPTION "1) Added the following to tnAutoTurnUpTable:
                      tnAutoTurnUpActiveTemplate.
                   2) Added the following card:
                      Opsum."

      REVISION    "202105071200Z"
      DESCRIPTION "Added the following to tnDwdmCmnPortXfpType:
                   ctSS64CTU(227)."

      REVISION    "202104301200Z"
      DESCRIPTION "Added the following to tnInsertionLossPortTable:
                   tnInsertionLossPortEgressL
                   tnInsertionLossPortIngressL."

      REVISION    "202103051200Z"
      DESCRIPTION "Marked the following tables as obsolete:
                   tn40cx800PortConfigTable
                   tn40cx800PortInfoTable
                   tn8cx800PortConfigTable
                   tn8cx800PortInfoTable
                   tn6px800PortConfigTable
                   tn6px800PortInfoTable."

      REVISION    "202102261200Z"
      DESCRIPTION "Added the following to tnSfpPortInfoTable:
                   tnSfpPortPowerClass
                   tnSfpPortFirmwareVersion."

      REVISION    "202101291200Z"
      DESCRIPTION "1) Added the following to tnMxnPortConfigTable:
                      tnMxnPortConfigPlannedFrequencyIn
                      tnMxnPortConfigPlannedFrequencyOut.
                   2) Added the following to tnMxnPortInfoTable:
                      tnMxnPortInfoPlannedFrequencyLowLimitOut
                      tnMxnPortInfoPlannedFrequencyHighLimitOut
                      tnMxnPortInfoPlannedFrequencyLowLimitIn
                      tnMxnPortInfoPlannedFrequencyHighLimitIn.
                   3) Added the following to tnAscPortInfoTable:
                      tnAscPortInfoPlannedFrequencyIn
                      tnAscPortInfoPlannedFrequencyOut
                      tnAscPortInfoPlannedFrequencyLowLimitOut
                      tnAscPortInfoPlannedFrequencyHighLimitOut
                      tnAscPortInfoPlannedFrequencyLowLimitIn
                      tnAscPortInfoPlannedFrequencyHighLimitIn."

      REVISION    "202101221200Z"
      DESCRIPTION "1) Added the following to tnDwdmCmnPortXfpType:
                      ctBMDCO6(226).
                   2) Added the following to tnDwdmCmnClientPortContainer:
                      odutc1(16)
                      odutc4(17).
                   3) Added the following to tnIroadmPortConfigTable:
                      tnIroadmPortConfigIngressTargetPowerWidth.
                   4) Added the following to tnOmdclPortConfigTable:
                      tnOmdclPortConfigAsellEnabledL
                      tnOmdclPortConfigIngressTargetPowerWidth
                      tnOmdclPortConfigIngressTargetPowerWidthL.
                   5) Added the following to tnMxnPortInfoTable:
                      tnMxnPortInfoAddTargetPower."

      REVISION    "202101081200Z"
      DESCRIPTION "1) Changed SYNTAX of the following from INTEGER to SnmpAdminString:
                      tnPortOtdrScanErrorType.
                   2) Added the following to tnPortOtdrScanTable:
                      tnPortOtdrScanErrorDetail
                      tnPortOtdrScanRequestTimeStamp.
                   3) Added the following to tnAutoTurnUpTable:
                      tnAutoTurnUpIfIndexOtsRx
                      tnAutoTurnUpIfIndexOtsTx
                      tnAutoTurnUpLinkSequenceNumber
                      tnAutoTurnUpLinkState
                      tnAutoTurnUpLinkStatus
                      tnAutoTurnUpOtsTxIpv6Address
                      tnAutoTurnUpOtsTxIfIndex
                      tnAutoTurnUpOtsTxLineType
                      tnAutoTurnUpOtsTxTargetPower
                      tnAutoTurnUpOtsRxIpAddress
                      tnAutoTurnUpOtsRxIfIndex
                      tnAutoTurnUpOtsRxLineType
                      tnAutoTurnUpOtsRxTargetPower."

      REVISION    "202012311200Z"
      DESCRIPTION "1) Added the following to tnPortOtdrScanState:
                      abort(5).
                   2) Added the following table:
                      tnMaxPortTable."

      REVISION    "202012181200Z"
      DESCRIPTION "1) Changed MAX-ACCESS of the following from read-only to
                      read-create:
                      tnDwdmCmnLinePortOtsigOtuStruct.
                   2) Added the following to tnIroadmPortConfigTable:
                      tnIroadmPortConfigTargetPowerWidth
                      tnIroadmPortConfigTargetPowerWidthL.
                   3) Added the following to tnOmdclPortConfigTable:
                      tnOmdclPortConfigTargetPowerWidth
                      tnOmdclPortConfigTargetPowerWidthL."

      REVISION    "202012111200Z"
      DESCRIPTION "1) Added the following to tnAutoTurnUpTable:
                      tnAutoTurnUpOperationType
                      tnAutoTurnUpSummary.
                   2) Added the following to tnDwdmCmnPortXfpType:
                      ctSGS161(225).
                   3) Added the following to tnOmdclPortConfigTable:
                      tnOmdclPortConfigAsellEnabled."

      REVISION    "202011201200Z"
      DESCRIPTION "Added the following to tnAscPortInfoTable:
                   tnAscPortInfoEnable."

      REVISION    "202011061200Z"
      DESCRIPTION "1) Added the following to tnPortLptConfigCons:
                      obsaitxdis(4).
                   2) Added the following to tnIroadmPortConfigTable:
                      tnIroadmPortConfigAsellEnabled.
                   3) Added the following to tnAscPortInfoTable:
                      tnAscPortInfoOAMPumpTemperature
                      tnAscPortInfoOAMPumpBiases."

      REVISION    "202010301200Z"
      DESCRIPTION "1) Added the following to tnDwdmCmnPortXfpType:
                      ctQ28DAC(223)
                      ctQ28FR1E(224).
                   2) Added the following to tnRamanPortConfigTable:
                      tnRamanPortSpanLossTh.
                   3) Added the following to tnIroadmPortConfigTable:
                      tnIroadmPortConfigSpanLossTh.
                   4) Added the following to tnOmdclPortConfigTable:
                      tnOmdclPortConfigSpanLossTh.
                   5) Added the following to tnRamanPortInfoTable:
                      tnRamanPortSpanLoss.
                   6) Added the following to tnIroadmPortInfoTable:
                      tnIroadmPortInfoSpanLoss
                      tnIroadmPortInfoAseAmpOn
                      tnIroadmPortInfoAseAmpOnL
                      tnIroadmPortInfoAseTotalPowerOut
                      tnIroadmPortInfoAseTotalPowerOutL
                      tnIroadmPortInfoAseTargetTotalPowerOut
                      tnIroadmPortInfoAseTargetTotalPowerOutL.
                   7) Added the following to tnOmdclPortInfoTable:
                      tnOmdclPortInfoSpanLoss.
                   8) Added the following tables:
                      tnMxnPortConfigTable
                      tnAscPortConfigTable
                      tnMxnPortInfoTable
                      tnAscPortInfoTable."

      REVISION    "202010231200Z"
      DESCRIPTION "1) Added the following to tnPortOtdrScanState:
                      notApplicable(4).
                   2) Added the following to tnAutoTurnUpTable:
                      tnAutoTurnUpDegreeNumber
                      tnAutoTurnUpTxFiberType
                      tnAutoTurnUpTxConnectorLoss
                      tnAutoTurnUpRxConnectorLoss
                      tnAutoTurnUpTxFiberLength.
                   3) Added the following to tnDwdmCmnClientPortConfigTable:
                      tnDwdmCmnClientPortCSFDelayTimer.
                   4) Added the following table:
                      tnMxnPortChannelInfoTable."

      REVISION    "202010091200Z"
      DESCRIPTION "Added the following table:
                   tnPotentialQMarginTable
                   tnAutoTurnUpTable."

      REVISION    "202010021200Z"
      DESCRIPTION "1) Added the following to tnDwdmGpPhyPortPacketIfType:
                      gecbr400(28).
                   2) Added the following cards:
                      Mxn824
                      Asc4
                      5mx500
                      2ux500."

      REVISION    "202009251200Z"
      DESCRIPTION "Added the following to tnDwdmCmnClientPortConfigTable:
                   tnDwdmCmnClientPortSignalMode."

      REVISION    "202009181200Z"
      DESCRIPTION "Added the following cards:
                   16p200
                   Ir9."

      REVISION    "202009111200Z"
      DESCRIPTION "Added the following to tnDwdmCmnPortXfpType:
                   ctSLC28D(222)."

      REVISION    "202009041200Z"
      DESCRIPTION "Added the following to tnDwdmCmnPortXfpType:
                   ctS28C10U(220)
                   ctS28C10D(221)."

      REVISION    "202008211200Z"
      DESCRIPTION "Marked the following tables as obsolete:
                   tnD1ad400qPortConfigTable
                   tnD1ad400qPortInfoTable."

      REVISION    "202008141200Z"
      DESCRIPTION "Added the following to tnDwdmCmnClientPortConfigTable:
                   tnDwdmCmnClientPortCSFHoldOff
                   tnDwdmCmnClientPortSSFHoldOff."

      REVISION    "202008071200Z"
      DESCRIPTION "Marked the following tables as deprecated:
                   tn40cx800PortConfigTable
                   tn40cx800PortInfoTable
                   tn8cx800PortConfigTable
                   tn8cx800PortInfoTable
                   tn6px800PortConfigTable
                   tn6px800PortInfoTable."

      REVISION    "202007241200Z"
      DESCRIPTION "Added the following to tnLoopbackPortTable:
                   tnLoopbackPortFacTwo."

      REVISION    "202007171200Z"
      DESCRIPTION "Added the following to tnPortOtdrScanTable:
                   tnPortOtdrScanState
                   tnPortOtdrScanErrorType."

      REVISION    "202007101200Z"
      DESCRIPTION "1) Added the following to tnRamanPortConfigTable:
                      tnRamanPortORLThreshold.
                   2) Added the following to tnRamanPortInfoTable:
                      tnRamanPortORLCurrentValue."

      REVISION    "202007031200Z"
      DESCRIPTION "Added the following to tnDwdmCmnPortXfpType:
                   ctGNSSGM(219)."

      REVISION    "202006261200Z"
      DESCRIPTION "1) Added the following to tnDwdmCmnLinePortConfigTable:
                      tnDwdmCmnLinePortOtuOtsigId
                      tnDwdmCmnLinePortOtsigOTSiList
                      tnDwdmCmnLinePortOtsigOtuStruct
                      tnDwdmCmnLinePortOtsigProfileId
                      tnDwdmCmnLinePortOtsigCapacity
                      tnDwdmCmnLinePortOtsiPayloadRate
                      tnDwdmCmnLinePortOtsigMgracd.
                   2) Added the following to tnDwdmCmnLinePorttxShape:
                      superRRC01(4)."

      REVISION    "202006191200Z"
      DESCRIPTION "Added the following to tnDwdmCmnLinePortConfigTable:
                   tnDwdmCmnLinePortManagementMode."

      REVISION    "202006121200Z"
      DESCRIPTION "Added the following to tnDwdmCmnPortXfpType:
                   ctSULS1OU(217)
                   ctSULS1OD(218)."

      REVISION    "202005151200Z"
      DESCRIPTION "Added the following to tnOtPortInfoTable:
                   tnOtPortQsfpCurrentBias
                   tnOtPortQsfpVoltage."

      REVISION    "202005011200Z"
      DESCRIPTION "Added the following to tnOmdclPortInfoTable:
                   tnOmdclPortInfoTotalOutputPowerCplusL."

      REVISION    "202004241200Z"
      DESCRIPTION "Added the following to tnDwdmCmnPortXfpType:
                   ctS28F32L(214)
                   to
                   ctC4ACOO(216)."

      REVISION    "202004171200Z"
      DESCRIPTION "Added the following to tnRamanPortInfoTable:
                   tnRamanPortBRRCurrent."

      REVISION    "202004031200Z"
      DESCRIPTION "1) Added the following to tnSfpPortConfigTable:
                      tnSfpPortProductCodeSup.
                   2) Added the following to tnDwdmCmnPortXfpType:
                      ctC2DCO4(213).
                   3) Added the following to tnDwdmCmnLinePortConfigTable:
                      tnDwdmCmnLinePortDesignatedPortMode
                      tnDwdmCmnLinePortDesignatedRegenPair.
                   4) Added the following card:
                      12p120s."

      REVISION    "202003201200Z"
      DESCRIPTION "Added the following cards:
                   4uc1t
                   Asg."

      REVISION    "202003061200Z"
      DESCRIPTION "Added the following tnDwdmCmnPortXfpType:
                   ctQ28SR4D(212)."

      REVISION    "202002281200Z"
      DESCRIPTION "Added the following card:
                   18P400."

      REVISION    "202002211200Z"
      DESCRIPTION "1) Added the following to tnNetworkPortConfigTable:
                      tnNwPortChannelTxLane
                      tnNwPortChannelRxLane.
                   2) Added the following to tnDwdmCmnPortXfpType:
                      ctSUL1GOU(210)
                      ctSUL1GOD(211).
                   3) Added the following to tnSfpPortConfigTable:
                      tnSfpPortModuleName
                      tnSfpPortLifeCycleState
                      tnSfpPortProductCode
                      tnSfpPortDueDate."

      REVISION    "202002141200Z"
      DESCRIPTION "Added the following to tnOmdclPortInfoTable:
                   tnOmdclPortInfoTotalOutputPower
                   tnOmdclPortInfoTotalOutputPowerL."

      REVISION    "202001241200Z"
      DESCRIPTION "1) Marked the following to tnDwdmCmnPortXfpType as obsolete:
                      ctSXS642D(197).
                   2) Added the following to tnDwdmCmnPortXfpType:
                      ctS28C30u(206)
                      to
                      ctS28D13(209).
                   3) Added the following to tnOmdclPortInfoTable:
                      tnOmdclPortInfoInsertionLossSigC1IntoLine1Out
                      tnOmdclPortInfoInsertionLossSigC2IntoLine2Out
                      tnOmdclPortInfoInsertionLossSigL1IntoLine1OutL
                      tnOmdclPortInfoInsertionLossSigL2IntoLine2OutL
                      tnOmdclPortInfoInsertionLosstoSigC1OutFromLine1In
                      tnOmdclPortInfoInsertionLosstoSigC2OutFromLine2In
                      tnOmdclPortInfoInsertionLosstoSigL1OutFromLine1InL
                      tnOmdclPortInfoInsertionLosstoSigL2OutFromLine2InL."

      REVISION    "202001171200Z"
      DESCRIPTION "Added the following tables:
                   tnPortLptConfigTable
                   tnPortConfigTable
                   tnPortLptInfoTable
                   tnPortInfoTable."

      REVISION    "202001101200Z"
      DESCRIPTION "1) Added the following to tnOmdclPortConfigTable:
                      tnOmdclPortConfigTargetLinePpcOut
                      tnOmdclPortConfigTargetLinePpcOutL
                      tnOmdclPortConfigOSCVoaAtten.
                   2) Added the following to tnOmdclPortInfoTable:
                      tnOmdclPortInfoOSCSfpRxPowerIn
                      tnOmdclPortInfoOSCSfpTxPowerOut
                      tnOmdclPortInfoOSCTxPowerIn
                      tnOmdclPortInfoOSCTxPowerOut
                      tnOmdclPortInfoTotalInputPower
                      tnOmdclPortInfoTotalInputPowerL.
                   3) Added the following card:
                      Mlfsb."

      REVISION    "201912131200Z"
      DESCRIPTION "Added the following to tnIroadmPortConfigTable:
                   tnIroadmPortConfigAlienWaveBank."

      REVISION    "201911151200Z"
      DESCRIPTION "Added the following cards:
                   Omdcl
                   Mcs16x15L
                   EilaL
                   Ra5pb."

      REVISION    "201911011200Z"
      DESCRIPTION "Added the following to tnDwdmCmnPortConfigTable:
                   tnDwdmCmnPortPowerClassMod."

      REVISION    "201910041200Z"
      DESCRIPTION "Added the following card:
                   D1ad400q."

      REVISION    "201909201200Z"
      DESCRIPTION "Added the following to tnDwdmCmnPortXfpType:
                   ctQ28P2C(203)
                   to
                   ctQ28C20d(205)."

      REVISION    "201908231200Z"
      DESCRIPTION "1) Added the following to tnRamanPortConfigTable:
                      tnRamanPortConfigConnToPort.
                   2) Added the following to tnRamanPortInfoTable:
                      tnRamanPortPumpPowers."

      REVISION    "201908161200Z"
      DESCRIPTION "Added the following to tnDwdmCmnPortXfpType:
                   ctQ56FR4(201)
                   ctQ56LR8(202)."

      REVISION    "201908091200Z"
      DESCRIPTION "Added the following to tnRamanPortInfoTable:
                   tnRamanPortBRRbaseline."

      REVISION    "201908021200Z"
      DESCRIPTION "Added the following cards:
                   genericOt
                   1ety100."

      REVISION    "201907051200Z"
      DESCRIPTION "Added the following to tnDwdmCmnPortXfpType:
                   ctSWU1GO(200)."

      REVISION    "201906281200Z"
      DESCRIPTION "Added the following to tnDwdmCmnPortXfpType:
                   ctXL64TC(199)."

      REVISION    "201906211200Z"
      DESCRIPTION "1) Added the following to tnNetworkPortConfigTable:
                      tnNwPortLinkSpan.
                   2) Added the following to tnDwdmCmnPortXfpType:
                      ctC2ACOA(198)."

      REVISION    "201905311200Z"
      DESCRIPTION "Added the following card:
                   Esre."

      REVISION    "201905101200Z"
      DESCRIPTION "1) Added the following to tnDwdmCmnPortXfpType:
                      ctSXS642D(197).
                   2) Changed SYNTAX of the following from Integer32 (-9900..-1900)
                      to Integer32 (-9900..-1600):
                      tnAarPortConfigOaInputChannelPowerTargetSpecified.
                   3) Added the following packs for TPS:
                      TPS24PS1
                      TPS24PS2
                      TPS12PS."

      REVISION    "201905031200Z"
      DESCRIPTION "Changed SYNTAX of the following from InterfaceIndexOrZero
                   to Integer (-1..2147483647):
                   tnPortOtdrScanConnAddress."

      REVISION    "201904261200Z"
      DESCRIPTION "1) Added the following to tnDwdmCmnClientPortConfigTable:
                      tnDwdmCmnClientPortGfpFcs.
                   2) Added the following to tnOscSfpPortConfigTable:
                      tnOscLcpEchoInterval
                      tnOscLcpEchoFailure."

      REVISION    "201904191200Z"
      DESCRIPTION "Added the following to tnDwdmCmnLinePortConfigTable:
                   tnDwdmCmnLinePortDegUcbIntvl
                   tnDwdmCmnLinePortDegUcbThr
                   tnDwdmCmnLinePortDegUcbMon
                   tnDwdmCmnLinePortDegUcbCa."

      REVISION    "201903221200Z"
      DESCRIPTION "Added the following to tnOscSfpPortConfigTable:
                   tnOscIPv6LinkLocalInetAddress."

      REVISION    "201903151200Z"
      DESCRIPTION "Added inv(8) and oscLan(9) port type to the following:
                   tnEilaPortConfigFunction
                   tnEilaPortInfoFunction."

      REVISION    "201903081200Z"
      DESCRIPTION "Added the following to tnDwdmCmnPortXfpType:
                   ctSSC38N(193)
                   to
                   ctSS64TU(196)."

      REVISION    "201903011200Z"
      DESCRIPTION "Added the following to tnOscSfpPortConfigTable:
                   tnOscPortInfoETR."

      REVISION    "201902221200Z"
      DESCRIPTION "Added the following to tnPortOtdrScanTable:
                   tnPortOtdrScanEventThreshold
                   tnPortOtdrScanIOR."

      REVISION    "201902151200Z"
      DESCRIPTION "Added the following to tnIroadmPortInfoTable:
                   tnIroadmPortInfoIngressOaMaxFlatGainL
                   tnIroadmPortInfoEgressOaMaxFlatGainL."

      REVISION    "201902081200Z"
      DESCRIPTION "1) Added inv port type to the following:
                      tnAswgPortConfigFunction
                      tnAswgPortInfoFunction.
                   2) Added the following to tnIroadmPortInfoTable:
                      tnIroadmPortInfoIngressOaPowerInL
                      tnIroadmPortInfoIngressOaPowerOutL
                      tnIroadmPortInfoEgressOaPowerInL
                      tnIroadmPortInfoEgressOaPowerOutL
                      tnIroadmPortInfoIngressOaSignalPowerOutL
                      tnIroadmPortInfoEgressOaSignalPowerOutL
                      tnIroadmPortInfoIngressOaInputToOutputGainL
                      tnIroadmPortInfoEgressOaInputToOutputGainL
                      tnIroadmPortInfoActualTiltL
                      tnIroadmPortInfoGainTiltL
                      tnIroadmPortInfoEgressOAPowerGainL."

      REVISION    "201902011200Z"
      DESCRIPTION "Added oscLan port type to the following:
                   tnIrdm32PortConfigFunction
                   tnIrdm32PortInfoFunction."

      REVISION    "201901251200Z"
      DESCRIPTION "1) Added the following to tnOscSfpPortConfigTable:
                      tnOscEnable
                      tnOscConnId.
                   2) Added the following to tnIroadmPortConfigTable:
                      tnIroadmPortConfigGainRangeL
                      tnIroadmPortConfigIngressOaTargetPpcOutL
                      tnIroadmPortConfigPowerGainL
                      tnIroadmPortConfigIngressOaGainMaxL
                      tnIroadmPortConfigIngressOaGainMinL
                      tnIroadmPortConfigTargetTiltL
                      tnIroadmPortConfigVoaSetL
                      tnIroadmPortConfigTargetPpcOutL.
                   3) Added the following to tnIroadmPortInfoTable:
                      tnIroadmPortInfoActOutAttenL."

      REVISION    "201901181200Z"
      DESCRIPTION "Added the following card:
                   S4x400."

      REVISION    "201901111200Z"
      DESCRIPTION "Added the following to tnDwdmCmnLinePortInfoTable:
                   tnDwdmCmnLinePortOtsigId."

      REVISION    "201812281200Z"
      DESCRIPTION "Added the following card:
                   Irdm32l."

      REVISION    "201812141200Z"
      DESCRIPTION "Added the following to tnFlexgridOtsInfoTable:
                   tnFlexgridOtsInfoLineGranularityMHzIn
                   tnFlexgridOtsInfoLineGranularityMHzInL
                   tnFlexgridOtsInfoLineMinMSlicesPerXcIn
                   tnFlexgridOtsInfoLineMinMSlicesPerXcInL."

      REVISION    "201812061200Z"
      DESCRIPTION "Marked the following as obsolete:
                   tnPortOtdrScanMTable."

      REVISION    "201811021200Z"
      DESCRIPTION "Added ethman port type to following attributes:
                   tn6se300PortConfigFunction
                   tn6se300PortInfoFunction
                   tn30se300PortConfigFunction
                   tn30se300PortInfoFunction."

      REVISION    "201810261200Z"
      DESCRIPTION "1) Added the following to tnOtsConfigTable:
                      tnOtsConfigExternalAmp.
                   2) Added the following card:
                      Dfc12."

      REVISION    "201810121200Z"
      DESCRIPTION "Added the following to tnMcsPortInfoCurrentAddDisposition,
                   tnMcsPortConfigTargetForDispositionForce, and
                   tnMcsPortInfoCurrentDropDisposition:
                   sig9(10)
                   to
                   sig16(17)."

      REVISION    "201809281200Z"
      DESCRIPTION "Added the following cards:
                   10an1t
                   8uc1t."

      REVISION    "201809211200Z"
      DESCRIPTION "Added the following to tnDwdmCmnPortXfpType:
                   ctQ28C10E(191)
                   ctQ28ER4D(192)."

      REVISION    "201809141200Z"
      DESCRIPTION "Added the following to tnNetworkPortConfigTable:
                   tnNwPortCalculatedRxFreq
                   tnNwPortCalculatedTxFreq."

      REVISION    "201809071200Z"
      DESCRIPTION "1) Added the following to tnMcsPortInfoTable:
                      tnMcsPortInfoAddInputPower.
                   2) Added the following to tnMcs16x15PortInfoTable:
                      tnMcs16x15PortInfoAddInsertionLossToSig[1-16]
                      tnMcs16x15PortInfoDropInsertionLossFromSig[1-16]."

      REVISION    "201808241200Z"
      DESCRIPTION "Updated DESCRIPTION for the following:
                   tnOpsPortConfigSwitchingThreshold."

      REVISION    "201808101200Z"
      DESCRIPTION "1) Added the following card:
                      Mcs16x15.
                   2) Added the following to tnNetworkPortConfigTable:
                      tnNwPortProgrammedITUNumOffsetTx
                      tnNwPortProgrammedITUNumOffsetRx
                      tnNwPortProgrammedITUNumOffsetGridStepSize.
                   3) Added the following to tnOtsConfigTable:
                      tnOtsConfigGridStepSizeType."

      REVISION    "201808031200Z"
      DESCRIPTION "Added the following to tnDwdmCmnPortXfpType:
                   ctC2Csr10D(190)."

      REVISION    "201807271200Z"
      DESCRIPTION "Added the following to tnDwdmCmnClientPortConfigTable:
                   tnDwdmCmnClientPortSdiRate."

      REVISION    "201807201200Z"
      DESCRIPTION "Added the following to tnDwdmCmnPortXfpType:
                   ctS28SR(188)
                   ctS28LR(189)."

      REVISION    "201807111200Z"
      DESCRIPTION "Updated ranges for the following:
                   tnOpsPortConfigSwitchingThreshold
                   tnOpsPortTargetReceivedPower."

      REVISION    "201807061200Z"
      DESCRIPTION "Added the following card:
                   6px800."

      REVISION    "201806291200Z"
      DESCRIPTION "Added the following cards:
                   Irdm32
                   Ra4p
                   Eila
                   8cx800."

      REVISION    "201806221200Z"
      DESCRIPTION "Added the following to tnRamanPortConfigTable:
                   tnRamanPortAPRPulseAttempt."

      REVISION    "201805251200Z"
      DESCRIPTION "1) Added the following card:
                      40cx800
                   2) Added the following to tnNetworkPortConfigTable:
                      tnNwPortLaserOffRequest
                      tnNwPortForcedLaserState."

      REVISION    "201805181200Z"
      DESCRIPTION "Added the following to tnDwdmCmnPortXfpType:
                   ct3GSDIM30(187)."

      REVISION    "201804201200Z"
      DESCRIPTION "Added the following to tnDwdmCmnClientPortConfigTable:
                   tnDwdmCmnClientPortFlexGfpSize."

      REVISION    "201804061200Z"
      DESCRIPTION "1) Added the following to tnDwdmCmnPortXfpType:
                      ctSWU12O(186).
                   2) Changed the SYNTAX of the following from InterfaceIndex
                      to InterfaceIndexOrZero:
                      tnTimeSlotLinePortFarEndInterfaceIndex
                      tnTimeSlotLinePortNearEndInterfaceIndex."

      REVISION    "201803301200Z"
      DESCRIPTION "Added the following to tnDwdmCmnClientPortConfigTable:
                   tnDwdmCmnClientPortSsdca."

      REVISION    "201803231200Z"
      DESCRIPTION "Added the following card:
                   Ipreamp."

      REVISION    "201803161200Z"
      DESCRIPTION "1) Added the following to tnDwdmCmnClientPortConfigTable:
                      tnDwdmCmnClientPortSSFDelayCa.
                   2) Added the following to tn11dpe12aPortInfoFunction:
                      bits(6).
                   3) Removed range of (1700..2300) from SYNTAX and updated
                      DESCRIPTION of the following:
                      tnIroadmPortInfoEgressOAPowerGain."

      REVISION    "201802231200Z"
      DESCRIPTION "1) Added the following to tnDwdmCmnPortXfpType:
                      ctSWR12OL(185).
                   2) Updated the contact info."

      REVISION    "201801261200Z"
      DESCRIPTION "Added the following card:
                   Aswgl."

      REVISION    "201801121200Z"
      DESCRIPTION "1) Added the following to tnIroadmPortConfigTable:
                      tnIroadmPortConfigDropMaxTargetPower
                      tnIroadmPortConfigDropMinTargetPower
                      tnIroadmPortConfigDropInitTargetPower
                      tnIroadmPortConfigDropExpressTargetPower.
                   2) Added the following card:
                      Opsb5."

      REVISION    "201801051200Z"
      DESCRIPTION "Added the following to tnDwdmCmnPortXfpType:
                   ctSS1GOU(183)
                   ctSS1GOD(184)."

      REVISION    "201712291200Z"
      DESCRIPTION "Added ethman port type to following attributes:
                   tn11ope8PortConfigFunction
                   tn11qce12xPortConfigFunction
                   tn1ce100PortConfigFunction
                   tn12ce121PortConfigFunction
                   tn12ce120PortConfigFunction
                   tn11ope8PortInfoFunction
                   tn11qce12xPortInfoFunction
                   tn12ce120PortInfoFunction
                   tn1ce100PortInfoFunction
                   tn12ce121PortInfoFunction."

      REVISION    "201712131200Z"
      DESCRIPTION "Added the following to tnIroadmPortInfoTable:
                   tnIroadmPortInfoEgressOAPowerGain."

      REVISION    "201712081200Z"
      DESCRIPTION "Added the following to tnDwdmCmnPortXfpType:
                   ctC4ACO(182)."

      REVISION    "201712011200Z"
      DESCRIPTION "Added the following to tnAarPortConfigTable:
                   tnAarPortConfigOaInputChannelPowerTargetSpecified
                   tnAarPortConfigOaInputChannelPowerTargetActive."

      REVISION    "201711171200Z"
      DESCRIPTION "Added the following to tnDwdmCmnClientPortConfigTable:
                   tnDwdmCmnClientPortFecBypassInd."

      REVISION    "201711101200Z"
      DESCRIPTION "1) Added the following to tnDwdmCmnPortXfpType:
                      ctSL64TU(181).
                   2) Added the following card:
                      2ux200
                      4mx200."

      REVISION    "201711031200Z"
      DESCRIPTION "Added the following card:
                   Msh4fsb."

      REVISION    "201710271200Z"
      DESCRIPTION "Added the following table:
                   tnOtsConfigTable."

      REVISION    "201710131200Z"
      DESCRIPTION "1) Added the following to tnDwdmCmnPortXfpType:
                      ctC2ACO(179),
                      ctC2ACOD(180).
                   2) Added the following card:
                      S2ad200."

      REVISION    "201709221200Z"
      DESCRIPTION "Added the following cards:
                   PSS12xPowerFilter
                   Iroadm20."

      REVISION    "201709081200Z"
      DESCRIPTION "Added the following to tnDwdmCmnLinePortConfigTable:
                   tnDwdmCmnLinePortWtpsProtection."

      REVISION    "201709011200Z"
      DESCRIPTION "Added the following cards:
                   130sla1
                   130slx10."

      REVISION    "201708301200Z"
      DESCRIPTION "1) Added the following to tnIroadmPortConfigTable:
                      tnIroadmPortConfigOSCVoaAtten.
                   2) Added the following to tnIroadmPortInfoTable:
                      tnIroadmPortInfoOSCVoaAtten
                      tnIroadmPortInfoOSCTxPowerIn
                      tnIroadmPortInfoOSCTxPowerOut
                      tnIroadmPortInfoOSCRxPowerIn
                      tnIroadmPortInfoOSCSfpTxPowerOut
                      tnIroadmPortInfoOSCSfpRxPowerIn."

      REVISION    "201708181200Z"
      DESCRIPTION "1) Added the following to tnDwdmCmnLinePortConfigTable:
                      tnDwdmCmnLinePortClusterConnFrom.
                   2) Added the following to tnIroadmPortConfigTable:
                      tnIroadmPortConfigAprMode
                      tnIroadmPortConfigGainRange.
                   3) Added the following to tnIroadmPortInfoTable:
                      tnIroadmPortInfoActOutAtten.
                   4) Added the following card:
                      Da2c4."

      REVISION    "201708111200Z"
      DESCRIPTION "Added the following to tnWaveKeyPortInfoTable:
                   tnWaveKeyPortWTDecoderMeasurementTypeInL
                   tnWaveKeyPortWTDecoderMeasurementTypeOutL."

      REVISION    "201708031200Z"
      DESCRIPTION "1) Added the following to tnDwdmCmnPortXfpType:
                      ctS161BU(177),
                      ctS161BD(178).
                   2) Added the following to tnOpsPortConfigTable:
                      tnOpsPortTargetReceivedPower
                      tnOpsPortPaired.
                   3) Added the following to tnDwdmCmnClientPortConfigTable:
                      tnDwdmCmnClientPortInOpsbAction
                      tnDwdmCmnClientPortSSFDelayTimer."

      REVISION    "201707071200Z"
      DESCRIPTION "1) Added the following card:
                      18p40.
                   2) Fixed MIB compile issues."

      REVISION    "201706301200Z"
      DESCRIPTION "1) Redefined the enum values for the following attributes:
                      tn12ce120PortConfigFunction
                      tn12ce120PortInfoFunction.
                   2) Added the following card:
                      D5x500q."

      REVISION    "201706231200Z"
      DESCRIPTION "Added the following card:
                   Opsflex."

      REVISION    "201706091200Z"
      DESCRIPTION "1) Added the following to tnDwdmCmnPortXfpType:
                      S10GBSRO(176).
                   2) Added the following cards:
                      20An80
                      10An400
                      8P20."

      REVISION    "201705311200Z"
      DESCRIPTION "1) Added the following tables:
                      tnEthToTDMPortAssocInfoTable
                      tnOcsPacketPortConfigTable.
                   2) Added the following to tnFlexgridOtsInfoTable:
                      tnFlexgridOtsInfoDcmExistsOut
                      tnFlexgridOtsInfoDcmExistsIn."

      REVISION    "201705261200Z"
      DESCRIPTION "Added the following table:
                   tnPortOtdrScanMTable."

      REVISION    "201705191200Z"
      DESCRIPTION "Added the following to tnDwdmCmnLinePortConfigTable:
                   tnDwdmCmnLinePortPolarizationTrack."

      REVISION    "201705121200Z"
      DESCRIPTION "Added the following to tnFlexgridOtsInfoTable:
                   tnFlexgridOtsInfoChannelMonitoringAllowsOffGridOutL
                   tnFlexgridOtsInfoChannelMonitoringAllowsOffGridInL
                   tnFlexgridOtsInfoLineWssIsFlexgridL
                   tnFlexgridOtsInfoLineGranularityMHzL
                   tnFlexgridOtsInfoLineMinMSlicesPerXcL
                   tnFlexgridOtsInfoLineMaxMSlicesPerXcL."

      REVISION    "201704071200Z"
      DESCRIPTION "Added the following card:
                   Otdrm."

      REVISION    "201703241200Z"
      DESCRIPTION "1) Added the following to tnFlexgridOtsInfoTable:
                      tnFlexgridOtsInfoOadmDgeSupportedBands.
                   2) Added the following card:
                      Ra2p96."

      REVISION    "201703101200Z"
      DESCRIPTION "Added the following card:
                   Iroadm9r."

      REVISION    "201702241200Z"
      DESCRIPTION "Added the following to tnWaveKeyPortInfoTable:
                   tnWaveKeyPortNwPowerInL
                   tnWaveKeyPortNwPowerOutL."

      REVISION    "201702171200Z"
      DESCRIPTION "Added bits(6) to the following:
                   tn11qce12xPortConfigFunction
                   tn11qce12xPortInfoFunction."

      REVISION    "201702101200Z"
      DESCRIPTION "Marked custLan(6) as obsolete for the following cards:
                   AM2017B
                   AM2325B."

      REVISION    "201701271200Z"
      DESCRIPTION "1) Added the following to tnDwdmCmnPortXfpType:
                      ctSgT1(175).
                   2) Added the following cards:
                      D5x500l
                      LcI2000l."

      REVISION    "201701201200Z"
      DESCRIPTION "Added the following cards:
                   8dc30t
                   16dc65t."

      REVISION    "201701131200Z"
      DESCRIPTION "Added backplane port to the following tables:
                   tn11qpa4bPortConfigTable
                   tn11qpa4bPortInfoTable."

      REVISION    "201701031200Z"
      DESCRIPTION "Added the following to tnDwdmCmnClientPortConfigTable:
                   tnDwdmCmnClientPortServerPort."

      REVISION    "201612281200Z"
      DESCRIPTION "1) Added evoa(6) to the following:
                      tnAa2donwbPortConfigFunction
                      tnAa2donwbPortInfoFunction
                      tnOsctaprPortConfigFunction
                      tnOsctaprPortInfoFunction.
                   2) Added the following to tnOsctaprPortConfigEntry:
                      tnOsctaprPortConfigVoaMode
                      tnOsctaprPortConfigAttenuationModeAtten
                      tnOsctaprPortConfigConnToPort.
                   3) Added the following to tnAa2donwbPortConfigEntry:
                      tnAa2donwbPortConfigVoaMode
                      tnAa2donwbPortConfigAttenuationModeAtten
                      tnAa2donwbPortConfigConnToPort.
                   4) Added the following to tnDwdmCmnPortXfpType:
                      ctSxs642D(174)."

      REVISION    "201612171200Z"
      DESCRIPTION "Added the following card:
                   Otdrwb."

      REVISION    "201612091200Z"
      DESCRIPTION "Added the following cards:
                   30SE300
                   6SE300."

      REVISION    "201612071200Z"
      DESCRIPTION "Added the following to tnDwdmCmnPortXfpType:
                   ctQ28LR4E(172)
                   ctQ28SR4E(173)."

      REVISION    "201611231200Z"
      DESCRIPTION "Marked the following as to be obsoleted:
                   tnNwPortOchRxStatus
                   tnNwPortOchTxStatus."

      REVISION    "201611221200Z"
      DESCRIPTION "Added the following to tnDwdmCmnPortXfpType:
                   ct100BLXS(171)."

      REVISION    "201611181200Z"
      DESCRIPTION "Corrected Compliance sections."

      REVISION    "201611161200Z"
      DESCRIPTION "Updated the contact info."

      REVISION    "201611011200Z"
      DESCRIPTION "1) Added the following card:
                      LcI2000.
                   2) Added the following to tnDwdmCmnClientPortConfigTable:
                      tnDwdmCmnClientPortFlsState."

      REVISION    "201610261200Z"
      DESCRIPTION "Added the following to tnDwdmCmnPortXfpType.
                   ctSeul12O(170)."

      REVISION    "201610201200Z"
      DESCRIPTION "Added the following to tnDwdmGpPhyPortPacketIfType:
                   ge1cbrlan1(27)."

      REVISION    "201610131200Z"
      DESCRIPTION "Added the following to tnWaveKeyPortTable.
                   tnWaveKeyPortDefaultPowerDeviationInL
                   tnWaveKeyPortDefaultPowerDeviationOutL
                   tnWaveKeyPortCommonEgressPowerL."

      REVISION    "201609301200Z"
      DESCRIPTION "Added tnPSS8xExpectedAmps to tnPSS8xPowerFilterPortConfigTable."

      REVISION    "201609211200Z"
      DESCRIPTION "Added tnOpticalPortConnectorTable."

      REVISION    "201609161200Z"
      DESCRIPTION "1) Added the following to tnDwdmCmnPortXfpType.
                      ctXi641BU(166)
                      to
                      ctXs642BD(169).
                   2) Added the following to tnAarPortInfoTable.
                      tnAarPortInfoOAPump1BiasCurrent
                      tnAarPortInfoOAPump2BiasCurrent
                      tnAarPortInfoOAPump1Temperature
                      tnAarPortInfoOAPump2Temperature."

      REVISION    "201609131200Z"
      DESCRIPTION "Added the following cards:
                   PSS8xPowerFilter
                   Wtocmfl
                   Aar2x8al
                   Wr20tfml
                   Mcs8x16l."

      REVISION    "201609091200Z"
      DESCRIPTION "1) Added custLan(6) to:
                      tnA2325aPortConfigFunction
                      tnAlphgPortConfigFunction
                      tnAhplgPortConfigFunction
                      tnAm2017bPortConfigFunction
                      tnAm2325bPortConfigFunction
                      tnAhphgPortConfigFunction
                      tnA2325aPortInfoFunction
                      tnAlphgPortInfoFunction
                      tnAhplgPortInfoFunction
                      tnAm2017bPortInfoFunction
                      tnAm2325bPortInfoFunction
                      tnAhphgPortInfoFunction.
                   2) Added custLan(7) to:
                      tnAm2318aPortConfigFunction
                      tnIroadmfPortConfigFunction
                      tnA2p2125PortConfigFunction
                      tnA4pswgPortConfigFunction
                      tnAswgPortConfigFunction
                      tnAwbilaPortConfigFunction
                      tnAwbingPortConfigFunction
                      tnAm2318aPortInfoFunction
                      tnIroadmfPortInfoFunction
                      tnA2p2125PortInfoFunction
                      tnA4pswgPortInfoFunction
                      tnAswgPortInfoFunction
                      tnAwbilaPortInfoFunction
                      tnAwbingPortInfoFunction.
                   3) Added custLan(8) to:
                      tnAm2125aPortConfigFunction
                      tnAm2625aPortConfigFunction
                      tnAm2032aPortConfigFunction
                      tnIroadmvPortConfigFunction
                      tnIroadm9mPortConfigFunction
                      tnAm2125bPortConfigFunction
                      tnAm2125aPortInfoFunction
                      tnAm2625aPortInfoFunction
                      tnAm2032aPortInfoFunction
                      tnIroadmvPortInfoFunction
                      tnIroadm9mPortInfoFunction
                      tnAm2125bPortInfoFunction."

      REVISION    "201609021200Z"
      DESCRIPTION "Added the following to tnDwdmCmnClientPortConfigTable:
                   tnDwdmCmnClientPortHoldOffTimer
                   tnDwdmCmnClientPortHoldOffTimerValue."

      REVISION    "201608291200Z"
      DESCRIPTION "Added the following card:
                   S13x100e."

      REVISION    "201608221200Z"
      DESCRIPTION "Added the following card:
                   Aar2x8a."

      REVISION    "201608111200Z"
      DESCRIPTION "Added the following cards:
                   1Ux100
                   20Ax200
                   20Mx80."

      REVISION    "201608101200Z"
      DESCRIPTION "Added the following to tnDwdmGpPhyPortPacketIfType:
                   ge10GfpPpos(25),
                   ge10GfpPposOld(26)."

      REVISION    "201608081200Z"
      DESCRIPTION "1) Added the following to tnIroadmPortChannelInfoAddDisposition:
                      adt[5-9]
                   2) Added the following to tnDwdmCmnLinePortOdu4Encoding:
                      cohpm16qam250G(14)."

      REVISION    "201607271200Z"
      DESCRIPTION "1) Added the following to tnDwdmCmnPortXfpType:
                      ctC2cer4D(165).
                   2) Added the following to tnDwdmCmnClientPortConfigTable:
                      tnDwdmCmnClientPortEthFecMode.
                   3) Added the 11QPA4B, AA2DONWB, OSCTAPR, and Sfdc8[a-e] cards.
                   4) Added the following to tnDwdmGpPhyPortPacketIfType:
                      fc1200cbr(24).
                   5) Added the following to tnOt11dpm8PortConfigTable:
                      tnOt11dpm8PortConfigTtpPresent."

      REVISION    "201607181200Z"
      DESCRIPTION "Added the following to tnDwdmCmnPortXfpType:
                   ctC4csr4E(164)."

      REVISION    "201607041200Z"
      DESCRIPTION "Added the following to tnDwdmCmnPortXfpType:
                   ctSi641BU(160),
                   to
                   ctSs642BD(163)."

      REVISION    "201606291200Z"
      DESCRIPTION "Added the following to tnDwdmCmnPortXfpType:
                   ctQ28CWDM4(158),
                   ctQ28LR4D(159)."

      REVISION    "201606031200Z"
      DESCRIPTION "Added the following to tnDwdmCmnPortXfpType:
                   ct3GSDIE(157)."

      REVISION    "201605311200Z"
      DESCRIPTION "1) Added the following card:
                      Ptpioctl.
                   2) Added the following to tnDwdmCmnPortXfpType:
                      ctSULS1BOU(155),
                      ctSULS1BOD(156)."

      REVISION    "201605251200Z"
      DESCRIPTION "Added the following cards:
                   S13x100
                   12ce121."

      REVISION    "201605211200Z"
      DESCRIPTION "1) Added the following to tnDwdmCmnClientPortConfigTable:
                      tnDwdmCmnClientPortYcableMode.
                   2) Moved the follwing from tnDwdmCmnClientPortConfigTable
                      to tnDwdmCmnPortConfigTable:
                      tnDwdmCmnClientPortMgracd."

      REVISION    "201605201200Z"
      DESCRIPTION "Added the following card:
                   Iroadm9m."

      REVISION    "201605141200Z"
      DESCRIPTION "1) Added the following to tnRamanPortConfigTable:
                      tnRamanPortInitialAgcTargetGain.
                   2) Added the following to tnRamanPortInfoTable:
                      tnRamanPortPump5Power."

      REVISION    "201605101200Z"
      DESCRIPTION "Added the following card:
                   Ra5p."

      REVISION    "201605061200Z"
      DESCRIPTION "1) Removed the following from tnFlexgridOtsInfoTable:
                      tnFlexgridOtsInfoCBandLowestFrequencyGHz,
                      tnFlexgridOtsInfoCBandHighestFrequencyGHz,
                      tnFlexgridOtsInfoLBandLowestFrequencyGHz,
                      tnFlexgridOtsInfoLBandHighestFrequencyGHz,
                      tnFlexgridOtsInfoChannelMonitoringAllowsOffGrid.
                   2) Renamed the following to tnFlexgridOtsInfoTable:
                      From tnFlexgridOtsInfoLineWssGranularityMHz
                      To tnFlexgridOtsInfoLineGranularityMHz."

      REVISION    "201605041200Z"
      DESCRIPTION "Added the following card:
                   Awbila."

      REVISION    "201605031200Z"
      DESCRIPTION "1) Added the following cards:
                      Awbing
                      Awbegr.
                   2) Added the following table:
                      tnFlexgridOtsInfoTable."

      REVISION    "201604191200Z"
      DESCRIPTION "Added the following to tnDwdmCmnPortXfpType:
                   ctSgE1(153),
                   ctSgS11C(154)."

      REVISION    "201604081200Z"
      DESCRIPTION "1) Added the following to tn12ce120PortConfigFunction:
                      tod(3).
                   2) Added the following to tn1ce100PortConfigFunction:
                      tod(3).
                   3) Added the follwoing to tn12ce120PortInfoFunction:
                      tod(3).
                   4) Added the following to tn1ce100PortInfoFunction:
                      tod(3)."

      REVISION    "201604071200Z"
      DESCRIPTION "Added the following to tnDwdmCmnClientPortConfigTable:
                   tnDwdmCmnClientPortMgracd."

      REVISION    "201603151200Z"
      DESCRIPTION "Added the following to tnDwdmCmnLinePortConfigTable:
                   tnDwdmCmnLinePortCdPreComp,
                   tnDwdmCmnLinePortPhasenCode."

      REVISION    "201603081200Z"
      DESCRIPTION "Renamed the value of tnDwdmCmnPortXfpType from:
                   ctC120G1TC(147)
                   to
                   ct1Dc100M(147)."

      REVISION    "201602191200Z"
      DESCRIPTION "Changed the SYNTAX of following tnOtdrPortConfigConnAddress:
                   From InterfaceIndexOrZero To (-1..2147483647)."

      REVISION    "201602081200Z"
      DESCRIPTION "Changed SYNTAX of tnDwdmCmnLinePorttxShape."

      REVISION    "201601211200Z"
      DESCRIPTION "1) Added the following to tnDwdmCmnPortXfpType:
                      ctSXL642(151),
                      ctSXL642C(152).
                   2) Marked the below following as obsolete:
                      tnOpsaPortSwitchingThreshold,
                      tnOpsaPortSwitchingThresholdTolerance,
                      tnOpsaPortTransmitAttenuation,
                      tnOpsaPortSwitchingThreshCalcControl."

      REVISION    "201601121200Z"
      DESCRIPTION "Added the following to tnDwdmCmnLinePortConfigTable:
                   tnDwdmCmnLinePorttxShape."

      REVISION    "201601081200Z"
      DESCRIPTION "Added the following to tnDwdmCmnPortXfpType:
                   ct2Ac100(150)."

      REVISION    "201601041200Z"
      DESCRIPTION "Added backplane port to the following tables:
                   tnD5x500PortConfigFunction
                   tnD5X500PortInfoFunction."

      REVISION    "201512151200Z"
      DESCRIPTION "Added the following to tnDwdmCmnPortXfpType:
                   ct2Ac100H(149)."

      REVISION    "201512101200Z"
      DESCRIPTION "Added the following to tnOt112sdx11PortConfigTable:
                   tnOt112sdx11ProgrammedNwOutputPower."

      REVISION    "201512071200Z"
      DESCRIPTION "1) Added the following to tnPSS96PowerFilterPortConfigTable:
                      tnPSS96ExpectedAmps.
                   2) Added the following to tnDwdmCmnPortXfpType:
                      ctSWR120(148).
                   3) Added the LcI1000 card."

      REVISION    "201511231200Z"
      DESCRIPTION "Added the following to tnDwdmCmnPortXfpType:
                   ctC120G1TC(147)."

      REVISION    "201510281200Z"
      DESCRIPTION "Added the following cards:
                   12ce120
                   1ce100."

      REVISION    "201510211200Z"
      DESCRIPTION "Moved the following from tnDwdmCmnOtu4Odu4LinePortConfigTable to
                   tnDwdmCmnLinePortConfigTable:
                   tnDwdmCmnLinePortDegInterval,
                   tnDwdmCmnLinePortDegThreshold"

      REVISION    "201510141200Z"
      DESCRIPTION "Added the following to tnDwdmCmnPortXfpType:
                   ctC2CER4E(145),
                   ctSL64TUW(146)"

      REVISION    "201510131200Z"
      DESCRIPTION "1) Added the following to tnDwdmCmnPortXfpType:
                      ctCFP2ALUMetro(143),
                      ctCFP2ALULH(144).
                   2) Changed the range of tnDwdmCmnClientPortDegThreshold:
                      From (0..128000) to (0..'ffffffff'h)."

      REVISION    "201510051200Z"
      DESCRIPTION "Added the following card:
                   PSS96PowerFilter."

      REVISION    "201509291200Z"
      DESCRIPTION "Added the following to tnDwdmGpPhyPortPacketIfType:
                   gecbr100(23)."

      REVISION    "201509141200Z"
      DESCRIPTION "Added the MAX-ACCESS of tnDwdmCmnLinePortCluster:
                   From read-only to read-create."

      REVISION    "201509071200Z"
      DESCRIPTION "Added the following to tnDwdmCmnLinePortConfigTable:
                   tnDwdmCmnLinePortCluster."

      REVISION    "201508251200Z"
      DESCRIPTION "Added the following to tnDwdmCmnLinePortOdu4Encoding:
                   spqpsk(12),
                   qam64(13)."

      REVISION    "201508181200Z"
      DESCRIPTION "1) Renamed the following to tnDwdmCmnClientPortConfigTable:
                      tnDwdmCmnClientPortOdu2DegInterval to tnDwdmCmnClientPortDegInterval
                      tnDwdmCmnClientPortOdu2DegThreshold to tnDwdmCmnClientPortDegThreshold.
                   2) Added the following to tnDwdmCmnOtu4Odu4LinePortConfigTable:
                      tnDwdmCmnLinePortOdu4DegInterval to tnDwdmCmnLinePortDegInterval
                      tnDwdmCmnLinePortOdu4DegThreshold to tnDwdmCmnLinePortDegThreshold.
                   3) Changed range of tnDwdmCmnClientPortDegThreshold:
                      From (1..82026) to (0..128000).
                   4) Changed the DEFVAL of tnDwdmCmnClientPortDegThreshold:
                      From  4000 to 0."

      REVISION    "201508061200Z"
      DESCRIPTION "Added the following card:
                   MON-OTDR."

      REVISION    "201507221200Z"
      DESCRIPTION "1) Added the following to tnDwdmCmnClientPortConfigTable:
                      tnDwdmCmnClientPortOdu2DegInterval
                      tnDwdmCmnClientPortOdu2DegThreshold.
                   2) Added the following to tnDwdmCmnOtu4Odu4LinePortConfigTable:
                      tnDwdmCmnLinePortOdu4DegInterval
                      tnDwdmCmnLinePortOdu4DegThreshold."

      REVISION    "201507211200Z"
      DESCRIPTION "Removed DEFVAL as there is inconsistency between
                   the DEFVAL and the SYNTAX clause"

      REVISION    "201507171200Z"
      DESCRIPTION "Added the following to tnDwdmCmnOtu4Odu4LinePortConfigTable:
                   tnDwdmCmnLinePortOdu4Encoding."

      REVISION    "201506221200Z"
      DESCRIPTION "Added the OtS11M100 card."

      REVISION    "201506121200Z"
      DESCRIPTION "1) Added the following to tnD5x500PortConfigTable:
                      tnD5x500PortConfigFunction.
                   2) Added the following to tnD5x500PortInfoTable:
                      tnD5x500PortInfoFunction"

      REVISION    "201506031200Z"
      DESCRIPTION "Changed the following from tnIroadmvPortConfigTable
                   to tnIroadmPortConfigTable:
                   tnIroadmPortConfigLineDcmConnAddress."

      REVISION    "201506011200Z"
      DESCRIPTION "Added the following to tnIroadmPortConfigTable:
                   tnIroadmPortConfigForcedTargetPpcOut."

      REVISION    "201505261200Z"
      DESCRIPTION "1) Added the following to tnIroadmvPortConfigTable:
                      tnIroadmPortConfigLineDcmConnAddress.
                   2) Added the following to tnDcmPortInfoTable:
                      tnDcmPortInfoIroadmConnAddress."

      REVISION    "201505251200Z"
      DESCRIPTION "Added ToD port type to following MIBs:
                   tn11ope8PortConfigFunction
                   tn11ope8PortInfoFunction
                   tn11qce12xPortConfigFunction
                   tn11qce12xPortInfoFunction."

      REVISION    "201505151200Z"
      DESCRIPTION "Added the following to tnDwdmCmnPortConfigTable:
                   tnDwdmCmnPortAlmProfName."

      REVISION    "201503261200Z"
      DESCRIPTION "1) Added the following to tnDwdmCmnOtu4Odu4LinePortConfigTable:
                      tnDwdmCmnLinePortOdu4CndRes.
                   2) Added the following to tnDwdmCmnClientPortConfigTable:
                      tnDwdmCmnClientPortScramMode."

      REVISION    "201502201200Z"
      DESCRIPTION "1) Added the following cards:
                      Ul2uc400
                      Ul4uc400
                      Ul20uc200.
                   2) Added new values to tnIroadmPortConfigFiberTypeOut."

      REVISION    "201501161200Z"
      DESCRIPTION "Added the following card:
                   MonOcm."

      REVISION    "201501081200Z"
      DESCRIPTION "Added the following to tnDwdmCmnPortXfpType
                   ctC2Clr4D(138)."

      REVISION    "201412221200Z"
      DESCRIPTION "Added the following table:
                   tnWssRefLdPortInfoTable."

      REVISION    "201412121200Z"
      DESCRIPTION "Added the following to tnDwdmCmnPortXfpType
                   ctC4Clr4E(141)
                   ctC4Clr4D(142)."

      REVISION    "201412031200Z"
      DESCRIPTION "1) Added the following to tnIroadmPortConfigTable
                      tnIroadmPortConfigAprDisable.
                   2) Removed the following from tnIroadmPortInfoTable
                      tnIroadmPortInfoOSCTxPowerIn
                      tnIroadmPortInfoOSCTxPowerOut."

      REVISION    "201411191200Z"
      DESCRIPTION "Added the following tables:
                   tnIroadmPortConfigTable
                   tnIroadmPortInfoTable
                   tnIroadmPortChannelInfoTable."

      REVISION    "201411131200Z"
      DESCRIPTION "Added the following to tnDwdmCmnClientPortConfigTable:
                   tnDwdmCmnClientPortCSF
                   tnDwdmCmnClientPortSSF."

      REVISION    "201410311200Z"
      DESCRIPTION "Added the following to tnDwdmCmnPortXfpType:
                   ct2CBx10U(139)
                   ct2CBx10D(140)."

      REVISION    "201409251200Z"
      DESCRIPTION "Added the following cards:
                   Iroadmv
                   Iroadmf."

      REVISION    "201409181200Z"
      DESCRIPTION "Added the following card:
                   Ot130snq10."

      REVISION    "201408221200Z"
      DESCRIPTION "Added the following to tnOt112sdx11PortConfigTable:
                   tnOt112sdx11PortConfigLinkGroupId."

      REVISION    "201408081200Z"
      DESCRIPTION "Added the following cards:
                   12p120
                   20p200
                   1ud200."

      REVISION    "201408051200Z"
      DESCRIPTION "Changed SYNTAX of tnPortOtdrScanLastSuccessfulTimeStamp
                   to Unsigned32 from TimeTicks."

      REVISION    "201407221200Z"
      DESCRIPTION "1) Marked the following as obsolete:
                      tnWr20tfmPortConfigExecuteForcedDropDisposition
                      tnWr20tfmPortConfigExecuteForcedAddDisposition.
                   2) Modified description of following to tnWr20tfmPortChannelConfigTable:
                      tnWr20tfmPortChannelConfigTargetForcedDropDisposition
                      tnWr20tfmPortChannelConfigTargetForcedAddDisposition."

      REVISION    "201406201200Z"
      DESCRIPTION "1) Added the following cards:
                      Io30an300
                      Io4an400.
                   2) Changed size of tnPortOtdrScanFileName from
                      34 to 25 chars."

      REVISION    "201406121200Z"
      DESCRIPTION "1) Added the following to tnWr20tfmPortInfoTable:
                      tnWr20tfmPortInfoTestingActive.
                   2) Added the following to tnMcsPortInfoTable:
                      tnMcsPortInfoTestingActive.
                   3) Added the following to tnAarPortInfoTable:
                      tnAarPortInfoTestingActive."

      REVISION    "201405201200Z"
      DESCRIPTION "Changed default value of
                   tnWaveKeyPortCommonEgressPower from -2000 to 0."

      REVISION    "201405181200Z"
      DESCRIPTION "1) Added the following cards:
                      Sfd2[a-i,l-r]
                      VwmSfd8[a-d]
                      VwmSfc8.
                   2) Added the following textual convention:
                      AluWdmSfdPortType."

      REVISION    "201405061200Z"
      DESCRIPTION "Added the following cards:
                   Io4an100g
                   Io30an10g."

      REVISION    "201404301200Z"
      DESCRIPTION "Added tnPortOtdrScanLastSuccessfulTimeStamp to
                   tnPortOtdrScanTable"

      REVISION    "201403301200Z"
      DESCRIPTION "1) Added ranges or DEFVAL to attributes in this MIB file.
                   2) Changed DEFVAL of the following from 1200 to 1000:
                      tnWaveKeyPortUnexpectedWKThreshAutoMaxOffsetIn
                      tnWaveKeyPortUnexpectedWKThreshAutoMaxOffsetOut.
                   3) Changed DEFVAL of the following from maxPower to gain:
                      tnRamanPortOperatingMode.
                   4) Changed DEFVAL of the following from -800 to -900:
                      tnWr20tfPortConfigExpressTargetPower.
                   5) Changed DEFVAL of the following from -800 to -600:
                      tnWr20tfPortConfigDropMaxTargetPower.
                   6) Changed DEFVAL of the following from wtdMeasured
                      to unavailable:
                      tnWaveKeyPortWTDecoderMeasurementTypeIn
                      tnWaveKeyPortWTDecoderMeasurementTypeOut."

      REVISION    "201403191200Z"
      DESCRIPTION "1) Changed SYNTAX of the following from TropicDwMode
                      to AluWdmFecMode:
                      tnDwPortDwMode.
                   2) Marked the following as obsolete:
                      TropicDwMode.
                   3) Moved AluWdmPortOchOtuRate to TROPIC-TC."

      REVISION    "201403181200Z"
      DESCRIPTION "1) Added the following tables:
                      tnWr20tfmPortConfigTable
                      tnWr20tfmPortChannelConfigTable
                      tnMpoPortConfigTable
                      tnMpoPortInfoTable
                      tnMpoPortMultiPositionInfoTable
                      tnWr20tfmPortChannelInfoTable.
                   2) Added following textual conventions:
                      AluWdmWRConfigAddDropDisposition
                      AluWdmWRChannelCurrentAddDropDisposition."

      REVISION    "201403111200Z"
      DESCRIPTION "1) Added the following tables:
                      tnMcsPortConfigTable
                      tnAarPortConfigTable
                      tnMcsPortInfoTable
                      tnMcsPortChannelInfoTable
                      tnAarPortInfoTable.
                   2) Added the following to tnMcs8x16PortInfoTable:
                      tnMcs8x16PortInfoAddInsertionLossToSig[1-8]
                      tnMcs8x16PortInfoDropInsertionLossFromSig[1-8].
                   3) Added the following to tnRamanPortConfigTable:
                      tnRamanPortAprMode.
                   4) Added the following to tnRamanPortInfoTable
                      tnRamanPortPump[3-4]Power."

      REVISION    "201403041200Z"
      DESCRIPTION "Added the following table:
                   tnPortOtdrScanTable."

      REVISION    "201402271200Z"
      DESCRIPTION "Added the following cards:
                   Aswg
                   A4pswg
                   Otdr
                   Wr20tfm
                   Aar8a
                   Mcs8x16
                   Msh8fsm."

      REVISION    "201402261200Z"
      DESCRIPTION "1) Changed SYTAX of the following to use
                      AluWdmDMInfoCurrentStatus:
                      tnDwdmCmnLinePortDMInfoCurrentStatus
                      tnDwdmCmnLinePortOdu4DMInfoCurrentStatus.
                   2) Moved AluWdmFecMode to TROPIC-TC."

      REVISION    "201401241200Z"
      DESCRIPTION "1) Added the following to tnDwdmCmnOtu4Odu4LinePortConfigTable:
                      tnDwdmCmnLinePortOdu4DMConfigCMEPMode
                      tnDwdmCmnLinePortOdu4DMConfigEnable.
                   2) Added the following to tnDwdmCmnOtu4Odu4LinePortInfoTable:
                      tnDwdmCmnLinePortOdu4DMInfoCurrentStatus
                      tnDwdmCmnLinePortOdu4DMInfoCurrentValue."

      REVISION    "201401071200Z"
      DESCRIPTION "Updated DESCRIPTION of the following from microseconds
                   to 10**(-7) seconds:
                   tnDwdmCmnLinePortDMInfoCurrentValue."

      REVISION    "201312121200Z"
      DESCRIPTION "Added the following to tnOtPortInfoTable:
                   tnOtPortRxLaneBslPowers
                   tnOtPortTxLaneBslPowers."

      REVISION    "201312051200Z"
      DESCRIPTION "1) Added the following to tnOscSfpPortConfigTable:
                      tnOscMtuNeg.
                   2) Changed DEFVAL of tnOscMtu to 1500."

      REVISION    "201311251200Z"
      DESCRIPTION "Added the Wtocmf card."

      REVISION    "201311131200Z"
      DESCRIPTION "Added the following to tnDwdmCmnOtu4Odu4LinePortConfigTable:
                   tnDwdmCmnLinePortOdu4112GInterworking."

      REVISION    "201311061200Z"
      DESCRIPTION "Marked the following as obsolete:
                   tnGccPortConfigTable."

      REVISION    "201310211200Z"
      DESCRIPTION "1) Added the following to tnWr20tfPortConfigTable:
                      tnWr20tfPortConfigDropInitTargetPower
                      tnWr20tfPortConfigExpressTargetPower
                      tnWr20tfPortConfigDropMaxTargetPower
                      tnWr20tfPortConfigDropMinTargetPower.
                   2) Added the following:
                      tnWssPortInfoTable.
                   3) Added the following to tnDwdmCmnPortXfpType:
                      ctSxs642C(136),
                      ctC2Csr10E(137).
                   4) Marked the following as obsolete:
                      tnCwr8PortBlockerAging
                      tnCwr8c88PortBlockerAging
                      tnWr2c88PortBlockerAging."

      REVISION    "201310101200Z"
      DESCRIPTION "Added the Wr20tf card."

      REVISION    "201310071200Z"
      DESCRIPTION "Added the Psc1x6 card."

      REVISION    "201310031200Z"
      DESCRIPTION "Added the following to tnDwdmCmnPortXfpType:
                   ctSgS11(132),
                   to
                   ctSgL41(135)."

      REVISION    "201309131200Z"
      DESCRIPTION "Added the following to tnDwdmCmnPortXfpType:
                   ctSxs642B(130),
                   ctS1E(131)."

      REVISION    "201309041200Z"
      DESCRIPTION "Added the Io10an10gb and Io10et10gb cards."

      REVISION    "201308121200Z"
      DESCRIPTION "Added the Ot130sca1 card."

      REVISION    "201308021200Z"
      DESCRIPTION "1) Renamed the following to tnDwdmCmnPortXfpType from:
                      ctC1134TU(122)
                      to
                      ctC113G4T(122).
                   2) Added the following to tnWtocmaPortConfigTable:
                      tnWtocmaPortConfigOsnrClear."

      REVISION    "201307121200Z"
      DESCRIPTION "Added backplane(4) to:
                   tn11ope8PortConfigFunction
                   tn11qce12xPortConfigFunction
                   tn11ope8PortInfoFunction
                   tn11qce12xPortInfoFunction."

      REVISION    "201306241200Z"
      DESCRIPTION "1) Added the following to tnOt112sdx11PortInfoTable:
                      tnOt112sdx11PortInfoAggrRate.
                   2) Added the Aa2donw card."

      REVISION    "201306211200Z"
      DESCRIPTION "Added the following to tnDwdmCmnPortXfpType:
                   ctC2Clr4E(126)."

      REVISION    "201306131200Z"
      DESCRIPTION "Added the following to tnDwdmCmnPortXfpType:
                   ctSxi641(127)
                   to
                   ctQ40Glr4(129)."

      REVISION    "201306041200Z"
      DESCRIPTION "Added the following to tnDwdmCmnPortXfpType:
                   ctXs642D(125)."

      REVISION    "201306011200Z"
      DESCRIPTION "1) Added the following to tn11dpe12aPortConfigFunction:
                      bits(6).
                   2) Added the following to tn11dpe12aPortConfigTable:
                      tn11dpe12aPortConfigFlowControl."

      REVISION    "201305241200Z"
      DESCRIPTION "Added the Ul130scupb and Ot112sdx11 cards."

      REVISION    "201305231200Z"
      DESCRIPTION "1) Added the following to tnDwdmCmnLinePortConfigTable:
                      tnDwdmCmnLinePortDMConfigCMEPMode
                      tnDwdmCmnLinePortDMConfigEnable.
                   2) Added the following to tnDwdmCmnLinePortInfoTable:
                      tnDwdmCmnLinePortDMInfoCurrentStatus
                      tnDwdmCmnLinePortDMInfoCurrentValue."

      REVISION    "201305211200Z"
      DESCRIPTION "Marked the following as obsolete:
                   tnOpticalPortLcConfigGroups
                   tnOpticalPortLcConfigCompliances
                   tnOpticalPortEvents
                   tnOpticalPortLcConfig."

      REVISION    "201304191200Z"
      DESCRIPTION "Added the Ot11dpm8 and Ot11dpm4m cards."

      REVISION    "201304141200Z"
      DESCRIPTION "Added the following to tnMvacPortConfigTable:
                   tnMvacPortConfigVoaMode
                   tnMvacPortConfigAttenuationModeAtten
                   tnMvacPortConfigConnToPort."

      REVISION    "201304111200Z"
      DESCRIPTION "Added the Ot130snx10 and Io24anmb cards."

      REVISION    "201304091200Z"
      DESCRIPTION "Added the following to tnWtocmaPortConfigTable:
                   tnWtocmaPortConfigOsnrMeasure."

      REVISION    "201303291200Z"
      DESCRIPTION "Added the following to tn11dpe12aPortConfigTable:
                   tn11dpe12aPortConfigCompatibilityMode."

      REVISION    "201303161200Z"
      DESCRIPTION "1) Added the following table:
                      tnPortInventoryTable.
                   2) Added the Am2625a, Am2032a, and Ot260scx2 cards.
                   3) Updated ranges for the following:
                      tnWaveKeyPortUnexpectedWKThreshIngress
                      tnWaveKeyPortUnexpectedWKThreshEgress."

      REVISION    "201303141200Z"
      DESCRIPTION "1) Renamed ge1(5) in tnDwdmGpPhyPortPacketIfType to the
                      following:
                      gmpGfpT(5).
                   2) Added the following tables:
                      tnPowerFilterPortConfigTable
                      tnPowerFilterPortInfoTable."

      REVISION    "201303071200Z"
      DESCRIPTION "Added the 11ope8 and 11qce12x cards."

      REVISION    "201301301200Z"
      DESCRIPTION "Added the following table:
                   tnDTVPortTable."

      REVISION    "201301261200Z"
      DESCRIPTION "1) Added the following to tnDwdmCmnLinePortConfigTable:
                      tnDwdmCmnLinePortHoldOffTimer.
                   2) Marked the following as deprecated:
                      tnDwdmCmnLinePortOtu2holdofftimer
                      tnDwdmCmnLinePortOtu4holdofftimer."

      REVISION    "201301241200Z"
      DESCRIPTION "Marked the following legacy tables as obsolete:
                   tnOC48STM16PortConfigTable
                   tnOC192STM64PortConfigTable
                   tnQuadOC48STM16MuxPortConfigTable
                   tnQuadOC3or12STM1or4MuxPortConfigTable
                   tnBandFilterPortConfigTable
                   tnChFilterPortConfigTable
                   tnChAddDropPortConfigTable
                   tnBbaHgPortConfigTable
                   tnBbaLgPortConfigTable
                   tnPpsPortConfigTable
                   tnDualGigEMuxPortConfigTable
                   tnRoadmPortConfigTable
                   tn10GigELANPortConfigTable
                   tnDecaGigEMuxPortConfigTable
                   tnExternalDcuPortConfigTable
                   tnMsaHgPortConfigTable
                   tnCmd42PortConfigTable
                   tnWssX9PortConfigTable
                   tn1xMR2dot5GPortConfigTable
                   tnBbaHgPortLcConfigTable
                   tnBbaLgPortLcConfigTable
                   tnOC48STM16PortInfoTable
                   tnOC192STM64PortInfoTable
                   tnQuadOC48STM16MuxPortInfoTable
                   tnQuadOC3or12STM1or4MuxPortInfoTable
                   tnBandFilterPortInfoTable
                   tnChFilterPortInfoTable
                   tnChAddDropPortInfoTable
                   tnBbaHgPortInfoTable
                   tnBbaLgPortInfoTable
                   tnPpsPortInfoTable
                   tnDualGigEMuxPortInfoTable
                   tnRoadmPortInfoTable
                   tn10GigELANPortInfoTable
                   tnDecaGigEMuxPortInfoTable
                   tnExternalDcuPortInfoTable
                   tnMsaHgPortInfoTable
                   tnWssX9PortInfoTable
                   tn1xMR2dot5GPortInfoTable."

      REVISION    "201301071200Z"
      DESCRIPTION "Changed DEFVAL of tnDwdmGpPhyPortGfpcrc to std(2)."

      REVISION    "201212181200Z"
      DESCRIPTION "1) Added the following to tnOtPortInfoTable:
                      tnOtPortRxLanePowers
                      tnOtPortTxLanePowers.
                   2) Added the following to tn4qpa8PortConfigTable:
                      tn4qpa8PortConfigTtpPresent."

      REVISION    "201212141200Z"
      DESCRIPTION "Added network port for the following packs:
                   Io24et1gb
                   Io4an10g
                   Io8et1gb
                   Io10et10g."

      REVISION    "201212131200Z"
      DESCRIPTION "Added the following to tnDwdmCmnOtu4Odu4LinePortConfigTable:
                   tnDwdmCmnLinePortOtu4holdofftimer."

      REVISION    "201211261200Z"
      DESCRIPTION "Added the following to tnPtpioPortConfigTable:
                   tnPtpioPortConfigSigPortConnFromPort
                   tnPtpioPortConfigSigPortConnToPort."

      REVISION    "201211121200Z"
      DESCRIPTION "Added the following to tnDwdmCmnPortXfpType:
                   ct100BULHO(124)."

      REVISION    "201210241200Z"
      DESCRIPTION "Added the following to tnDwdmCmnPortXfpType:
                   ctXL64TCW(123)."

      REVISION    "201210221200Z"
      DESCRIPTION "1) Added the following table:
                      tnSkewInfoTable.
                   2) Added the following to AluWdmPortOchOtuRate:
                      otm129G280(12).
                   3) Updated DESCRIPTION for the following:
                      tnOpsaPortSwitchingThreshold
                      tnOpsPortConfigSwitchingThreshold."

      REVISION    "201209271200Z"
      DESCRIPTION "Added the following table:
                   tnWssAprPortConfigTable."

      REVISION    "201209251200Z"
      DESCRIPTION "1) Added the following to
                      tnDwdmCmnOtu4Odu4LinePortConfigTable:
                      tnDwdmCmnLinePortOdu4Interworking.
                   2) Added the following to tnNetworkPortConfigTable:
                      tnNwPortChannelSpacing."

      REVISION    "201209201200Z"
      DESCRIPTION "1) Added the following to tn11dpe12aPortConfigTable:
                      tn11dpe12aPortConfigPtpTrans.
                   2) Added the following to tnPtpioPortConfigFunction
                      and tnPtpioPortInfoFunction:
                      itp(4)."

      REVISION    "201209181200Z"
      DESCRIPTION "Marked the following as obsolete:
                   tnDwdmGpPhyPortInfoTable."

      REVISION    "201209111200Z"
      DESCRIPTION "Added the following to tnWtocmaPortInfoTable:
                   tnWtocmaPortInfoPower
                   tnWtocmaPortInfoPowerMonitoredPort."

      REVISION    "201208281200Z"
      DESCRIPTION "1) Added the Io4an10g, Io8et1gb, Io10et10g, Ul11qcupc,
                      and Ot520scx4 cards.
                   2) Added the following to tnDwdmCmnPortXfpType:
                      ctC113G4D(117),
                      to
                      ctC1134TU(122).
                   3) Added the following to tn11dpe12aPortConfigTable:
                      tn11dpe12aPortConfigPortRole."

      REVISION    "201208211200Z"
      DESCRIPTION "1) Added tnDwdmIoPortConfigTable with the following:
                      tnDwdmIoPortRole.
                   2) Added the following to tnDwdmCmnClientPortContainer:
                      odu2(6),
                      to
                      oduflexfc400(15)."

      REVISION    "201208061200Z"
      DESCRIPTION "1) Added the following to tnDwdmCmnPortXfpType:
                      ct16FCLCL(115),
                      ct16FCSNI(116).
                   2) Added the following to tnDwdmGpPhyPortConfigTable:
                      tnDwdmGpPhyPortGfpcrc."

      REVISION    "201207241200Z"
      DESCRIPTION "1) Added the Io24et1gb card.
                   2) Marked the following as obsolete:
                      11qta4."

      REVISION    "201206261200Z"
      DESCRIPTION "Added the following port to 11dpe12a:
                   tod(5)."

      REVISION    "201206201200Z"
      DESCRIPTION "1) Added the following to
                      tnDwdmCmnOtu4Odu4LinePortConfigTable:
                      tnDwdmCmnLinePortOtu4RegenResponse.
                   2) Added DEFVAL to other attributes in
                      tnDwdmCmnOtu4Odu4LinePortConfigTable."

      REVISION    "201206181200Z"
      DESCRIPTION "1) Added the A2p2125, 4qpa8, Ot112pdm11, Wtocma, Ptpctl,
                      and Ptpio cards.
                   2) Added the following to tnDwdmCmnPortXfpType:
                      ctC113S10(114)."

      REVISION    "201206151200Z"
      DESCRIPTION "Changed tnDwdmCmnLinePortApsEnable SYNTAX from
                   TruthValue to INTEGER, updated DESCRIPTION, and
                   added DEFVAL."

      REVISION    "201205251200Z"
      DESCRIPTION "1) Added the following to AluWdmFecMode:
                      eSDFec(10).
                   2) Marked the following as obsolete:
                      tnTcmPortConfigAttributeTotal
                      tnTcmPortConfigTable
                      tnTcmPortInfoAttributeTotal
                      tnTcmPortInfoTable."

      REVISION    "201205181200Z"
      DESCRIPTION "1) Added the following to tn11dpe12aPortConfigTable:
                      tn11dpe12aPortConfigMtu.
                   2) Marked the following as obsolete:
                      tnWr8c88aAttenPortConfigTable
                      tnWavekeyPortWTDecoderUsageStatusIn
                      tnWavekeyPortWTDecoderUsageStatusOut
                      tnE1T1PortInfoTable
                      tn1dpp24mPortClockSourceIncomingQLStatus
                      tn1dpp24mPortClockSourceIncomingQL."

      REVISION    "201204271200Z"
      DESCRIPTION "1) Added the following to tnDwdmCmnLinePortConfigTable:
                      tnDwdmCmnLinePortApsEnable.
                   2) Added the 130scx10 card."

      REVISION    "201204251200Z"
      DESCRIPTION "Added the following to AluWdmPortOchOtuRate:
                   otm10G714(10)."

      REVISION    "201204241200Z"
      DESCRIPTION "Added the ul130scup card."

      REVISION    "201203291200Z"
      DESCRIPTION "1) Added the 11dpe12a card.
                   2) Updated port names for Wr2c88."

      REVISION    "201203181200Z"
      DESCRIPTION "1) Added the Opsb card.
                   2) Marked the following as deprecated:
                      tnOpsaPortSwitchingThreshold
                      tnOpsaPortSwitchingThresholdTolerance
                      tnOpsaPortTransmitAttenuation
                      tnOpsaPortSwitchingThreshCalcControl
                      tnOpsaPortReceivedPower
                      tnOpsaPortPresentTransmitAttenuation.
                   3) Added the following scalars and tables to replace
                      the attributes that are common to Opsa and Opsb
                      in tnOpsaPortConfigTable and tnOpsaPortInfoTable:
                      tnOpsPortConfigAttributeTotal
                      tnOpsPortConfigTable
                      tnOpsPortInfoAttributeTotal
                      tnOpsPortInfoTable."

      REVISION    "201203151200Z"
      DESCRIPTION "Moved the following to TROPIC-TC:
                   AluWdmTtiStatus."

      REVISION    "201203071200Z"
      DESCRIPTION "Added the following to AluWdmPortOchOtuRate:
                   otm11G317(11)."

      REVISION    "201201231200Z"
      DESCRIPTION "Added the following to tnDwdmCmnPortXfpType:
                   ctC43G4C(113)."

      REVISION    "201201191200Z"
      DESCRIPTION "Added the cl10an10g and cl24anm cards."

      REVISION    "201201181200Z"
      DESCRIPTION "Added the Wr8c88af card."

      REVISION    "201201141200Z"
      DESCRIPTION "1) Added the following to tnDwdmCmnLinePortConfigTable:
                      tnDwdmCmnLinePortOtu2holdofftimer.
                   2) Added the following to tnDwdmCmnOtu3Odu3LinePortConfigTable:
                      tnDwdmCmnLinePortOdu3Interworking.
                   3) Added tnWssAttenPortConfigTable with the following:
                      tnWssAttenPortConfigWssAtten.
                   4) Marked the following as deprecated (replaced by
                      tnWssAttenPortConfigTable):
                      tnWr8c88aAttenPortConfigTable."

      REVISION    "201201101200Z"
      DESCRIPTION "Added the 11star1a and Mvac8b cards."

      REVISION    "201112211200Z"
      DESCRIPTION "Marked the following as deprecated:
                   tn1dpp24mPortClockSourceIncomingQLStatus
                   tn1dpp24mPortClockSourceIncomingQL."

      REVISION    "201111211200Z"
      DESCRIPTION "Added the 11qpe24 card."

      REVISION    "201111141200Z"
      DESCRIPTION "1) Added the 43scge1 card.
                   2) Added the following to
                      tnDwdmCmnOtu3Odu3LinePortConfigTable:
                      tnDwdmCmnLinePortOchOtu3Rate."

      REVISION    "201111091200Z"
      DESCRIPTION "1) Added the following table:
                      tnWssAttenPortInfoTable.
                   2) Added the following to AluWdmFecMode:
                      eFecI(7),
                      eFecE(8),
                      eFecB(9).
                   3) Added the following to AluWdmPortOchOtuRate:
                      otm44G58(9).
                   4) Added the following to tnDwdmCmnPortXfpType:
                      ctC11G4C(112)."

      REVISION    "201111021200Z"
      DESCRIPTION "Added the following to tnRamanPortInfoTable:
                   tnRamanPortPump[1-2]Power."

      REVISION    "201110241200Z"
      DESCRIPTION "Added the following to tnDwdmCmnLinePortConfigTable:
                   tnDwdmCmnLinePortDemandName."

      REVISION    "201109301200Z"
      DESCRIPTION "Marked the following as deprecated:
                   tnWavekeyPortWTDecoderUsageStatusIn
                   tnWavekeyPortWTDecoderUsageStatusOut."

      REVISION    "201109161200Z"
      DESCRIPTION "Added the 43scx4e card."

      REVISION    "201109061200Z"
      DESCRIPTION "Added the 11qpen4 card."

      REVISION    "201108311200Z"
      DESCRIPTION "Added the ul43scup and ul11qcup cards."

      REVISION    "201108191200Z"
      DESCRIPTION "1) Added the following to tnE1T1PortConfigTable:
                      tnE1T1PortConfigImpedance.
                   2) Marked the following as deprecated:
                      tnE1T1PortInfoTable
                      tnE1T1PortImpedance."

      REVISION    "201107291200Z"
      DESCRIPTION "1) Added the following to
                      tnDwdmCmnOtu3Odu3ClientPortInfoTable:
                      tnDwdmCmnClientPortOtu3PreFec
                      tnDwdmCmnClientPortOtu3PostFec.
                   2) Added the following to
                      tnDwdmCmnOtu4Odu4ClientPortInfoTable:
                      tnDwdmCmnClientPortOtu4PreFec
                      tnDwdmCmnClientPortOtu4PostFec."

      REVISION    "201107221200Z"
      DESCRIPTION "1) Added AluWdmWTDecoderMeasurementType.
                   2) Added the following to tnWaveKeyPortInfoTable:
                      tnWaveKeyPortWTDecoderMeasurementTypeIn
                      tnWaveKeyPortWTDecoderMeasurementTypeOut.
                   3) Added the following tables:
                      tnDwdmCmnOtu3Odu3ClientPortConfigTable
                      tnDwdmCmnOtu3Odu3ClientPortInfoTable."

      REVISION    "201107191200Z"
      DESCRIPTION "Added the 1dpp24m card."

      REVISION    "201107081200Z"
      DESCRIPTION "Added the following to tn1dpp21PortInfoTable:
                   tn1dpp21PortClockSourceIncomingQLStatus
                   tn1dpp21PortClockSourceIncomingQL."

      REVISION    "201107071200Z"
      DESCRIPTION "Added the 11qta4 card."

      REVISION    "201107021200Z"
      DESCRIPTION "Added the following to tnDwdmCmnPortXfpType:
                   ct1000BT2(110),
                   ctSFEBTEE(111)."

      REVISION    "201106301200Z"
      DESCRIPTION "Added the 112snx10 and 112sna1 cards."

      REVISION    "201105231200Z"
      DESCRIPTION "1) Changed range of tnOpticalFiberDispersionRating
                      from (0, 1000) to (-1, 1000).
                   2) Added range (-2650, -400) for
                      tnCwr8c88PortDropTargetPower.
                   3) Added DEFVAL for the following attributes:
                      tnWaveKeyPortUnexpectedWKThreshAutoModeIngress, true
                      tnWaveKeyPortUnexpectedWKThreshAutoModeEgress, true
                      tnWaveKeyPortUnexpectedWKThreshDeltaIngress, 500
                      tnWaveKeyPortUnexpectedWKThreshDeltaEgress, 500
                      tnWaveKeyPortUnexpectedWKThreshAutoMaxOffsetOut, 1200
                      tnWaveKeyPortCommonEgressPower, -2000
                      tnWaveKeyPortCommonIngressPower, -2000
                      tnWaveKeyPortDefaultPowerDeviationIn, 150
                      tnWaveKeyPortDefaultPowerDeviationOut, 150
                      tnOpticalFiberFixedLoss, 100
                      tnOpticalFiberLength, -1
                      tnOpticalFiberLossRating, 100
                      tnOpticalFiberDispersionRating, -1
                      tnSdhPortRxSignalDegradeThreshold, 7
                      tnSdhPortRxSignalFailThreshold, 5
                      tnSonetPortRxSignalDegradeThreshold, 7
                      tnSonetPortRxSignalFailThreshold, 5
                      tnDwPortRxRSBERSDThresh, 4
                      tnDwPortRxRSBERSFThresh, 3
                      tnOpsaPortSwitchingThreshold, -3000
                      tnOpsaPortSwitchingThresholdTolerance, 200
                      tnOpsaPortTransmitAttenuation, -1
                      tnCwr8PortBlockerAging, 0
                      tnDwdmCmnLinePortOdu2PayloadType, 253
                      tnOmdPortLosThresholdTolerance, 200
                      tnOmdPortLosOutThresholdTolerance, 200
                      tnCwr8c88PortBlockerAging, 0
                      tnCwr8c88PortDropTargetPower, -1200
                      tnDwdmCmnLinePortOdu1PayloadType, 128
                      tnDwdmCmnLinePortOdu3PayloadType, 32
                      tnWr2c88PortBlockerAging, 0."

      REVISION    "201105171200Z"
      DESCRIPTION "1) Added the 43scx4l and Am2125b cards.
                   2) Marked test(5) of Wr8c88a as obsolete.
                   3) Renumbered meshOut(7) as meshOut(5)."

      REVISION    "201105041200Z"
      DESCRIPTION "Added the 43sca1 card."

      REVISION    "201105021200Z"
      DESCRIPTION "Added support for Tandem Connection Monitoring (TCM)."

      REVISION    "201103301200Z"
      DESCRIPTION "Updated default value of tnWr8c88aPortConfigWssAtten
                   from 15 to 1500."

      REVISION    "201103251200Z"
      DESCRIPTION "1) Added otm43G018(8) to AluWdmPortOchOtuRate.
                   2) Added the following to tnDwdmCmnPortXfpType:
                      ct3GSDISH(108),
                      ct3GSDIMH(109)."

      REVISION    "201102101200Z"
      DESCRIPTION "Added the following to tnDwdmCmnPortXfpType:
                   ctX8FCSNI(107)."

      REVISION    "201101121200Z"
      DESCRIPTION "1) Updated the upper range of the following from 2000
                      to 2500:
                      tnRamanPortGMinExpected
                      tnRamanPortGMaxExpected.
                   2) Updated the default values of tnRamanPortGMinExpected
                      from 1000 to 700, and tnRamanPortGMaxExpected from
                      2000 to 2500."

      REVISION    "201012141200Z"
      DESCRIPTION "Added the following to tnRamanPortConfigTable:
                   tnRamanPortAgcTargetGain."

      REVISION    "201011301200Z"
      DESCRIPTION "Renamed tnDwdmCmnClientPortMappingMode to
                   tnDwdmCmnClientPortContainer."

      REVISION    "201011231200Z"
      DESCRIPTION "Added the following to tnDwdmCmnOtu4Odu4LinePortInfoTable:
                   tnDwdmCmnLinePortOtu4PreFec
                   tnDwdmCmnLinePortOtu4PostFec."

      REVISION    "201011221200Z"
      DESCRIPTION "Added the following to tnLoopbackPortTable:
                   tnLoopbackPortTSEB."

      REVISION    "201011141200Z"
      DESCRIPTION "Added the following to tnDwdmCmnClientPortConfigTable:
                   tnDwdmCmnClientPortMappingMode."

      REVISION    "201011101200Z"
      DESCRIPTION "1) Added the Mesh4 card.
                   2) Changed the following attributes from deprecated to current:
                      tnOscPortTotalNwPowerIn
                      tnOscPortTotalNwPowerOut
                      tnOscPortPhyDeviceLinkStatus
                      tnOscPortPhyDeviceIdNo
                      tnOscPortPhyDeviceMfgModelNo
                      tnOscPortPhyDeviceMfgRevNo."

      REVISION    "201011091200Z"
      DESCRIPTION "Marked the following as obsolete:
                   tnOscPortPhyDeviceReset
                   tnOscSfpPortType
                   tnOC48STM16PortSfpModulePresentType
                   tnOC48STM16PortSfpModuleVendorSerNo
                   tnOC48STM16PortSfpModuleState
                   tnOC48STM16PortSfpModuleVendor
                   tnOC48STM16PortSfpTxDisable
                   tnOC48STM16PortSfpWavelength
                   tnQuadOC48STM16MuxPortSfpModulePresentType
                   tnQuadOC48STM16MuxPortSfpModuleVendorSerNo
                   tnQuadOC48STM16MuxPortSfpModuleState
                   tnQuadOC48STM16MuxPortSfpModuleVendor
                   tnQuadOC48STM16MuxPortSfpTxDisable
                   tnQuadOC48STM16MuxPortSfpWavelength
                   tnQuadOC3or12STM1or4MuxPortSfpModulePresentType
                   tnQuadOC3or12STM1or4MuxPortSfpModuleVendorSerNo
                   tnQuadOC3or12STM1or4MuxPortSfpModuleState
                   tnQuadOC3or12STM1or4MuxPortSfpModuleVendor
                   tnQuadOC3or12STM1or4MuxPortSfpTxDisable
                   tnQuadOC3or12STM1or4MuxPortSfpWavelength
                   tnOscPortTotalNwPowerIn
                   tnOscPortPhyDeviceLinkStatus
                   tnOscPortPhyDeviceIdNo
                   tnOscPortPhyDeviceMfgModelNo
                   tnOscPortPhyDeviceMfgRevNo
                   tnDualGigEMuxPortSfpModulePresentType
                   tnDualGigEMuxPortSfpModuleVendorSerNo
                   tnDualGigEMuxPortSfpModuleState
                   tnDualGigEMuxPortSfpModuleVendor
                   tnDualGigEMuxPortSfpTxDisable
                   tnDualGigEMuxPortSfpWavelength
                   tnDecaGEMuxPortSfpModulePresentType
                   tnDecaGEMuxPortSfpModuleVendorSerNo
                   tnDecaGEMuxPortSfpModuleState
                   tnDecaGEMuxPortSfpModuleVendor
                   tnDecaGEMuxPortSfpTxDisable
                   tnDecaGEMuxPortSfpWavelength
                   tnWssX9PortTotalNwPowerIn
                   tnWssX9PortTotalNwPowerOut
                   tnCwr8PortTotalNwPowerIn
                   tnCwr8PortTotalNwPowerOut
                   tnDwdmCmnClientPortAvailableBandwidth
                   tnDwdmCmnLinePortAvailableBandwidth."

      REVISION    "201011011200Z"
      DESCRIPTION "Added the following to tnDwdmCmnLinePortConfigTable:
                   tnDwdmCmnLinePortRegenResponse."

      REVISION    "201010261200Z"
      DESCRIPTION "Added the following to tnDwdmGpPhyPortPacketIfType:
                   fc8GfpT(22)."

      REVISION    "201010251200Z"
      DESCRIPTION "Added the following to tnDwdmCmnPortXfpType:
                   ctC113G4Cd(106)."

      REVISION    "201010241200Z"
      DESCRIPTION "Added the following new tables:
                   tnWr8c88aAttenPortConfigTable
                   tnRamanPortConfigTable
                   tnRamanPortInfoTable."

      REVISION    "201010191200Z"
      DESCRIPTION "Added the 11dpm12 card."

      REVISION    "201010171200Z"
      DESCRIPTION "Added the 112sx10l and 112sa1l cards."

      REVISION    "201009281200Z"
      DESCRIPTION "1) Added the following to tnDwdmCmnPortXfpType:
                      ctX8FCLCL(105).
                   2) Added the 11dpe12e card."

      REVISION    "201009201200Z"
      DESCRIPTION "Added the Ra2p, Am2318a, Am2125a, Itlu, and Wr8c88a cards."

      REVISION    "201009161200Z"
      DESCRIPTION "Added range of SFD4 to tnOmdPortLosThreshold."

      REVISION    "201009101200Z"
      DESCRIPTION "Added the 43scx4 card."

      REVISION    "201008261200Z"
      DESCRIPTION "1) Added the following to tnGccPortConfigTable:
                      tnGccType.
                   2) Added the following to tnDwdmCmnClientPortInfoTable:
                      tnDwdmCmnClientPortOdu2IncFwFTFLTypeID
                      tnDwdmCmnClientPortOdu2IncFwFTFLOperID
                      tnDwdmCmnClientPortOdu2IncBwFTFLTypeID
                      tnDwdmCmnClientPortOdu2IncBwFTFLOperID
                      tnDwdmCmnClientPortOdu2IncResRow2
                      tnDwdmCmnClientPortOdu2IncResRow4
                      tnDwdmCmnClientPortOdu2IncExp
                      tnDwdmCmnClientPortOtu2IncRes.
                   3) Added the following to tnDwdmCmnLinePortInfoTable:
                      tnDwdmCmnLinePortOdu2IncFwFTFLTypeID
                      tnDwdmCmnLinePortOdu2IncFwFTFLOperID
                      tnDwdmCmnLinePortOdu2IncBwFTFLTypeID
                      tnDwdmCmnLinePortOdu2IncBwFTFLOperID
                      tnDwdmCmnLinePortOdu2IncResRow2
                      tnDwdmCmnLinePortOdu2IncResRow4
                      tnDwdmCmnLinePortOdu2IncExp
                      tnDwdmCmnLinePortOtu2IncRes.
                   4) Added the following to tnDwdmCmnOtu3Odu3LinePortInfoTable:
                      tnDwdmCmnLinePortOdu3IncFwFTFLTypeID
                      tnDwdmCmnLinePortOdu3IncFwFTFLOperID
                      tnDwdmCmnLinePortOdu3IncBwFTFLTypeID
                      tnDwdmCmnLinePortOdu3IncBwFTFLOperID
                      tnDwdmCmnLinePortOdu3IncResRow2
                      tnDwdmCmnLinePortOdu3IncResRow4
                      tnDwdmCmnLinePortOdu3IncExp
                      tnDwdmCmnLinePortOtu3IncRes.
                   5) Added the following to tn11dpge12PortInfoTable:
                      tn11dpge12PortIngAvailableBandwidth
                       tn11dpge12PortEgrAvailableBandwidth."

      REVISION    "201008091200Z"
      DESCRIPTION "Added the following to tnDwdmCmnPortXfpType:
                   ct100BFXS(104)."

      REVISION    "201007291200Z"
      DESCRIPTION "1) Added the following to tnDwdmCmnLinePortInfoTable:
                      tnDwdmCmnLinePortOtu2PostFec
                      tnDwdmCmnLinePortOtu2PreFec.
                   2) Added the following to tnDwdmCmnClientPortInfoTable:
                      tnDwdmCmnClientPortOtu2PreFec
                      tnDwdmCmnClientPortOtu2PostFec.
                   3) Added the following to tnDwdmCmnOtu1Odu1ClientPortInfoTable:
                      tnDwdmCmnClientPortOtu1PreFec
                      tnDwdmCmnClientPortOtu1PostFec.
                   4) Added the following to tnDwdmCmnOtu3Odu3LinePortInfoTable:
                      tnDwdmCmnLinePortOtu3PreFec
                      tnDwdmCmnLinePortOtu3PostFec."

      REVISION    "201007211200Z"
      DESCRIPTION "Added the following to tnWtocmPortInfoTable:
                   tnWtocmPortInfoPower
                   tnWtocmPortInfoPowerMonitoredPort."

      REVISION    "201007201200Z"
      DESCRIPTION "1) Added the Mvac card.
                   2) Added the following to tnE1T1PortConfigTable:
                      tnE1T1ClientEgressTimingMode."

      REVISION    "201007151200Z"
      DESCRIPTION "Changed tnSfpPortModuleVendorSerNo from 16 to 18 bytes."

      REVISION    "201007111200Z"
      DESCRIPTION "Added the following to tnSfpPortInfoTable:
                   tnSfpPortInterchangeabilityMarking
                   tnSfpPortAcronymCode."

      REVISION    "201006281200Z"
      DESCRIPTION "1) Added the Sfd4[a-h] cards.
                   2) Added the following to tnWaveKeyPortInfoTable:
                      tnWavekeyPortWTDecoderUsageStatusIn
                      tnWavekeyPortWTDecoderUsageStatusOut."

      REVISION    "201006231200Z"
      DESCRIPTION "Corrected inconsistent type declarations."

      REVISION    "201006161200Z"
      DESCRIPTION "1) Added the following to tnRsmonEgrPortInfoTable:
                      tnRsmonEgrPortTtiStatus.
                   2) Corrected SYNTAX for the following attributes:
                      tnOpsaPortSwitchingThreshCalcControl
                      tnDwdmCmnClientPortOchOtu1Rate
                      tnDwdmCmnClientPortOchOtu2Rate
                      tnDwdmCmnClientPortOchOtu4Rate."

      REVISION    "201006101200Z"
      DESCRIPTION "1) Added the following to tnGccPortConfigTable:
                      tnGccMtu
                      tnGccStd.
                   2) Added the following to tnOscSfpPortConfigTable:
                      tnOscMtu."

      REVISION    "201006071200Z"
      DESCRIPTION "Added the following to tnRsmonEgrPortConfigTable:
                   tnRsmonEgrPortTransmittedTti
                   tnRsmonEgrPortExpectedTti
                   tnRsmonEgrPortTimDetection
                   tnRsmonEgrPortTimConsequenceAction."

      REVISION    "201006041200Z"
      DESCRIPTION "1) Added the Am2017b, Am2325b, and 1dpp21 cards.
                   2) Added E1 signal table."

      REVISION    "201005101200Z"
      DESCRIPTION "1) Added the Wtocm and Wr2c88 cards.
                   2) Added the following to tn11dpge12PortInfoTable:
                      tn11dpge12PortTotalVTS.
                   3) Added backplane(4) port for the 11dpe12 pack.
                   4) Added the following to tnDwdmGpPhyPortPacketIfType:
                      ge10(21)."

      REVISION    "201003311200Z"
      DESCRIPTION "Marked tnDwdmCmnClientPortOdu4IncomingTti and
                   tnDwdmCmnClientPortOdu4TtiStatus in
                   tnDwdmCmnOtu4Odu4ClientPortConfigTable as obsolete
                   and added these two attributes to
                   tnDwdmCmnOtu4Odu4ClientPortInfoTable."

      REVISION    "201003051200Z"
      DESCRIPTION "Added the following to tnDwdmCmnPortXfpType:
                   ctL642(103)."

      REVISION    "201003011200Z"
      DESCRIPTION "Added the following to tnDwdmCmnPortXfpType:
                   ctGeBx20U(97),
                   to
                   ctFeBx40D(102)."

      REVISION    "201002251200Z"
      DESCRIPTION "1) Marked the following OSC attributes as deprecated:
                      tnOscPortPhyDeviceReset
                      tnOscPortTotalNwPowerIn
                      tnOscPortTotalNwPowerOut
                      tnOscPortPhyDeviceLinkStatus
                      tnOscPortPhyDeviceIdNo
                      tnOscPortPhyDeviceMfgModelNo
                      tnOscPortPhyDeviceMfgRevNo.
                   2) Deleted the following OSCT attributes:
                      tnOsctPortPhyDeviceReset
                      tnOsctPortTotalNwPowerIn
                      tnOsctPortTotalNwPowerOut
                      tnOsctPortPhyDeviceLinkStatus
                      tnOsctPortPhyDeviceIdNo
                      tnOsctPortPhyDeviceMfgModelNo
                      tnOsctPortPhyDeviceMfgRevNo."

      REVISION    "201002191200Z"
      DESCRIPTION "Added the following to tnDwdmCmnPortXfpType:
                   ct4FCOC(95),
                   ct4FCOD(96)."

      REVISION    "201002171200Z"
      DESCRIPTION "Added the Alpfgt and OscT cards."

      REVISION    "201002161200Z"
      DESCRIPTION "1) Added the following to tnDwdmCmnPortXfpType:
                      ctC113G4C(93),
                      ctC113G10C(94).
                   2) Added tnDwdmCbrArPortHdsdiRate to a new table,
                      tnDwdmCbrArPortConfigTable."

      REVISION    "201002091200Z"
      DESCRIPTION "Added the evoa port to tn11dpge12PortConfigFunction and
                   tn11dpge12PortInfoFunction."

      REVISION    "201002041200Z"
      DESCRIPTION "Updated descriptions for tnOtPortTxPower and
                   tnOtPortTxPowerLaser."

      REVISION    "201002021200Z"
      DESCRIPTION "Added the following to AluWdmFecMode:
                   aFec(6)."

      REVISION    "201001241200Z"
      DESCRIPTION "Marked the following as obsolete:
                   tnDwdmCmnClientPortLoopType
                   tnDwdmCmnLinePortLoopType."

      REVISION    "201001151200Z"
      DESCRIPTION "Added the following to tnDwdmCmnPortXfpType:
                   ctXl64Tu(90),
                   to
                   ctBncdvTx(92)."

      REVISION    "201001131200Z"
      DESCRIPTION "Added the following to tnDwdmCmnOtu4Odu4LinePortInfoTable:
                   tnDwdmCmnLinePortOdu4IncomingTti
                   tnDwdmCmnLinePortOdu4TtiStatus
                   tnDwdmCmnOtu4Odu4LinePortInfoTable."

      REVISION    "201001081200Z"
      DESCRIPTION "Moved tnRsmonEgrPortTimod and tnRsmonEgrPortSigMode
                   from tnRsmonEgrPortInfoTable to tnRsmonEgrPortConfigTable
                   (new table)."

      REVISION    "201001041200Z"
      DESCRIPTION "1) Added the 112scx10 and 112sca1 cards.
                   2) Added the following to AluWdmPortOchOtuRate:
                      otm111G810(7).
                   3) Added OTU4/ODU4 attributes to new tables:
                      tnDwdmCmnLinePortOchOtu4FecMode
                      tnDwdmCmnLinePortOchOtu4Rate
                      tnDwdmCmnLinePortOtu4TransmittedTti
                      tnDwdmCmnLinePortOtu4ExpectedTti
                      tnDwdmCmnLinePortOtu4TimConsequenceAction
                      tnDwdmCmnLinePortOtu4TimDetectionMode
                      tnDwdmCmnClientPortOchOtu4FecMode
                      tnDwdmCmnClientPortOchOtu4Rate
                      tnDwdmCmnClientPortOtu4TransmittedTti
                      tnDwdmCmnClientPortOtu4ExpectedTti
                      tnDwdmCmnClientPortOtu4TimConsequenceAction
                      tnDwdmCmnClientPortOtu4TimDetectionMode
                      tnDwdmCmnLinePortOdu4PayloadType
                      tnDwdmCmnLinePortOdu4PlmConsequenceAction
                      tnDwdmCmnLinePortOdu4TransmittedTti
                      tnDwdmCmnLinePortOdu4ExpectedTti
                      tnDwdmCmnLinePortOdu4TimConsequenceAction
                      tnDwdmCmnLinePortOdu4TimDetectionMode
                      tnDwdmCmnClientPortOdu4TransmittedTti
                      tnDwdmCmnClientPortOdu4ExpectedTti
                      tnDwdmCmnClientPortOdu4TimDetectionMode
                      tnDwdmCmnClientPortOtu4IncomingTti
                      tnDwdmCmnClientPortOtu4TtiStatus
                      tnDwdmCmnClientPortOdu4IncomingTti
                      tnDwdmCmnClientPortOdu4TtiStatus."

      REVISION    "200912281200Z"
      DESCRIPTION "Added the following to tnPortInfoTable:
                   tnOtPortTxPowerLaser."

      REVISION    "200912171200Z"
      DESCRIPTION "Added the following to tnDwdmCmnPortXfpType:
                   ctSEU12O(89)."

      REVISION    "200912111200Z"
      DESCRIPTION "1) Added the 11qpa4, Sfd40, Sfd40b, and A2325a cards.
                   2) Added the following to tnOscSfpPortConfigTable:
                      tnOscSfpTemperature.
                   3) Added the following to tnOtPortInfoTable:
                      tnOtPortBias
                      tnOtPortTemperature.
                   4) Added the following to tnDwdmCmnLinePortConfigTable:
                      tnDwdmCmnLinePortCrossRegPartner
                      tnDwdmCmnLinePortBroadcastFrom.
                   5) Added the following to tnDwdmCmnClientPortInfoTable:
                      tnDwdmCmnClientPortBroadcastPortMap."

      REVISION    "200911181200Z"
      DESCRIPTION "1) Added the following to tnOmdPortConfigTable:
                      tnOmdPortLosOutThreshold
                      tnOmdPortLosOutThresholdTolerance.
                   2) Added the following to tnOmdPortInfoTable:
                      tnOmdPortTransmittedPower.
                   3) Updated descriptions for tnOmdPortLosThreshold,
                      tnOmdPortLosThresholdTolerance, and
                      tnOmdPortReceivedPower."

      REVISION    "200911031200Z"
      DESCRIPTION "Added tnRsmonEgrPortInfoTable for OC48, STM16, and
                   1GBE for line ports for 4DPA2."

      REVISION    "200911011200Z"
      DESCRIPTION "1) Added the 43sta1p and 43stx4p cards.
                   2) Added the following to
                      tnDwdmCmnOtu3Odu3LinePortConfigTable:
                      tnDwdmCmnLinePortOdu3MappingMode."

      REVISION    "200909261200Z"
      DESCRIPTION "Added the following to AluWdmPortOchOtuRate:
                   otm4G55(6)."

      REVISION    "200909251200Z"
      DESCRIPTION "1) Added the Alpfgk, 4dpa2, and Sfd8[a-d] cards.
                   2) Changed the Osc card definitions for 1830."

      REVISION    "200909091200Z"
      DESCRIPTION "Fixed typo of tnDwdmCmnLinePortOdu1TimDetectionMode
                   in tnDwdmCmnOtu3Odu3LinePortConfigGroup."

      REVISION    "200908281200Z"
      DESCRIPTION "Changed tnNwPortChannelRx from read-only to read-create."

      REVISION    "200906121200Z"
      DESCRIPTION "Marked tnRsmonIngrPortTimDetectionMode as to be obsoleted."

      REVISION    "200905311200Z"
      DESCRIPTION "Ranamed tnNwPortProgrammedChannelRx as
                   tnNwPortChannelRx and changed it from read-create
                   to read-only."

      REVISION    "200905211200Z"
      DESCRIPTION "Added the following to tnNetworkPortConfigTable:
                   tnNwPortProgrammedChannelRx."

      REVISION    "200905141200Z"
      DESCRIPTION "Updated description for tnSfpPortDate."

      REVISION    "200905061200Z"

      DESCRIPTION "1) Renamed tnSfpMaximumCaseTemperature to
                      tnSfpPortMaximumCaseTemperature and changed its
                      SYNTAX to Integer32.
                   2) Added descriptions to the attributes in
                      tnSfpPortInfoTable."

      REVISION    "200905051200Z"
      DESCRIPTION "Added the following to tnSfpPortInfoTable:
                   tnSfpMaximumCaseTemperature."

      REVISION    "200904271200Z"
      DESCRIPTION "1) Added tn11dpge12PortAvailableBandwidth
                      to replace both tnDwdmCmnLinePortAvailableBandwidth
                      and tnDwdmCmnClientPortAvailableBandwidth
                      because of moving these attributes from
                      tnDwdmCmn*PortInfoTable to 11dpge12PortInfoTable.
                   2) Marked the following as deprecated:
                      tnDwdmCmnLinePortAvailableBandwidth
                      and tnDwdmCmnClientPortAvailableBandwidth."

      REVISION    "200904241200Z"
      DESCRIPTION "Added the following to tnDwdmCmnPortXfpType:
                   ct10GBZR(87),
                   ct100BLX10(88)."

      REVISION    "200904231200Z"
      DESCRIPTION "1) Added the following to tnDwdmCmnLinePortInfoTable:
                      tnDwdmCmnLinePortAvailableBandwidth.
                   2) Added the following to tnDwdmCmnClientPortInfoTable:
                      tnDwdmCmnClientPortAvailableBandwidth."

      REVISION    "200904071200Z"
      DESCRIPTION "Moved tnDwdmCmnClientPortTsMap from
                   TnDwdmCmnOtu1Odu1ClientPortConfigEntry to
                   tnDwdmCmnClientPortConfigGroup."

      REVISION    "200903311200Z"
      DESCRIPTION "Added support for the 43Stx4 card and OTU3/ODU3
                   attributes for this pack."

      REVISION    "200903251200Z"
      DESCRIPTION "Moved OTU1/ODU1 attributes to new tables."

      REVISION    "200903241200Z"
      DESCRIPTION "1) Renamed tnDwdmCmnLinePortOdu1OdukInterwork to
                      tnDwdmCmnLinePortOdu1Interworking.
                   2) Added table and attributes for NETSMAP/FETSMAP."

      REVISION    "200903221200Z"
      DESCRIPTION "1) Removed tnDwdmCmnLinePortFarEndTimeSlotMap.
                   2) Added the following to
                      tnDwdmCmnLinePortTransmissionMode:
                      crossRegen(6).
                   3) Added the following to tnDwdmGpPhyPortPacketFcMode:
                      isc(3).
                   4) Added the following to
                      tnDwdmCmnOtu1Odu1LinePortConfigTable:
                      tnDwdmCmnLinePortOdu1OdukInterwork.
                   5) Added the following to tnRsmonIngrPortConfigTable:
                      tnRsmonIngrPortSigMode."

      REVISION    "200903181200Z"
      DESCRIPTION "Added the AHPLG card."

      REVISION    "200903151200Z"
      DESCRIPTION "Added the CWR8-88, SFD44B, and ITLB cards."

      REVISION    "200903091200Z"
      DESCRIPTION "1) Removed the following XFP/SFP types defined in
                      tnDwdmCmnPortXfpType:
                      ctOc3sh(85)
                      to
                      unknown(91).
                   2) Added the following new XFP/SFP types:
                      ctEvoaFast(85)
                      ctEvoaSlow(86).
                   3) Changed otm226 to otm2G66."

      REVISION    "200903041200Z"
      DESCRIPTION "Renamed tnDwdmCmnClientPortTimeSlotMap to
                   tnDwdmCmnClientPortTsMap."

      REVISION    "200903031200Z"
      DESCRIPTION "Used AluWdmDisabledEnabled common enum in TROPIC-TC."

      REVISION    "200903021200Z"
      DESCRIPTION "1) Renamed tnOmdPortInfoGroup to <tnOpticalPortInfoGroups
                      73>.
                   2) Moved definition of tnOmdPortInfoGroup to the
                      <Conformance Port Info Group Definitions> section.
                   3) Add the following to AluWdmPortOchOtuRate:
                      otm2G66(5)."

      REVISION    "200903011200Z"
      DESCRIPTION "1) Used the following common enums:
                      AluWdmDisabledEnabled
                      AluWdmPortLaserTunability
                      AluWdmPortOchOtuRate
                      AluWdmTimDetectionMode
                      AluWdmMappingMode.
                   2) Added support for the 4DPA4 card and OTU1/ODU1
                      attributes for line ports for this pack."

      REVISION    "200902201200Z"
      DESCRIPTION "Added OTU1/ODU1 attributes for client ports for 11STMM10."

      REVISION    "200901051200Z"
      DESCRIPTION "Changed lower bound of tnOpsaPortSwitchingThreshold
                   from -2500 to -3000."

      REVISION    "200812161200Z"
      DESCRIPTION "Added the following to tnOpsaPortConfigTable:
                   tnOpsaPortSwitchingThreshCalcControl."

      REVISION    "200811231200Z"
      DESCRIPTION "Changed description of tnDwdmCmnPortXfpType from
                   The XFP type
                   to
                   The programmed XFP or SFP type."

      REVISION    "200811121200Z"
      DESCRIPTION "Changed SYNTAX of the following from SnmpAdminString
                   to OCTET STRING:
                   tnDwdmCmnClientPortOdu2ExpectedTti
                   tnDwdmCmnClientPortOdu2IncomingTti
                   tnDwdmCmnClientPortOdu2TransmittedTti
                   tnDwdmCmnClientPortOtu2ExpectedTti
                   tnDwdmCmnClientPortOtu2IncomingTti
                   tnDwdmCmnClientPortOtu2TransmittedTti
                   tnDwdmCmnLinePortOdu2ExpectedTti
                   tnDwdmCmnLinePortOdu2IncomingTti
                   tnDwdmCmnLinePortOdu2TransmittedTti
                   tnDwdmCmnLinePortOtu2ExpectedTti
                   tnDwdmCmnLinePortOtu2IncomingTti
                   tnDwdmCmnLinePortOtu2TransmittedTti."

      REVISION    "200810211200Z"
      DESCRIPTION "1) Changed ctSul120(82), ctSs1620(83), and ctSl1620(84)
                      in tnDwdmCmnPortXfpType from trailing 0 to the
                      letter O.
                   2) Changed ge10Cbr11095 to ge10Cbr11096 in
                      tnDwdmGpPhyPortPacketIfType."

      REVISION    "200810161200Z"
      DESCRIPTION "Marked the following as deprecated:
                   tnDwdmCmnLinePortLoopType
                   tnOscSfpPortType
                   tnWssX9PortTotalNwPowerIn
                   tnWssX9PortTotalNwPowerOut
                   tnCwr8PortTotalNwPowerIn
                   tnCwr8PortTotalNwPowerOut."

      REVISION    "200810071200Z"
      DESCRIPTION "Changed SYNTAX of the following from SnmpAdminString
                   to OCTET STRING:
                   tnRsmonIngrPortExpectedTti
                   tnRsmonIngrPortIncomingTti
                   tnRsmonIngrPortTransmittedTti."

      REVISION    "200809021200Z"
      DESCRIPTION "1) Added the following to tnDwdmCmnPortXfpType:
                      ctSul120(82),
                      to
                      ctSl1620(84).
                   2) Added the following tables:
                      tnOmdPortConfigTable
                      tnOmdPortInfoable."

      REVISION    "200808181200Z"
      DESCRIPTION "Added XS64.2_C to tnDwdmCmnPortXfpType and mapped
                   ctXS642b to CT_XS_642."

      REVISION    "200807281200Z"
      DESCRIPTION "Added new moduletypes to tnDwdmCmnPortXfpType and
                   re-ordered the enum list."

      REVISION    "200807251200Z"
      DESCRIPTION "1) Corrected the 11DPGE12 current configurable range for
                      tnDwdmCmnClientPortTs1.
                   2) Adjusted the values of tnDwdmCmnPortXfpType.
                   3) Added the following to tnRsmonIngrPortConfigTable:
                      tnRsmonIngrPortTimConsequenceAction
                      tnRsmonIngrPortTimDetectionMode."

      REVISION    "200807241200Z"
      DESCRIPTION "Added SFC1 port function attributes."

      REVISION    "200806251200Z"
      DESCRIPTION "1) Added the following to tnWaveKeyPortInfoTable:
                      tnWaveKeyPortNwPowerIn
                      tnWaveKeyPortNwPowerOut.
                   2) Added the following to tnDwdmCmnClientPortConfigTable:
                      tnDwdmCmnClientPortProtectionTs1
                      tnDwdmCmnClientPortProtectionTs2."

      REVISION    "200806171200Z"
      DESCRIPTION "Added tnVtsPortConfigTable."

      REVISION    "200806121200Z"
      DESCRIPTION "Added the EXP port type to the SFD (except SFD44) and
                   SFC (except SFC8) port function attributes."

      REVISION    "200806111200Z"
      DESCRIPTION "Added the SVAC, SFD and SFC port function attributes."

      REVISION    "200806091200Z"
      DESCRIPTION "1) Marked tnOscSfpPortType as to be deleted.
                   2) Marked tnDwdmCmnLinePortLoopType as to be deleted.
                   3) Added the following to tnDwdmCmnPortXfpType:
                      unknown(57)
                      to
                      ctFxulh(63)
                   4) Updated the descriptions of tnDwdmCmnClientPortTs1 and
                      tnDwdmCmnClientPortTs2.
                   5) Added the following to tnDwdmGpPhyPortConfigTable:
                      tnDwdmGpPhyPortPacketFcMode."

      REVISION    "200806051200Z"
      DESCRIPTION "1) Added the following to tnDwdmCmnPortXfpType:
                      ctSul11(43)
                      to
                      ct4FCLCL(56)
                   2) Changed tnMsmonPortAdaptationType to tnMsmonPortMappingMode.
                   3) Deleted tnDwdmCmnLinePortFrequency."

      REVISION    "200805291200Z"
      DESCRIPTION "1) Marked tnDwdmCmnLinePortFrequency as to be obsoleted.
                   2) Added auto and user to tnDwdmCmnPortXfpType.
                   3) Added tnOtPortInfoTable."

      REVISION    "200805221200Z"
      DESCRIPTION "Changed the description of the SFP port tables."

      REVISION    "200805021200Z"
      DESCRIPTION "1) Changed Line Loopback to Facility Loopback.
                   2) Updated the tnOpsaPortTransmitAttenuation description.
                   3) Changed the tnDwdmGpPhyPortAutoNegotiationStatus enum
                      values.
                   4) Changed the minimum configurable range of
                      tnDwdmCmnLinePortOdu2PayloadType to 0.
                   5) Added the following to tnDwdmCmnClientPortInfoTable:
                      tnDwdmCmnClientPortOtu2IncomingTti
                      tnDwdmCmnClientPortOtu2TtiStatus
                      tnDwdmCmnClientPortOdu2IncomingTti
                      tnDwdmCmnClientPortOdu2TtiStatus."

      REVISION    "200804111200Z"
      DESCRIPTION "1) Added the remote inventory to the SFP info table.
                   2) Added the following to tnDwdmGpPhyPortInfoTable:
                      tnDwdmGpPhyPortAutoNegotiationStatus.
                   4) Added the following to tnDwdmCmnClientPortConfigTable:
                      tnDwdmCmnClientPortOdu2TransmittedTti
                      tnDwdmCmnClientPortOdu2ExpectedTti
                      tnDwdmCmnClientPortOdu2TimDetectionMode
                   5) Changed SYNTAX of tnDwdmCmnClientPortOtu2TimConsequenceAction
                      to an enumerated integer (disabled, enabled).
                   6) Added the Far-End Time Slot Map against line ports.
                   7) Changed tnWaveKeyPortOutDeviation to:
                      tnWaveKeyPortDefaultPowerDeviationIn,
                      tnWaveKeyPortDefaultPowerDeviationOut.
                   8) Added the following to tnDwdmCmnLinePortInfoTable:
                      tnDwdmCmnLinePortOtu2IncomingTti
                      tnDwdmCmnLinePortOtu2TtiStatus
                      tnDwdmCmnLinePortOdu2IncomingTti
                      tnDwdmCmnLinePortOdu2TtiStatus.
                   9) Added the following to tnRsmonIngrPortInfoTable:
                      tnRsmonIngrPortIncomingTti
                      tnRsmonIngrPortTtiStatus."

      REVISION    "200804051200Z"
      DESCRIPTION "1) Added tnWaveKeyPortOutDeviation for FOADM SCOT.
                   2) Changed tnDwdmCmnLinePortOdu2PlmConsequenceAction
                      from Unsigned32 to TruthValue.
                   3) Changed the tnDwdmCmnLinePortFrequency range low
                      from 1 to 0.
                   4) Changed the tnDwdmCmnClientPortLosProp SYNTAX
                      values to laserOn and laserOff.
                   5) Changed the tnDwdmCmnClientPortOchOtu2Rate SYNTAX
                      to INTEGER with values:
                      otm10G709
                      otm11G049
                      otm11G096
                      otm11G27
                   6) Changed the tnOscSfpPortType SYNTAX values to:
                      unknown
                      oc3sh
                      oc3lh
                      oc3ulh
                      fxsh
                      fxlh
                      fxulh
                   7) Added the following to tnDwdmGpPhyPortConfigTable:
                      tnDwdmGpPhyPortErroredFrameDrop
                      tnDwdmGpPhyPortAutoNegotiation.
                   8) Added tnGccPortConfigTable."

      REVISION    "200804021200Z"
      DESCRIPTION "Changed the FEC mode values in the DWDM Line and
                   Client port FEC attributes."

      REVISION    "200803281200Z"
      DESCRIPTION "1) Added common ingress power to the wave key table.
                   2) Added value unknown to tnOscSfpPortType.
                   3) Changed the following attributes from Unsigned32 to INTEGER:
                      tnDwdmCmnLinePortTransmissionMode
                      tnDwdmCmnLinePortOdu2OchSignalDefConsequenceAction
                      tnDwdmCmnLinePortOtu2TimDetectionMode
                      tnDwdmCmnLinePortOdu2MappingMode
                      tnDwdmCmnLinePortOdu2TimDetectionMode
                      tnDwdmCmnClientPortOtu2TimDetectionMode
                   4) Added tnDwdmGpPhyPortConfigTable."

      REVISION    "200803201200Z"
      DESCRIPTION "1) Renamed OMD44 to SFD44.
                   2) Renamed 11GBART to 11STAR1.
                   3) Renamed 12XGBET to 11STGE12.
                   4) Renamed 12XGBEP2 to 11DPGE12.
                   5) Renamed 10XANYT to 11STMM10.
                   6) Renamed OPS to OPSA.
                   7) Removed 11GUART.
                   8) Added the OSC SFP table."

      REVISION    "200803141200Z"
      DESCRIPTION "Changed the AHPHG, ALPHG and DCM port tables
                   such that the 2 DCM ports are consolidated into 1."

      REVISION    "200803101200Z"
      DESCRIPTION "Updated OT port specific attribute descriptions."

      REVISION    "200803061200Z"
      DESCRIPTION "Added OT port specific attributes."

      REVISION    "200802161200Z"
      DESCRIPTION "Added port specific attributes to the CWR8 port tables."

      REVISION    "200802041200Z"
      DESCRIPTION "Change the AHPHG and ALPHG port function SYNTAX
                   value dcm to toDcm and fromDcm."

      ::= { tnPortModules 3 }

  tnOpticalPortConf                OBJECT IDENTIFIER ::= { tnOpticalPortMIB 1 }
  tnOpticalPortGroups              OBJECT IDENTIFIER ::= { tnOpticalPortConf 1 }
  tnOpticalPortCompliances         OBJECT IDENTIFIER ::= { tnOpticalPortConf 2 }
  tnOpticalPortConfigGroups        OBJECT IDENTIFIER ::= { tnOpticalPortConf 3 }
  tnOpticalPortInfoGroups          OBJECT IDENTIFIER ::= { tnOpticalPortConf 4 }
--  obsolete
--  tnOpticalPortLcConfigGroups      OBJECT IDENTIFIER ::= { tnOpticalPortConf 5 }
  tnOpticalPortConfigCompliances   OBJECT IDENTIFIER ::= { tnOpticalPortConf 6 }
  tnOpticalPortInfoCompliances     OBJECT IDENTIFIER ::= { tnOpticalPortConf 7 }
--  obsolete
--  tnOpticalPortLcConfigCompliances OBJECT IDENTIFIER ::= { tnOpticalPortConf 8 }
  tnOpticalPortObjs                OBJECT IDENTIFIER ::= { tnOpticalPortMIB 2 }
--  obsolete
--  tnOpticalPortEvents              OBJECT IDENTIFIER ::= { tnOpticalPortMIB 3 }
  tnOpticalPortConfig              OBJECT IDENTIFIER ::= { tnOpticalPortMIB 4 }
  tnOpticalPortInfo                OBJECT IDENTIFIER ::= { tnOpticalPortMIB 5 }
--  obsolete
--  tnOpticalPortLcConfig            OBJECT IDENTIFIER ::= { tnOpticalPortMIB 6 }

--------------------------------------------------------------------------------
-- Type Definitions
--------------------------------------------------------------------------------
--    obsolete
--    TropicDwMode ::= TEXTUAL-CONVENTION

    TropicMauType ::= TEXTUAL-CONVENTION
        STATUS         current
        DESCRIPTION    "."
        SYNTAX         INTEGER {
                         typeInvalid(1),
                         typeNone(2),
                         type10Base5(3),
                         typeFoir1(4),
                         type10Base2(5),
                         type10BaseT(6),
                         type10BaseFP(7),
                         type10BaseFB(8),
                         type10BaseFL(9),
                         type10Broad36(10),
                         type10BaseTHD(11),
                         type10BaseTFD(12),
                         type10BaseFLHD(13),
                         type10BaseFLFD(14),
                         type100BaseT4(15),
                         type100BaseTXHD(16),
                         type100BaseTXFD(17),
                         type100BaseFXHD(18),
                         type100BaseFXFD(19),
                         type100BaseT2HD(20),
                         type100BaseT2FD(21),
                         type1000BaseXHD(22),
                         type1000BaseXFD(23),
                         type1000BaseLXHD(24),
                         type1000BaseLXFD(25),
                         type1000BaseSXHD(26),
                         type1000BaseSXFD(27),
                         type1000BaseCXHD(28),
                         type1000BaseCXFD(29),
                         type1000BaseTHD(30),
                         type1000BaseTFD(31),
                         type10GigBaseX(32),
                         type10GigBaseLX4(33),
                         type10GigBaseR(34),
                         type10GigBaseER(35),
                         type10GigBaseLR(36),
                         type10GigBaseSR(37),
                         type10GigBaseW(38),
                         type10GigBaseEW(39),
                         type10GigBaseLW(40),
                         type10GigBaseSW(41)
                       }

    TropicSonetS1 ::= TEXTUAL-CONVENTION
        STATUS         current
        DESCRIPTION    "."
        SYNTAX         INTEGER {
                         unknown(1),
                         prs(2),       -- Stratum 1 Traceable
                         stu(3),       -- Synchronized - Traceability Unknown
                         st2(4),       -- Stratum 2 Traceable
                         tnc(5),       -- Transit Node Clock Traceable
                         st3e(6),      -- Stratum 3E Traceable
                         st3(7),       -- Stratum 3 Traceable
                         smc(8),       -- SONET Minimum Clock Traceable
                         dus(9),       -- DON'T USE for Synchronization
                         invalid(10)   -- Invalid S1
                       }

    TropicSdhS1 ::= TEXTUAL-CONVENTION
        STATUS         current
        DESCRIPTION    "."
        SYNTAX         INTEGER {
                         unknown(1),
                         prc(2),       -- PRC Clock G.811
                         ssua(3),      -- Type I or V SSU clock G.812
                         ssub(4),      -- Type VI SSU clock G.812
                         sec(5),       -- SEC clock G.813 option 1
                         dnu(6),       -- DON'T USE for Synchronization
                         invalid(7)    -- Invalid S1
                       }

    AluWdmVtsSource ::= TEXTUAL-CONVENTION
        STATUS         current
        DESCRIPTION    "VTS source."
        SYNTAX         INTEGER {
                         none(1),
                         c1(2),
                         c2(3),
                         c3(4),
                         c4(5),
                         c5(6),
                         c6(7),
                         c7(8),
                         c8(9),
                         c9(10),
                         c10(11),
                         c11(12),
                         c12(13),
                         l1slot1(14),
                         l1slot2(15),
                         l1slot3(16),
                         l1slot4(17),
                         l1slot5(18),
                         l1slot6(19),
                         l1slot7(20),
                         l1slot8(21),
                         l1slot9(22),
                         l1slot10(23),
                         l2slot1(24),
                         l2slot2(25),
                         l2slot3(26),
                         l2slot4(27),
                         l2slot5(28),
                         l2slot6(29),
                         l2slot7(30),
                         l2slot8(31),
                         l2slot9(32),
                         l2slot10(33)
                       }

    AluWdmPortLaserTunability ::= TEXTUAL-CONVENTION
        STATUS         current
        DESCRIPTION    "Laser tunability of this port."
        SYNTAX         INTEGER {
                         unknown(1),
                         fixed(2),
                         fixedSpecial(3),
                         fullyTunable(4),
                         semiTunable(5),
                         semiTunableBandAligned(6)
                       }

    AluWdmTimDetectionMode ::= TEXTUAL-CONVENTION
        STATUS         current
        DESCRIPTION    "TIM detection mode."
        SYNTAX         INTEGER {
                         off(1),
                         sapiOnly(2),
                         dapiOnly(3),
                         sapiAndDapiOnly(4),
                         userSpecificOnly(5),
                         userSpecificAndSapiOnly(6),
                         userSpecificAndDapiOnly(7),
                         userSpecificAndSapiAndDapi(8)
                       }

    AluWdmMappingMode ::= TEXTUAL-CONVENTION
        STATUS         current
        DESCRIPTION    "ODU2/ODU1 mapping mode."
        SYNTAX         INTEGER {
                         null(1),
                         prbs(2),
                         cbrA(3),
                         cbrB(4),
                         rsA(5),
                         rsB(6),
                         lanPhyGfp(7),
                         gmp(8)
                       }

    AluWdmOduOchSignalDefConsequenceAction ::= TEXTUAL-CONVENTION
        STATUS         current
        DESCRIPTION    "ODU2/ODU1 OCH signal def consequence action."
        SYNTAX         INTEGER {
                         none(1),
                         ais(2),
                         oduAis(3),
                         msAis(4),
                         genericAis(5),
                         lfi(6),
                         laserOff(7)
                       }

    AluWdmWTDecoderMeasurementType ::= TEXTUAL-CONVENTION
        STATUS         current
        DESCRIPTION    "Indicate the measurement source."
        SYNTAX         INTEGER {
                         wtdMeasured(1),
                         wtocmMeasured(2),
                         calculated(3),
                         unavailable(4)
                       }

    AluWdmWRConfigAddDropDisposition ::= TEXTUAL-CONVENTION
        STATUS         current
        DESCRIPTION    "Configurable Add Drop Disposition"
        SYNTAX         INTEGER {
                         adt1(1),
                         adt2(2),
                         adt3(3),
                         adt4(4),
                         adt5(5),
                         adt6(6),
                         adt7(7),
                         adt8(8),
                         ad9(9),
                         ad10(10),
                         ad11(11),
                         ad12(12),
                         ad13(13),
                         ad14(14),
                         ad15(15),
                         ad16(16),
                         ad17(17),
                         ad18(18),
                         ad19(19),
                         ad20(20),
                         notForced(21)
                       }

    AluWdmWRChannelCurrentAddDropDisposition ::= TEXTUAL-CONVENTION
        STATUS         current
        DESCRIPTION    "Current Add Drop Disposition."
        SYNTAX         INTEGER {
                         adt1(1),
                         adt2(2),
                         adt3(3),
                         adt4(4),
                         adt5(5),
                         adt6(6),
                         adt7(7),
                         adt8(8),
                         ad9(9),
                         ad10(10),
                         ad11(11),
                         ad12(12),
                         ad13(13),
                         ad14(14),
                         ad15(15),
                         ad16(16),
                         ad17(17),
                         ad18(18),
                         ad19(19),
                         ad20(20),
                         blocked(21)
                       }

    AluWdmSfdPortType ::= TEXTUAL-CONVENTION
        STATUS         current
        DESCRIPTION    "SFD Port Type."
        SYNTAX         INTEGER {
                         channel(1),
                         mux(2),
                         exp(3)
                       }

    NokiaPtpClockIdentifier ::= TEXTUAL-CONVENTION
        STATUS         current
        DESCRIPTION
        "This 64-bit extended unique identifier (EUI-64) is a constructed by
         the external MAC address of the card and the clock number in the card.
         For example, if the external MAC address is AC-DE-48-23-45-67, and the
         clock number is 0x01.  The clock identifier shall be:

           |        company_id       | fixed  |clockNum|   extension identifier  | field
           |  AC   |   DE   |   48   |   FF   |   01   |   23   |   45   |   67  | hex
           10101100 11011110 01001000 11111111 00000001 00100011 01000101 01100111 bits
           |  |                                                               |  |
           |  most-significant-byte                      least-significant-byte  |
           most-significant-bit                              least-significant-bit."

        SYNTAX         OCTET STRING (SIZE(8))

--------------------------------------------------------------------------------
-- Obsoleted OIDs
--------------------------------------------------------------------------------
--    obsolete
--    tnOpticalPortTotal        OBJECT-TYPE ::= { tnOpticalPortObjs 1 }
--    tnOC48SwsPortTotal        OBJECT-TYPE ::= { tnOpticalPortObjs 2 }
--    tnSimpleOpticsPortTotal   OBJECT-TYPE ::= { tnOpticalPortObjs 3 }
--    tnOC48SwsUserNwPortTotal  OBJECT-TYPE ::= { tnOpticalPortObjs 4 }
--    tnOC48SwsUserNwPortTable  OBJECT-TYPE ::= { tnOpticalPortObjs 5 }
--    tnBandFilterPortTotal     OBJECT-TYPE ::= { tnOpticalPortObjs 6 }
--    tnBandFilterPortTable     OBJECT-TYPE ::= { tnOpticalPortObjs 7 }
--    tnOscPortTotal            OBJECT-TYPE ::= { tnOpticalPortObjs 8 }
--    tnOscPortTable            OBJECT-TYPE ::= { tnOpticalPortObjs 9 }
--    tnChannelFilterPortTotal  OBJECT-TYPE ::= { tnOpticalPortObjs 10 }
--    tnChannelFilterPortTable  OBJECT-TYPE ::= { tnOpticalPortObjs 11 }
--    tnBbaLinePortTotal        OBJECT-TYPE ::= { tnOpticalPortObjs 12 }
--    tnBbaLinePortTable        OBJECT-TYPE ::= { tnOpticalPortObjs 13 }
--    tnPpsPortTotal            OBJECT-TYPE ::= { tnOpticalPortObjs 14 }
--    tnPpsPortTable            OBJECT-TYPE ::= { tnOpticalPortObjs 15 }
--    tnOC192SwsUserNwPortTotal OBJECT-TYPE ::= { tnOpticalPortObjs 16 }
--    tnOC192SwsUserNwPortTable OBJECT-TYPE ::= { tnOpticalPortObjs 17 }
--    tn2x1GEoSWSPortTotal      OBJECT-TYPE ::= { tnOpticalPortObjs 18 }
--    tn2x1GEoSWSPortTable      OBJECT-TYPE ::= { tnOpticalPortObjs 19 }
--    tnSonetPortTotal          OBJECT-TYPE ::= { tnOpticalPortObjs 20 }
--    tnSonetPortTable          OBJECT-TYPE ::= { tnOpticalPortObjs 21 }

--------------------------------------------------------------------------------
-- Optical Port Table
--------------------------------------------------------------------------------
    tnOpticalPortTable OBJECT-TYPE
        SYNTAX         SEQUENCE OF TnOpticalPortEntry
        MAX-ACCESS     not-accessible
        STATUS         current
        DESCRIPTION    "The ports on optical cards."
        ::= { tnOpticalPortObjs 22 }

    tnOpticalPortEntry OBJECT-TYPE
        SYNTAX         TnOpticalPortEntry
        MAX-ACCESS     not-accessible
        STATUS         current
        DESCRIPTION    "."
        INDEX { ifIndex,
                tnOpticalPortDirection }
        ::= { tnOpticalPortTable 1 }

    TnOpticalPortEntry ::=
        SEQUENCE {
            tnOpticalPortDirection     INTEGER,
            tnOpticalPortInsertionLoss Integer32
        }

    tnOpticalPortDirection OBJECT-TYPE
        SYNTAX         INTEGER {
                         out(1),
                         in(2)
                       }
        MAX-ACCESS     not-accessible
        STATUS         current
        DESCRIPTION    "The signal direction."
        ::= { tnOpticalPortEntry 1 }

    tnOpticalPortInsertionLoss OBJECT-TYPE
        SYNTAX         Integer32
        UNITS          "mB"
        MAX-ACCESS     read-only
        STATUS         current
        DESCRIPTION    "The insertion loss.  This will be supported on
                        all input to output flows."
        DEFVAL         { 840 }
        ::= { tnOpticalPortEntry 2 }

--------------------------------------------------------------------------------
-- Obsoleted OIDs
--------------------------------------------------------------------------------
--    obsolete
--    tnRoadmPortTotal   OBJECT-TYPE ::= { tnOpticalPortObjs 23 }
--    tnRoadmPortTable   OBJECT-TYPE ::= { tnOpticalPortObjs 24 }
--    tnWaveKeyPortTotal OBJECT-TYPE ::= { tnOpticalPortObjs 25 }

--------------------------------------------------------------------------------
-- Wave Key Optical Port Table
--------------------------------------------------------------------------------
    tnWaveKeyPortTable OBJECT-TYPE
        SYNTAX         SEQUENCE OF TnWaveKeyPortEntry
        MAX-ACCESS     not-accessible
        STATUS         current
        DESCRIPTION    "This table is a compilation of attributes
                        associated with the ports on a Wave Key decode
                        supported optical card."
        ::= { tnOpticalPortObjs 26 }

    tnWaveKeyPortEntry OBJECT-TYPE
        SYNTAX         TnWaveKeyPortEntry
        MAX-ACCESS     not-accessible
        STATUS         current
        DESCRIPTION    "."
        INDEX { ifIndex }
        ::= { tnWaveKeyPortTable 1 }

    TnWaveKeyPortEntry ::=
        SEQUENCE {
            tnWaveKeyPortUnexpectedWKThreshIngress          Integer32,
            tnWaveKeyPortUnexpectedWKThreshEgress           Integer32,
            tnWaveKeyPortUnexpectedWKThreshAutoModeIngress  TruthValue,
            tnWaveKeyPortUnexpectedWKThreshAutoModeEgress   TruthValue,
            tnWaveKeyPortUnexpectedWKThreshDeltaIngress     Unsigned32,
            tnWaveKeyPortUnexpectedWKThreshDeltaEgress      Unsigned32,
            tnWaveKeyPortPresentUnexpectedWKThreshIngress   Integer32,
            tnWaveKeyPortPresentUnexpectedWKThreshEgress    Integer32,
            tnWaveKeyPortSupportedDirections                INTEGER,
            tnWaveKeyPortUnexpectedWKThreshAutoMaxOffsetIn  Unsigned32,
            tnWaveKeyPortUnexpectedWKThreshAutoMaxOffsetOut Unsigned32,
            tnWaveKeyPortCommonEgressPower                  Integer32,
            tnWaveKeyPortCommonIngressPower                 Integer32,
            tnWaveKeyPortDefaultPowerDeviationIn            Unsigned32,
            tnWaveKeyPortDefaultPowerDeviationOut           Unsigned32,
            tnWaveKeyPortDefaultPowerDeviationInL           Unsigned32,
            tnWaveKeyPortDefaultPowerDeviationOutL          Unsigned32,
            tnWaveKeyPortCommonEgressPowerL                 Integer32
        }

    tnWaveKeyPortUnexpectedWKThreshIngress OBJECT-TYPE
        SYNTAX         Integer32
        UNITS          "mBm"
        MAX-ACCESS     read-create
        STATUS         current
        DESCRIPTION    "Unexpected Wave Key filtering based on power
                        level, with -9900 means no measured power.

                        Current configurable range: -9900, -3000 to 1100."
        ::= { tnWaveKeyPortEntry 1 }

    tnWaveKeyPortUnexpectedWKThreshEgress OBJECT-TYPE
        SYNTAX         Integer32
        UNITS          "mBm"
        MAX-ACCESS     read-create
        STATUS         current
        DESCRIPTION    "Unexpected Wave Key filtering based on power
                        level, with -9900 means no measured power.

                        Current configurable range: -9900, -3000 to 1100."
        ::= { tnWaveKeyPortEntry 2 }

    tnWaveKeyPortUnexpectedWKThreshAutoModeIngress OBJECT-TYPE
        SYNTAX         TruthValue
        MAX-ACCESS     read-create
        STATUS         current
        DESCRIPTION    "An indication as to whether or not unexpected
                        Wave Key filtering is automatic or manual."
        DEFVAL         { true }
        ::= { tnWaveKeyPortEntry 3 }

    tnWaveKeyPortUnexpectedWKThreshAutoModeEgress OBJECT-TYPE
        SYNTAX         TruthValue
        MAX-ACCESS     read-create
        STATUS         current
        DESCRIPTION    "An indication as to whether or not unexpected
                        Wave Key filtering is automatic or manual."
        DEFVAL         { true }
        ::= { tnWaveKeyPortEntry 4 }

    tnWaveKeyPortUnexpectedWKThreshDeltaIngress OBJECT-TYPE
        SYNTAX         Unsigned32
        UNITS          "mB"
        MAX-ACCESS     read-create
        STATUS         current
        DESCRIPTION    "Unexpected Wave Key filtering power level delta.

                        Current configurable range: 0 to 3400."
        DEFVAL         { 500 }
        ::= { tnWaveKeyPortEntry 5 }

    tnWaveKeyPortUnexpectedWKThreshDeltaEgress OBJECT-TYPE
        SYNTAX         Unsigned32
        UNITS          "mB"
        MAX-ACCESS     read-create
        STATUS         current
        DESCRIPTION    "Unexpected Wave Key filtering power level delta.

                        Current configurable range: 0 to 3400."
        DEFVAL         { 500 }
        ::= { tnWaveKeyPortEntry 6 }

    tnWaveKeyPortPresentUnexpectedWKThreshIngress OBJECT-TYPE
        SYNTAX         Integer32
        UNITS          "mBm"
        MAX-ACCESS     read-only
        STATUS         current
        DESCRIPTION    "Present unexpected Wave Key filtering power level."
        ::= { tnWaveKeyPortEntry 7 }

    tnWaveKeyPortPresentUnexpectedWKThreshEgress OBJECT-TYPE
        SYNTAX         Integer32
        UNITS          "mBm"
        MAX-ACCESS     read-only
        STATUS         current
        DESCRIPTION    "Present unexpected Wave Key filtering power level."
        ::= { tnWaveKeyPortEntry 8 }

    tnWaveKeyPortSupportedDirections OBJECT-TYPE
        SYNTAX         INTEGER {
                         in(1),
                         out(2),
                         both(3)
                       }
        MAX-ACCESS     read-only
        STATUS         current
        DESCRIPTION    "The supported directions."
        ::= { tnWaveKeyPortEntry 9 }

    tnWaveKeyPortUnexpectedWKThreshAutoMaxOffsetIn OBJECT-TYPE
        SYNTAX         Unsigned32
        UNITS          "mB"
        MAX-ACCESS     read-create
        STATUS         current
        DESCRIPTION    "This attribute will clamp the total offset from
                        the average provisioned powers to the given power
                        level (ingress).

                        Current configurable range: 0 to 3400."
        DEFVAL         { 1000 }
        ::= { tnWaveKeyPortEntry 10 }

    tnWaveKeyPortUnexpectedWKThreshAutoMaxOffsetOut OBJECT-TYPE
        SYNTAX         Unsigned32
        UNITS          "mB"
        MAX-ACCESS     read-create
        STATUS         current
        DESCRIPTION    "This attribute will clamp the total offset from
                        the average provisioned powers to the given
                        power level (egress).

                        Current configurable range: 0 to 3400."
        DEFVAL         { 1000 }
        ::= { tnWaveKeyPortEntry 11 }

    tnWaveKeyPortCommonEgressPower OBJECT-TYPE
        SYNTAX         Integer32
        UNITS          "mBm"
        MAX-ACCESS     read-create
        STATUS         current
        DESCRIPTION    "Common Egress Power.  This is the per channel
                        default egress power.

                        Current configurable range: -3000 to 1100."
        DEFVAL         { 0 }
        ::= { tnWaveKeyPortEntry 12 }

    tnWaveKeyPortCommonIngressPower OBJECT-TYPE
        SYNTAX         Integer32
        UNITS          "mBm"
        MAX-ACCESS     read-create
        STATUS         current
        DESCRIPTION    "Common Ingress Power.  This is the per channel
                        default ingress power.

                        Current configurable range: -3000 to 1100."
        DEFVAL         { -2000 }
        ::= { tnWaveKeyPortEntry 13 }

    tnWaveKeyPortDefaultPowerDeviationIn OBJECT-TYPE
        SYNTAX         Unsigned32
        UNITS          "mB"
        MAX-ACCESS     read-create
        STATUS         current
        DESCRIPTION    "EPT - Default Deviation In.

                        Current configurable range: 0 to 1000."
        DEFVAL         { 150 }
        ::= { tnWaveKeyPortEntry 14 }

    tnWaveKeyPortDefaultPowerDeviationOut OBJECT-TYPE
        SYNTAX         Unsigned32
        UNITS          "mB"
        MAX-ACCESS     read-create
        STATUS         current
        DESCRIPTION    "EPT - Default Deviation Out.

                        Current configurable range: 0 to 1000."
        DEFVAL         { 150 }
        ::= { tnWaveKeyPortEntry 15 }

    tnWaveKeyPortDefaultPowerDeviationInL OBJECT-TYPE
        SYNTAX         Unsigned32
        UNITS          "mB"
        MAX-ACCESS     read-create
        STATUS         current
        DESCRIPTION    "EPT - Default Deviation In.

                        Current configurable range: 0 to 1000."
        DEFVAL         { 150 }
        ::= { tnWaveKeyPortEntry 16 }

    tnWaveKeyPortDefaultPowerDeviationOutL OBJECT-TYPE
        SYNTAX         Unsigned32
        UNITS          "mB"
        MAX-ACCESS     read-create
        STATUS         current
        DESCRIPTION    "EPT - Default Deviation Out.

                        Current configurable range: 0 to 1000."
        DEFVAL         { 150 }
        ::= { tnWaveKeyPortEntry 17 }

    tnWaveKeyPortCommonEgressPowerL OBJECT-TYPE
        SYNTAX         Integer32
        UNITS          "mBm"
        MAX-ACCESS     read-create
        STATUS         current
        DESCRIPTION    "Common Egress Power.  This is the per channel
                        default egress power.

                        Current configurable range: -3000 to 1100."
        DEFVAL         { 0 }
        ::= { tnWaveKeyPortEntry 18 }

--------------------------------------------------------------------------------
-- Obsoleted OIDs
--------------------------------------------------------------------------------
--    obsolete
--    tn10GELANPortTotal OBJECT-TYPE ::= { tnOpticalPortObjs 27 }
--    tn10GELANPortTable OBJECT-TYPE ::= { tnOpticalPortObjs 28 }

--------------------------------------------------------------------------------
-- Optical Fiber Table
--------------------------------------------------------------------------------
    tnOpticalFiberTable OBJECT-TYPE
        SYNTAX         SEQUENCE OF TnOpticalFiberEntry
        MAX-ACCESS     not-accessible
        STATUS         current
        DESCRIPTION    "Per port optical fiber characteristics."
        ::= { tnOpticalPortObjs 29 }

    tnOpticalFiberEntry OBJECT-TYPE
        SYNTAX         TnOpticalFiberEntry
        MAX-ACCESS     not-accessible
        STATUS         current
        DESCRIPTION    "."
        INDEX { ifIndex }
        ::= { tnOpticalFiberTable 1 }

    TnOpticalFiberEntry ::=
        SEQUENCE {
            tnOpticalFiberFixedLoss        Integer32,
            tnOpticalFiberLength           Integer32,
            tnOpticalFiberLossRating       Integer32,
            tnOpticalFiberDispersionRating Integer32
        }

    tnOpticalFiberFixedLoss OBJECT-TYPE
        SYNTAX         Integer32
        UNITS          "mB"
        MAX-ACCESS     read-create
        STATUS         current
        DESCRIPTION    "Current configurable range: -10000 to 100."
        DEFVAL         { 100 }
        ::= { tnOpticalFiberEntry 1 }

    tnOpticalFiberLength OBJECT-TYPE
        SYNTAX         Integer32
        UNITS          "km"
        MAX-ACCESS     read-create
        STATUS         current
        DESCRIPTION    "Current configurable range: -1 to 1000."
        DEFVAL         { -1 }
        ::= { tnOpticalFiberEntry 2 }

    tnOpticalFiberLossRating OBJECT-TYPE
        SYNTAX         Integer32
        UNITS          "mB/km"
        MAX-ACCESS     read-create
        STATUS         current
        DESCRIPTION    "Current configurable range: -10000 to 100."
        DEFVAL         { 100 }
        ::= { tnOpticalFiberEntry 3 }

    tnOpticalFiberDispersionRating OBJECT-TYPE
        SYNTAX         Integer32
        UNITS          "ps/(nm*km)"
        MAX-ACCESS     read-create
        STATUS         current
        DESCRIPTION    "Current configurable range: -1 to 1000."
        DEFVAL         { -1 }
        ::= { tnOpticalFiberEntry 4 }

--------------------------------------------------------------------------------
-- Obsoleted OIDs
--------------------------------------------------------------------------------
--    obsolete
--    tnChannelAddDropPortTotal OBJECT-TYPE ::= { tnOpticalPortObjs 30 }
--    tnChannelAddDropPortTable OBJECT-TYPE ::= { tnOpticalPortObjs 31 }
--    tnQuadOC48MuxPortTotal    OBJECT-TYPE ::= { tnOpticalPortObjs 32 }
--    tnQuadOC48MuxPortTable    OBJECT-TYPE ::= { tnOpticalPortObjs 33 }
--    tnBbaLowGainPortTotal     OBJECT-TYPE ::= { tnOpticalPortObjs 34 }
--    tnBbaLowGainPortTable     OBJECT-TYPE ::= { tnOpticalPortObjs 35 }

--------------------------------------------------------------------------------
-- Loopback Port Table
--------------------------------------------------------------------------------
    tnLoopbackPortTable OBJECT-TYPE
        SYNTAX         SEQUENCE OF TnLoopbackPortEntry
        MAX-ACCESS     not-accessible
        STATUS         current
        DESCRIPTION    "This table is a compilation of attributes
                        associated with the ports on loopback supported
                        optical cards."
        ::= { tnOpticalPortObjs 36 }

    tnLoopbackPortEntry OBJECT-TYPE
        SYNTAX         TnLoopbackPortEntry
        MAX-ACCESS     not-accessible
        STATUS         current
        DESCRIPTION    "."
        INDEX { ifIndex }
        ::= { tnLoopbackPortTable 1 }

    TnLoopbackPortEntry ::=
        SEQUENCE {
            tnLoopbackPortDLEB       TruthValue,
            tnLoopbackPortLLEB       TruthValue,
            tnLoopbackPortTSEB       TruthValue,
            tnLoopbackPortFacTwo     TruthValue
        }

    tnLoopbackPortDLEB OBJECT-TYPE
        SYNTAX         TruthValue
        MAX-ACCESS     read-create
        STATUS         current
        DESCRIPTION    "Terminal Loopback, also known as diagnostic loopback."
        DEFVAL         { false }
        ::= { tnLoopbackPortEntry 1 }

    tnLoopbackPortLLEB OBJECT-TYPE
        SYNTAX         TruthValue
        MAX-ACCESS     read-create
        STATUS         current
        DESCRIPTION    "Facility Loopback, also known as line loopback."
        DEFVAL         { false }
        ::= { tnLoopbackPortEntry 2 }

    tnLoopbackPortTSEB OBJECT-TYPE
        SYNTAX         TruthValue
        MAX-ACCESS     read-create
        STATUS         current
        DESCRIPTION    "Test signal generator."
        DEFVAL         { false }
        ::= { tnLoopbackPortEntry 3 }

    tnLoopbackPortFacTwo OBJECT-TYPE
        SYNTAX         TruthValue
        MAX-ACCESS     read-create
        STATUS         current
        DESCRIPTION    "."
        DEFVAL         { false }
        ::= { tnLoopbackPortEntry 4 }

--------------------------------------------------------------------------------
-- Obsoleted OIDs
--------------------------------------------------------------------------------
--    obsolete
--    tnDcmPortTotal OBJECT-TYPE ::= { tnOpticalPortObjs 37 }
--    tnDcmPortTable OBJECT-TYPE ::= { tnOpticalPortObjs 38 }

--------------------------------------------------------------------------------
-- Insertion Loss Port Table
--------------------------------------------------------------------------------
    tnInsertionLossPortTable OBJECT-TYPE
        SYNTAX         SEQUENCE OF TnInsertionLossPortEntry
        MAX-ACCESS     not-accessible
        STATUS         current
        DESCRIPTION    "This table provides the same information as
                        tnOpticalPortTable, but with a different index."
        ::= { tnOpticalPortObjs 39 }

    tnInsertionLossPortEntry OBJECT-TYPE
        SYNTAX         TnInsertionLossPortEntry
        MAX-ACCESS     not-accessible
        STATUS         current
        DESCRIPTION    "."
        INDEX { ifIndex }
        ::= { tnInsertionLossPortTable 1 }

    TnInsertionLossPortEntry ::=
        SEQUENCE {
            tnInsertionLossPortEgress       Integer32,
            tnInsertionLossPortIngress      Integer32,
            tnInsertionLossPortEgressL      Integer32,
            tnInsertionLossPortIngressL     Integer32
        }

    tnInsertionLossPortEgress OBJECT-TYPE
        SYNTAX         Integer32
        UNITS          "mB"
        MAX-ACCESS     read-only
        STATUS         current
        DESCRIPTION    "The egress insertion loss."
        ::= { tnInsertionLossPortEntry 1 }

    tnInsertionLossPortIngress OBJECT-TYPE
        SYNTAX         Integer32
        UNITS          "mB"
        MAX-ACCESS     read-only
        STATUS         current
        DESCRIPTION    "The ingress insertion loss."
        ::= { tnInsertionLossPortEntry 2 }

    tnInsertionLossPortEgressL OBJECT-TYPE
        SYNTAX         Integer32
        UNITS          "mB"
        MAX-ACCESS     read-only
        STATUS         current
        DESCRIPTION    "The egress insertion loss L Band."
        ::= { tnInsertionLossPortEntry 3 }

    tnInsertionLossPortIngressL OBJECT-TYPE
        SYNTAX         Integer32
        UNITS          "mB"
        MAX-ACCESS     read-only
        STATUS         current
        DESCRIPTION    "The ingress insertion loss L Band."
        ::= { tnInsertionLossPortEntry 4 }

--------------------------------------------------------------------------------
-- Obsoleted OIDs
--------------------------------------------------------------------------------
--    obsolete
--    tnQuadOC3or12MuxPortTotal OBJECT-TYPE ::= { tnOpticalPortObjs 40 }
--    tnQuadOC3or12MuxPortTable OBJECT-TYPE ::= { tnOpticalPortObjs 41 }
--    tnDecaGigEMuxPortTotal    OBJECT-TYPE ::= { tnOpticalPortObjs 42 }
--    tnDecaGigEMuxPortTable    OBJECT-TYPE ::= { tnOpticalPortObjs 43 }

--------------------------------------------------------------------------------
-- Protection Group Optical Port Table
--------------------------------------------------------------------------------
    tnProtectionGroupPortTable OBJECT-TYPE
        SYNTAX         SEQUENCE OF TnProtectionGroupPortEntry
        MAX-ACCESS     not-accessible
        STATUS         current
        DESCRIPTION    "."
        ::= { tnOpticalPortObjs 44 }

    tnProtectionGroupPortEntry OBJECT-TYPE
        SYNTAX         TnProtectionGroupPortEntry
        MAX-ACCESS     not-accessible
        STATUS         current
        DESCRIPTION    "."
        INDEX { ifIndex }
        ::= { tnProtectionGroupPortTable 1 }

    TnProtectionGroupPortEntry ::=
        SEQUENCE {
            tnProtectionGroupId TnApsGroupId
        }

    tnProtectionGroupId OBJECT-TYPE
        SYNTAX         TnApsGroupId
        MAX-ACCESS     read-only
        STATUS         current
        DESCRIPTION    "The APS group ID."
        DEFVAL         { 0 }
        ::= { tnProtectionGroupPortEntry 1 }

--------------------------------------------------------------------------------
-- Decision Threshold Voltage (DTV) Port Table
--------------------------------------------------------------------------------
    tnDTVPortTable OBJECT-TYPE
        SYNTAX         SEQUENCE OF TnDTVPortEntry
        MAX-ACCESS     not-accessible
        STATUS         current
        DESCRIPTION    "."
        ::= { tnOpticalPortObjs 45 }

    tnDTVPortEntry OBJECT-TYPE
        SYNTAX         TnDTVPortEntry
        MAX-ACCESS     not-accessible
        STATUS         current
        DESCRIPTION    "."
        INDEX { ifIndex }
        ::= { tnDTVPortTable 1 }

    TnDTVPortEntry ::=
        SEQUENCE {
            tnDTVPortControl            AluWdmEnabledDisabled,
            tnDTVPortValueAmplitude     Integer32,
            tnDTVPortValuePhase         Integer32
        }

    tnDTVPortControl OBJECT-TYPE
        SYNTAX         AluWdmEnabledDisabled
        MAX-ACCESS     read-create
        STATUS         current
        DESCRIPTION    "When this is set to disabled, the DTV amplitude
                        will be reset to the default value."
        DEFVAL         { enabled }
        ::= { tnDTVPortEntry 1 }

    tnDTVPortValueAmplitude OBJECT-TYPE
        SYNTAX         Integer32
        MAX-ACCESS     read-only
        STATUS         current
        DESCRIPTION    "Reports the current DTV amplitude value.  If the
                        module is not present, it returns -1.

                        Current range: -1 to 100."
        DEFVAL         { -1 }
        ::= { tnDTVPortEntry 2 }

    tnDTVPortValuePhase OBJECT-TYPE
        SYNTAX         Integer32
        MAX-ACCESS     read-only
        STATUS         current
        DESCRIPTION    "Reports the current DTV phase value.  If the module
                        is not present, it returns -1.

                        Current range: -1 to 100."
        DEFVAL         { -1 }
        ::= { tnDTVPortEntry 3 }

--------------------------------------------------------------------------------
-- Port Inventory Table
--------------------------------------------------------------------------------
    tnPortInventoryTable OBJECT-TYPE
        SYNTAX         SEQUENCE OF TnPortInventoryEntry
        MAX-ACCESS     not-accessible
        STATUS         current
        DESCRIPTION    "."
        ::= { tnOpticalPortObjs 46 }

    tnPortInventoryEntry OBJECT-TYPE
        SYNTAX         TnPortInventoryEntry
        MAX-ACCESS     not-accessible
        STATUS         current
        DESCRIPTION    "."
        INDEX { ifIndex }
        ::= { tnPortInventoryTable 1 }

    TnPortInventoryEntry ::= SEQUENCE {
        tnPortInventoryCLEI                     TropicCardCLEI,
        tnPortInventoryCompanyID                SnmpAdminString,
        tnPortInventoryDate                     SnmpAdminString,
        tnPortInventoryExtraData                SnmpAdminString,
        tnPortInventoryFactoryID                SnmpAdminString,
        tnPortInventoryManufacturingPartNumber  TropicCardManufacturingPartNumber,
        tnPortInventoryMnemonic                 SnmpAdminString,
        tnPortInventorySerialNumber             TropicCardSerialNumber,
        tnPortInventorySWPartNumber             SnmpAdminString
    }

    tnPortInventoryCLEI OBJECT-TYPE
        SYNTAX         TropicCardCLEI
        MAX-ACCESS     read-only
        STATUS         current
        DESCRIPTION    "."
        DEFVAL         { "" }
        ::= { tnPortInventoryEntry 1 }

    tnPortInventoryCompanyID OBJECT-TYPE
        SYNTAX         SnmpAdminString
        MAX-ACCESS     read-only
        STATUS         current
        DESCRIPTION    "."
        DEFVAL         { "" }
        ::= { tnPortInventoryEntry 2 }

    tnPortInventoryDate OBJECT-TYPE
        SYNTAX         SnmpAdminString
        MAX-ACCESS     read-only
        STATUS         current
        DESCRIPTION    "."
        DEFVAL         { "" }
        ::= { tnPortInventoryEntry 3 }

    tnPortInventoryExtraData OBJECT-TYPE
        SYNTAX         SnmpAdminString
        MAX-ACCESS     read-only
        STATUS         current
        DESCRIPTION    "."
        DEFVAL         { "" }
        ::= { tnPortInventoryEntry 4 }

    tnPortInventoryFactoryID OBJECT-TYPE
        SYNTAX         SnmpAdminString
        MAX-ACCESS     read-only
        STATUS         current
        DESCRIPTION    "."
        DEFVAL         { "" }
        ::= { tnPortInventoryEntry 5 }

    tnPortInventoryManufacturingPartNumber OBJECT-TYPE
        SYNTAX         TropicCardManufacturingPartNumber
        MAX-ACCESS     read-only
        STATUS         current
        DESCRIPTION    "."
        DEFVAL         { "" }
        ::= { tnPortInventoryEntry 6 }

    tnPortInventoryMnemonic OBJECT-TYPE
        SYNTAX         SnmpAdminString
        MAX-ACCESS     read-only
        STATUS         current
        DESCRIPTION    "."
        DEFVAL         { "" }
        ::= { tnPortInventoryEntry 7 }

    tnPortInventorySerialNumber OBJECT-TYPE
        SYNTAX         TropicCardSerialNumber
        MAX-ACCESS     read-only
        STATUS         current
        DESCRIPTION    "."
        DEFVAL         { "" }
        ::= { tnPortInventoryEntry 8 }

    tnPortInventorySWPartNumber OBJECT-TYPE
        SYNTAX         SnmpAdminString
        MAX-ACCESS     read-only
        STATUS         current
        DESCRIPTION    "."
        DEFVAL         { "" }
        ::= { tnPortInventoryEntry 9 }

--------------------------------------------------------------------------------
-- OTDR (Optical Time Domain Reflectometer) Port Scan Table
--------------------------------------------------------------------------------
    tnPortOtdrScanTable OBJECT-TYPE
        SYNTAX         SEQUENCE OF TnPortOtdrScanEntry
        MAX-ACCESS     not-accessible
        STATUS         current
        DESCRIPTION    "OTDR scan attributes."
        ::= { tnOpticalPortObjs 47 }

    tnPortOtdrScanEntry OBJECT-TYPE
        SYNTAX         TnPortOtdrScanEntry
        MAX-ACCESS     not-accessible
        STATUS         current
        DESCRIPTION    "."
        INDEX { ifIndex }
        ::= { tnPortOtdrScanTable 1 }

    TnPortOtdrScanEntry ::=
        SEQUENCE {
            tnPortOtdrScanProfileId                Integer32,
            tnPortOtdrScanDescription              SnmpAdminString,
            tnPortOtdrScanWaveLength               Unsigned32,
            tnPortOtdrScanPulseLength              Unsigned32,
            tnPortOtdrScanRange                    Unsigned32,
            tnPortOtdrScanResolution               Unsigned32,
            tnPortOtdrScanAvgTime                  Unsigned32,
            tnPortOtdrScanConnAddress              Integer32,
            tnPortOtdrScanFileName                 SnmpAdminString,
            tnPortOtdrScanControl                  INTEGER,
            tnPortOtdrScanStatus                   INTEGER,
            tnPortOtdrScanResult                   INTEGER,
            tnPortOtdrScanTimeRemaining            Unsigned32,
            tnPortOtdrScanLastSuccessfulTimeStamp  Unsigned32,
            tnPortOtdrScanEventThreshold           Unsigned32,
            tnPortOtdrScanIOR                      Unsigned32,
            tnPortOtdrScanState                    INTEGER,
            tnPortOtdrScanErrorType                SnmpAdminString,
            tnPortOtdrScanErrorDetail              SnmpAdminString,
            tnPortOtdrScanRequestTimeStamp         Unsigned32
        }
    tnPortOtdrScanProfileId OBJECT-TYPE
        SYNTAX         Integer32
        MAX-ACCESS     read-create
        STATUS         current
        DESCRIPTION    "Profile Id to be used for the scan.

                        Current configurable range: 1 to 16.

                        After selecting a profile Id, if user tries to
                        change any of the parameter, profile id changes
                        to -1."
        DEFVAL         { 1 }
        ::= { tnPortOtdrScanEntry 1 }

    tnPortOtdrScanDescription OBJECT-TYPE
        SYNTAX         SnmpAdminString (SIZE(0..64))
        MAX-ACCESS     read-create
        STATUS         current
        DESCRIPTION    "Describes the different settings for
                        the scan."
        ::= { tnPortOtdrScanEntry 2 }

    tnPortOtdrScanWaveLength OBJECT-TYPE
        SYNTAX         Unsigned32
        UNITS          "nanometers"
        MAX-ACCESS     read-create
        STATUS         current
        DESCRIPTION    "The wavelength used for the OTDR scan.  The
                        wavelength is 1610 nm, and is not configurable."
        DEFVAL         { 1610 }
        ::= { tnPortOtdrScanEntry 3 }

    tnPortOtdrScanPulseLength OBJECT-TYPE
        SYNTAX         Unsigned32
        UNITS          "nanoseconds"
        MAX-ACCESS     read-create
        STATUS         current
        DESCRIPTION    "Pulse length.

                        Current configurable values: 5, 10, 30, 100,
                          300, 1000, 3000, 10000, and 20000."
        DEFVAL         { 300 }
        ::= { tnPortOtdrScanEntry 4 }

    tnPortOtdrScanRange OBJECT-TYPE
        SYNTAX         Unsigned32
        UNITS          "meters"
        MAX-ACCESS     read-create
        STATUS         current
        DESCRIPTION    "The range of the span that is being probed
                        in meters.

                        Current configurable values: 100, 500, 1000, 2000,
                          5000, 10000, 20000, 40000,80000, and 260000."
        DEFVAL         { 260000 }
        ::= { tnPortOtdrScanEntry 5 }

    tnPortOtdrScanResolution OBJECT-TYPE
        SYNTAX         Unsigned32
        UNITS          "centimeters"
        MAX-ACCESS     read-create
        STATUS         current
        DESCRIPTION    "Distance resolution of the OTDR scan.

                        Current configurable values are 4, 8, 16,
                        32, 64, 120, 250, 500, 1000, 2000, 4000,
                        8000 and 16000 centimeters."
        DEFVAL         { 250 }
        ::= { tnPortOtdrScanEntry 6 }

    tnPortOtdrScanAvgTime OBJECT-TYPE
        SYNTAX         Unsigned32 (5..300)
        UNITS          "seconds"
        MAX-ACCESS     read-create
        STATUS         current
        DESCRIPTION    "Signal averaging time for a scan.

                        Current configurable range: 5 to 300."
        DEFVAL         { 180 }
        ::= { tnPortOtdrScanEntry 7 }

    tnPortOtdrScanConnAddress OBJECT-TYPE
        SYNTAX         Integer32 (-1..2147483647)
        MAX-ACCESS     read-only
        STATUS         current
        DESCRIPTION    "Specifies the assigned OTDR port that is connected to
                        the LD port."
        ::= { tnPortOtdrScanEntry 8 }

    tnPortOtdrScanFileName OBJECT-TYPE
        SYNTAX         SnmpAdminString (SIZE(0..25))
        MAX-ACCESS     read-create
        STATUS         current
        DESCRIPTION    "Name of the file to be used for scan.  If not provided,
                        last filename will be used.  The filename needs to be
                        alphanumeric."
        DEFVAL         { "" }
        ::= { tnPortOtdrScanEntry 9 }

    tnPortOtdrScanControl OBJECT-TYPE
        SYNTAX         INTEGER {
                         noCmd(1),
                         abort(2),
                         start(3)
                       }
        MAX-ACCESS     read-create
        STATUS         current
        DESCRIPTION    "Different states of scan."
        DEFVAL         { noCmd }
        ::= { tnPortOtdrScanEntry 10 }

    tnPortOtdrScanStatus OBJECT-TYPE
        SYNTAX         INTEGER {
                         available(1),
                         busy(2)
                       }
        MAX-ACCESS     read-only
        STATUS         current
        DESCRIPTION    "Current Scan status.

                          available: Available for use.
                          busy:      Scan is already running on the connected OTDR."
        ::= { tnPortOtdrScanEntry 11 }

    tnPortOtdrScanResult OBJECT-TYPE
        SYNTAX         INTEGER {
                         noScan(1),
                         fail(2),
                         inprogress(3),
                         abort(4),
                         complete(5)
                       }
        MAX-ACCESS     read-only
        STATUS         current
        DESCRIPTION    "Most recent scan Results for the LD Port.

                          noScan:     No scan result is available.
                          fail:       Last scan failed.
                          inprogress: Last scan not completed yet.
                          abort:      Last scan aborted.
                          complete:   Last scan completed successfully."
        DEFVAL         { noScan }
        ::= { tnPortOtdrScanEntry 12 }

    tnPortOtdrScanTimeRemaining OBJECT-TYPE
        SYNTAX         Unsigned32
        UNITS          "seconds"
        MAX-ACCESS     read-only
        STATUS         current
        DESCRIPTION    "Time remaining for scan to complete. It should not
                        exceed maximum scan time (300 seconds)."
        ::= { tnPortOtdrScanEntry 13 }

    tnPortOtdrScanLastSuccessfulTimeStamp OBJECT-TYPE
        SYNTAX         Unsigned32
        MAX-ACCESS     read-only
        STATUS         current
        DESCRIPTION    "The date and time when the last OTDR scan was successful."
        DEFVAL         { 0 }
        ::= { tnPortOtdrScanEntry 14 }

    tnPortOtdrScanEventThreshold OBJECT-TYPE
        SYNTAX         Unsigned32
        UNITS          "dB"
        MAX-ACCESS     read-create
        STATUS         current
        DESCRIPTION    "Otdr Scan Event Threshold."
        ::= { tnPortOtdrScanEntry 15 }

    tnPortOtdrScanIOR OBJECT-TYPE
        SYNTAX         Unsigned32
        MAX-ACCESS     read-create
        STATUS         current
        DESCRIPTION    "."
        ::= { tnPortOtdrScanEntry 16 }

    tnPortOtdrScanState OBJECT-TYPE
        SYNTAX         INTEGER {
                         running(1),
                         pending(2),
                         complete(3),
                         notApplicable(4),
                         abort(5)
                       }
        MAX-ACCESS     read-only
        STATUS         current
        DESCRIPTION    "Displays the state of the OTDR to which this port is
                        connected:
                          running:  The OTDR is currently performing an OTDR
                                    trace on the selected port.
                          pending:  The OTDR is pending underlying resources
                                    being available.
                          complete: The OTDR trace has completed."
        ::= { tnPortOtdrScanEntry 17 }

    tnPortOtdrScanErrorType OBJECT-TYPE
        SYNTAX         SnmpAdminString (SIZE(0..64))
        MAX-ACCESS     read-only
        STATUS         current
        DESCRIPTION    "Error Type Category:
                          unknown       : Error that causes the scan to be rejected
                          alreadyIssued : Scan is already in progress on the port
                          hardwareFailed: Card failure."
        ::= { tnPortOtdrScanEntry 18 }

    tnPortOtdrScanErrorDetail OBJECT-TYPE
        SYNTAX         SnmpAdminString (SIZE(0..64))
        MAX-ACCESS     read-only
        STATUS         current
        DESCRIPTION    "."
        ::= { tnPortOtdrScanEntry 19 }

    tnPortOtdrScanRequestTimeStamp OBJECT-TYPE
        SYNTAX         Unsigned32
        MAX-ACCESS     read-only
        STATUS         current
        DESCRIPTION    "The date and time when the OTDR scan was launched."
        ::= { tnPortOtdrScanEntry 20 }

--------------------------------------------------------------------------------
-- FLEX Grid OTS Info Table
--------------------------------------------------------------------------------
    tnFlexgridOtsInfoTable OBJECT-TYPE
        SYNTAX         SEQUENCE OF TnFlexgridOtsInfoEntry
        MAX-ACCESS     not-accessible
        STATUS         current
        DESCRIPTION    "."
        ::= { tnOpticalPortObjs 48 }

    tnFlexgridOtsInfoEntry OBJECT-TYPE
        SYNTAX         TnFlexgridOtsInfoEntry
        MAX-ACCESS     not-accessible
        STATUS         current
        DESCRIPTION    "."
        INDEX { ifIndex }
        ::= { tnFlexgridOtsInfoTable 1 }

    TnFlexgridOtsInfoEntry ::=
        SEQUENCE {
            tnFlexgridOtsInfoLineGranularityMHz                     Unsigned32,
            tnFlexgridOtsInfoCBandLowestFrequencyGHzOut             Unsigned32,
            tnFlexgridOtsInfoCBandHighestFrequencyGHzOut            Unsigned32,
            tnFlexgridOtsInfoCBandLowestFrequencyGHzIn              Unsigned32,
            tnFlexgridOtsInfoCBandHighestFrequencyGHzIn             Unsigned32,
            tnFlexgridOtsInfoLBandLowestFrequencyGHzOut             Unsigned32,
            tnFlexgridOtsInfoLBandHighestFrequencyGHzOut            Unsigned32,
            tnFlexgridOtsInfoLBandLowestFrequencyGHzIn              Unsigned32,
            tnFlexgridOtsInfoLBandHighestFrequencyGHzIn             Unsigned32,
            tnFlexgridOtsInfoChannelMonitoringAllowsOffGridOut      TruthValue,
            tnFlexgridOtsInfoChannelMonitoringAllowsOffGridIn       TruthValue,
            tnFlexgridOtsInfoLineWssIsFlexgrid                      TruthValue,
            tnFlexgridOtsInfoLineMinMSlicesPerXc                    Unsigned32,
            tnFlexgridOtsInfoLineMaxMSlicesPerXc                    Unsigned32,
            tnFlexgridOtsInfoOadmDgeSupportedBands                  INTEGER,
            tnFlexgridOtsInfoChannelMonitoringAllowsOffGridOutL     TruthValue,
            tnFlexgridOtsInfoChannelMonitoringAllowsOffGridInL      TruthValue,
            tnFlexgridOtsInfoLineWssIsFlexgridL                     TruthValue,
            tnFlexgridOtsInfoLineGranularityMHzL                    Unsigned32,
            tnFlexgridOtsInfoLineMinMSlicesPerXcL                   Unsigned32,
            tnFlexgridOtsInfoLineMaxMSlicesPerXcL                   Unsigned32,
            tnFlexgridOtsInfoDcmExistsOut                           TruthValue,
            tnFlexgridOtsInfoDcmExistsIn                            TruthValue,
            tnFlexgridOtsInfoLineGranularityMHzIn                   Unsigned32,
            tnFlexgridOtsInfoLineGranularityMHzInL                  Unsigned32,
            tnFlexgridOtsInfoLineMinMSlicesPerXcIn                  Unsigned32,
            tnFlexgridOtsInfoLineMinMSlicesPerXcInL                 Unsigned32
    }

    tnFlexgridOtsInfoLineGranularityMHz OBJECT-TYPE
        SYNTAX         Unsigned32 (0..100000)
        UNITS          "MHz"
        MAX-ACCESS     read-only
        STATUS         current
        DESCRIPTION    "Indicates the granularity (minimum slice size multiple)
                        of the optical line Wavelength Selective Switch.

                        If tnFlexgridOtsInfoLineWssIsFlexgrid is true, the upper
                        frequency edge of a slice aligns with reference
                        193.1 THz for n=0 (ITU G.694.1).

                        If tnFlexgridOtsInfoLineWssIsFlexgrid is false, the granularity
                        is the channel slot width centered on the regular ITU grid implied
                        by the granularity.

                        Values in MHz. Should be displayed in user interfaces in GHz."
        DEFVAL         { 0 }
        ::= { tnFlexgridOtsInfoEntry 1 }

    tnFlexgridOtsInfoCBandLowestFrequencyGHzOut OBJECT-TYPE
        SYNTAX         Unsigned32 (0..200000)
        UNITS          "GHz"
        MAX-ACCESS     read-only
        STATUS         current
        DESCRIPTION    "The lowest C-Band optical frequency that can
                        pass through the OTS in tx direction. Signals must
                        fit between this minimum and the maximum frequency.
                        Units of GHz. Value of 0 indicates line topology is
                        incomplete."
        DEFVAL         { 0 }
        ::= { tnFlexgridOtsInfoEntry 2 }

    tnFlexgridOtsInfoCBandHighestFrequencyGHzOut OBJECT-TYPE
        SYNTAX         Unsigned32 (0..200000)
        UNITS          "GHz"
        MAX-ACCESS     read-only
        STATUS         current
        DESCRIPTION    "The highest C-Band optical frequency that can
                        pass through the OTS in tx direction. Signals must
                        fit between this minimum and the maximum frequency.
                        Units of GHz. Value of 0 indicates line topology is
                        incomplete."
        DEFVAL         { 0 }
        ::= { tnFlexgridOtsInfoEntry 3 }

    tnFlexgridOtsInfoCBandLowestFrequencyGHzIn OBJECT-TYPE
        SYNTAX         Unsigned32 (0..200000)
        UNITS          "GHz"
        MAX-ACCESS     read-only
        STATUS         current
        DESCRIPTION    "The lowest C-Band optical frequency that can
                        pass through the OTS in tx direction. Signals must
                        fit between this minimum and the maximum frequency.
                        Units of GHz. Value of 0 indicates line topology is
                        incomplete."
        DEFVAL         { 0 }
        ::= { tnFlexgridOtsInfoEntry 4 }

    tnFlexgridOtsInfoCBandHighestFrequencyGHzIn OBJECT-TYPE
        SYNTAX         Unsigned32 (0..200000)
        UNITS          "GHz"
        MAX-ACCESS     read-only
        STATUS         current
        DESCRIPTION    "The highest C-Band optical frequency that can
                        pass through the OTS in tx direction. Signals must
                        fit between this minimum and the maximum frequency.
                        Units of GHz. Value of 0 indicates line topology is
                        incomplete."
        DEFVAL         { 0 }
        ::= { tnFlexgridOtsInfoEntry 5 }

    tnFlexgridOtsInfoLBandLowestFrequencyGHzOut OBJECT-TYPE
        SYNTAX         Unsigned32 (0..200000)
        UNITS          "GHz"
        MAX-ACCESS     read-only
        STATUS         current
        DESCRIPTION    "The lowest L-Band optical frequency that can
                        pass through the OTS in tx direction. Signals must
                        fit between this minimum and the maximum frequency.
                        Units of GHz. Value of 0 indicates line topology is
                        incomplete."
        DEFVAL         { 0 }
        ::= { tnFlexgridOtsInfoEntry 6 }

    tnFlexgridOtsInfoLBandHighestFrequencyGHzOut OBJECT-TYPE
        SYNTAX         Unsigned32 (0..200000)
        UNITS          "GHz"
        MAX-ACCESS     read-only
        STATUS         current
        DESCRIPTION    "The Highest L-Band optical frequency that can
                        pass through the OTS in tx direction. Signals must
                        fit between this minimum and the maximum frequency.
                        Units of GHz. Value of 0 indicates line topology is
                        incomplete."
        DEFVAL         { 0 }
        ::= { tnFlexgridOtsInfoEntry 7 }

    tnFlexgridOtsInfoLBandLowestFrequencyGHzIn OBJECT-TYPE
        SYNTAX         Unsigned32 (0..200000)
        UNITS          "GHz"
        MAX-ACCESS     read-only
        STATUS         current
        DESCRIPTION    "The lowest L-Band optical frequency that can
                        pass through the OTS in rx direction. Signals must
                        fit between this minimum and the maximum frequency.
                        Units of GHz. Value of 0 indicates line topology is
                        incomplete."
        DEFVAL         { 0 }
        ::= { tnFlexgridOtsInfoEntry 8 }

    tnFlexgridOtsInfoLBandHighestFrequencyGHzIn OBJECT-TYPE
        SYNTAX         Unsigned32 (0..200000)
        UNITS          "GHz"
        MAX-ACCESS     read-only
        STATUS         current
        DESCRIPTION    "The Highest L-Band optical frequency that can
                        pass through the OTS in rx direction. Signals must
                        fit between this minimum and the maximum frequency.
                        Units of GHz. Value of 0 indicates line topology is
                        incomplete."
        DEFVAL         { 0 }
        ::= { tnFlexgridOtsInfoEntry 9 }

    tnFlexgridOtsInfoChannelMonitoringAllowsOffGridOut OBJECT-TYPE
        SYNTAX         TruthValue
        MAX-ACCESS     read-only
        STATUS         current
        DESCRIPTION    "Indicates if line channel monitoring for the tx
                        direction allows flexgrid off regular grid channels."
        DEFVAL         { false }
        ::= { tnFlexgridOtsInfoEntry 10 }

    tnFlexgridOtsInfoChannelMonitoringAllowsOffGridIn OBJECT-TYPE
        SYNTAX         TruthValue
        MAX-ACCESS     read-only
        STATUS         current
        DESCRIPTION    "Indicates if line channel monitoring for the rx
                        direction allows flexgrid off regular grid channels."
        DEFVAL         { false }
        ::= { tnFlexgridOtsInfoEntry 11 }

    tnFlexgridOtsInfoLineWssIsFlexgrid OBJECT-TYPE
        SYNTAX         TruthValue
        MAX-ACCESS     read-only
        STATUS         current
        DESCRIPTION    "Indicates if the type of Wavelength Selective Switch
                        in the optical line supports flexible frequency slices."
        DEFVAL         { false }
        ::= { tnFlexgridOtsInfoEntry 12 }

    tnFlexgridOtsInfoLineMinMSlicesPerXc OBJECT-TYPE
        SYNTAX         Unsigned32 (0..6)
        MAX-ACCESS     read-only
        STATUS         current
        DESCRIPTION    "Indicates the minimum number of 12.5 GHz slices that
                        can be used to enter an OCh cross-connect on this optical
                        line.

                        E.g. value of 4 equals 50.0 GHz cross-connect width.

                        Value of 0 indicates line topology is incomplete."
        DEFVAL         { 0 }
        ::= { tnFlexgridOtsInfoEntry 13 }

    tnFlexgridOtsInfoLineMaxMSlicesPerXc OBJECT-TYPE
        SYNTAX         Unsigned32 (0..6)
        MAX-ACCESS     read-only
        STATUS         current
        DESCRIPTION    "Indicates the minimum number of 12.5 GHz slices that
                        can be used to enter an OCh cross-connect on this optical
                        line.

                        E.g. value of 4 equals 50.0 GHz cross-connect width.

                        Value of 0 indicates line topology is incomplete."
        DEFVAL         { 0 }
        ::= { tnFlexgridOtsInfoEntry 14 }

    tnFlexgridOtsInfoOadmDgeSupportedBands OBJECT-TYPE
        SYNTAX         INTEGER {
                         noneBand(1),
                         cBandOnly(2),
                         lBandOnly(3),
                         cAndLBand(4)
                       }
        MAX-ACCESS     read-only
        STATUS         current
        DESCRIPTION    "Indicates if C band, L band, or both is present"
        DEFVAL         { noneBand }
        ::= { tnFlexgridOtsInfoEntry 15 }

    tnFlexgridOtsInfoChannelMonitoringAllowsOffGridOutL OBJECT-TYPE
        SYNTAX         TruthValue
        MAX-ACCESS     read-only
        STATUS         current
        DESCRIPTION    "Indicates if line channel monitoring for the tx
                        direction allows flexgrid off regular grid channels
                        for L-Band."
        DEFVAL         { false }
        ::= { tnFlexgridOtsInfoEntry 16 }

    tnFlexgridOtsInfoChannelMonitoringAllowsOffGridInL OBJECT-TYPE
        SYNTAX         TruthValue
        MAX-ACCESS     read-only
        STATUS         current
        DESCRIPTION    "Indicates if line channel monitoring for the rx
                        direction allows flexgrid off regular grid channels
                        for L-Band."
        DEFVAL         { false }
        ::= { tnFlexgridOtsInfoEntry 17 }

    tnFlexgridOtsInfoLineWssIsFlexgridL OBJECT-TYPE
        SYNTAX         TruthValue
        MAX-ACCESS     read-only
        STATUS         current
        DESCRIPTION    "Indicates if the type of Wavelength Selective Switch
                        in the optical line supports flexible frequency slices
                        for L-Band."
        DEFVAL         { false }
        ::= { tnFlexgridOtsInfoEntry 18 }

    tnFlexgridOtsInfoLineGranularityMHzL OBJECT-TYPE
        SYNTAX         Unsigned32 (0..100000)
        UNITS          "MHz"
        MAX-ACCESS     read-only
        STATUS         current
        DESCRIPTION    "Indicates the granularity (minimum slice size multiple)
                        of the optical line Wavelength Selective Switch for L-Band.

                        If tnFlexgridOtsInfoLineWssIsFlexgrid is true, the upper
                        frequency edge of a slice aligns with reference 193.1 THz
                        for n=0 (ITU G.694.1).

                        If tnFlexgridOtsInfoLineWssIsFlexgrid is false, the
                        granularity is the channel slot width centered on the
                        regular ITU grid implied by the granularity.

                        Values are in MHz but should be displayed in user interfaces
                        in GHz."
        DEFVAL         { 0 }
        ::= { tnFlexgridOtsInfoEntry 19 }

    tnFlexgridOtsInfoLineMinMSlicesPerXcL OBJECT-TYPE
        SYNTAX         Unsigned32 (0..6)
        MAX-ACCESS     read-only
        STATUS         current
        DESCRIPTION    "Indicates the minimum number of 12.5 GHz slices that can
                        be used to enter an OCh cross-connect on this optical line
                        for L-Band.

                        E.g. value of 4 equals 50.0 GHz cross-connect width.

                        Value of 0 indicates line topology is incomplete."
        DEFVAL         { 0 }
        ::= { tnFlexgridOtsInfoEntry 20 }

    tnFlexgridOtsInfoLineMaxMSlicesPerXcL OBJECT-TYPE
        SYNTAX         Unsigned32 (0..6)
        MAX-ACCESS     read-only
        STATUS         current
        DESCRIPTION    "Indicates the minimum number of 12.5 GHz slices that can
                        be used to enter an OCh cross-connect on this optical line
                        for L-Band.

                        E.g. value of 4 equals 50.0 GHz cross-connect width.

                        Value of 0 indicates line topology is incomplete."
        DEFVAL         { 0 }
        ::= { tnFlexgridOtsInfoEntry 21 }

    tnFlexgridOtsInfoDcmExistsOut OBJECT-TYPE
        SYNTAX         TruthValue
        MAX-ACCESS     read-only
        STATUS         current
        DESCRIPTION    "Indicate if degree has DCM"
        DEFVAL         { false }
        ::= { tnFlexgridOtsInfoEntry 22 }

    tnFlexgridOtsInfoDcmExistsIn OBJECT-TYPE
        SYNTAX         TruthValue
        MAX-ACCESS     read-only
        STATUS         current
        DESCRIPTION    "Indicate if degree has DCM."
        DEFVAL         { false }
        ::= { tnFlexgridOtsInfoEntry 23 }

    tnFlexgridOtsInfoLineGranularityMHzIn OBJECT-TYPE
        SYNTAX         Unsigned32 (0..100000)
        UNITS          "MHz"
        MAX-ACCESS     read-only
        STATUS         current
        DESCRIPTION    "Indicates the granularity (minimum slice size multiple)
                        of the optical line Wavelength Selective Switch."
        DEFVAL         { 0 }
        ::= { tnFlexgridOtsInfoEntry 24 }

    tnFlexgridOtsInfoLineGranularityMHzInL OBJECT-TYPE
        SYNTAX         Unsigned32 (0..100000)
        UNITS          "MHz"
        MAX-ACCESS     read-only
        STATUS         current
        DESCRIPTION    "Indicates the granularity (minimum slice size multiple)
                        of the optical line Wavelength Selective Switch."
        DEFVAL         { 0 }
        ::= { tnFlexgridOtsInfoEntry 25 }

    tnFlexgridOtsInfoLineMinMSlicesPerXcIn OBJECT-TYPE
        SYNTAX         Unsigned32 (0..6)
        MAX-ACCESS     read-only
        STATUS         current
        DESCRIPTION    "Indicates the minimum number of 12.5 GHz slices that can
                        be used to enter an OCh cross-connect on this optical line
                        Value of 0 indicates line topology is incomplete."
        DEFVAL         { 0 }
        ::= { tnFlexgridOtsInfoEntry 26 }

    tnFlexgridOtsInfoLineMinMSlicesPerXcInL OBJECT-TYPE
        SYNTAX         Unsigned32 (0..6)
        MAX-ACCESS     read-only
        STATUS         current
        DESCRIPTION    "Indicates the minimum number of 12.5 GHz slices that can
                        be used to enter an OCh cross-connect on this optical line
                        Value of 0 indicates line topology is incomplete."
        DEFVAL         { 0 }
        ::= { tnFlexgridOtsInfoEntry 27 }

--------------------------------------------------------------------------------
-- Optical Port Connector Table
--------------------------------------------------------------------------------
    tnOpticalPortConnectorTable OBJECT-TYPE
        SYNTAX         SEQUENCE OF TnOpticalPortConnectorEntry
        MAX-ACCESS     not-accessible
        STATUS         current
        DESCRIPTION    "."
        ::= { tnOpticalPortObjs 49 }

    tnOpticalPortConnectorEntry OBJECT-TYPE
        SYNTAX         TnOpticalPortConnectorEntry
        UNITS          "mB"
        MAX-ACCESS     not-accessible
        STATUS         current
        DESCRIPTION    "."
        INDEX { ifIndex }
        ::= { tnOpticalPortConnectorTable 1 }

    TnOpticalPortConnectorEntry ::=
        SEQUENCE {
            tnOpticalPortConnectorExtraInsertionLossIn INTEGER
        }

    tnOpticalPortConnectorExtraInsertionLossIn OBJECT-TYPE
        SYNTAX         Integer32
        MAX-ACCESS     read-create
        STATUS         current
        DESCRIPTION    "Extra insertion loss added between the upstream
                        port and this optical port, receiving into the port.

                       Current configurable range: 0 to 1000."
        DEFVAL         { 0 }
        ::= { tnOpticalPortConnectorEntry 1 }

--------------------------------------------------------------------------------
-- OTDRM (Optical Time Domain Reflectometer) Port Scan Table
--------------------------------------------------------------------------------
--    obsolete
--    tnPortOtdrScanMTable OBJECT-TYPE ::= { tnOpticalPortObjs 50 }

--------------------------------------------------------------------------------
-- OTS Config Table
--------------------------------------------------------------------------------
    tnOtsConfigTable OBJECT-TYPE
        SYNTAX         SEQUENCE OF TnOtsConfigEntry
        MAX-ACCESS     not-accessible
        STATUS         current
        DESCRIPTION    "."
        ::= { tnOpticalPortObjs 51 }

    tnOtsConfigEntry OBJECT-TYPE
        SYNTAX         TnOtsConfigEntry
        MAX-ACCESS     not-accessible
        STATUS         current
        DESCRIPTION    "."
        INDEX { ifIndex }
        ::= { tnOtsConfigTable 1 }

    TnOtsConfigEntry ::=
        SEQUENCE {
            tnOtsConfigsupportingsinglefiberbidi       INTEGER,
            tnOtsConfigsinglefiberchannelplan          INTEGER,
            tnOtsConfigGridStepSizeType                INTEGER,
            tnOtsConfigExternalAmp                     TruthValue,
            tnOtsConfigOscInExternal                   TruthValue
    }

    tnOtsConfigsupportingsinglefiberbidi OBJECT-TYPE
        SYNTAX         INTEGER {
                         dual(1),
                         single(2)
                       }
        MAX-ACCESS     read-create
        STATUS         current
        DESCRIPTION    "dual   - The port is supporting transmission
                                 on a two-fiber span.
                        single - The port is supporting bidirectional
                                 transmission on a single-fiber span."
        DEFVAL         { dual }
        ::= { tnOtsConfigEntry 1 }

    tnOtsConfigsinglefiberchannelplan OBJECT-TYPE
        SYNTAX         INTEGER {
                         redBlue(1),
                         sFC(2),
                         notApplicable(3)
                       }
        MAX-ACCESS     read-create
        STATUS         current
        DESCRIPTION    "Channel plan."
        DEFVAL         { redBlue }
        ::= { tnOtsConfigEntry 2 }

    tnOtsConfigGridStepSizeType OBJECT-TYPE
        SYNTAX         INTEGER {
                         notAllowed (1),
                         allowed    (2)
                       }
        MAX-ACCESS     read-create
        STATUS         current
        DESCRIPTION    "This attribute manages center frequencies.
                        notAllowed - The OTS degree has standard application and
                                     does not allow channels with center frequencies
                                     on the finer 1.25 GHz increments.
                        allowed    - The OTS degree allows channels with center
                                     frequencies on the finer 1.25 GHz increments."
        DEFVAL         { notAllowed }
        ::= { tnOtsConfigEntry 3 }

    tnOtsConfigExternalAmp OBJECT-TYPE
        SYNTAX         TruthValue
        MAX-ACCESS     read-create
        STATUS         current
        DESCRIPTION    "."
        DEFVAL         { false }
        ::= { tnOtsConfigEntry 4 }

    tnOtsConfigOscInExternal OBJECT-TYPE
        SYNTAX         TruthValue
        MAX-ACCESS     read-create
        STATUS         current
        DESCRIPTION    "."
        DEFVAL         { false }
        ::= { tnOtsConfigEntry 5 }

--------------------------------------------------------------------------------
-- Potential QMargin Table
--------------------------------------------------------------------------------
    tnPotentialQMarginTable OBJECT-TYPE
        SYNTAX         SEQUENCE OF TnPotentialQMarginEntry
        MAX-ACCESS     not-accessible
        STATUS         current
        DESCRIPTION    "."
        ::= { tnOpticalPortObjs 52 }

    tnPotentialQMarginEntry OBJECT-TYPE
        SYNTAX         TnPotentialQMarginEntry
        MAX-ACCESS     not-accessible
        STATUS         current
        DESCRIPTION    "."
        INDEX { ifIndex,
                tnPotentialQMarginProfileId }
        ::= { tnPotentialQMarginTable 1 }

    TnPotentialQMarginEntry ::=
        SEQUENCE {
            tnPotentialQMarginProfileId      Integer32,
            tnPotentialQMarginBaudrate       INTEGER,
            tnPotentialQMarginPayloadRate    Integer32,
            tnPotentialQMarginMin            Integer32,
            tnPotentialQMarginMax            Integer32,
            tnPotentialQMarginAverage        Integer32
        }

    tnPotentialQMarginProfileId OBJECT-TYPE
        SYNTAX         Integer32
        MAX-ACCESS     not-accessible
        STATUS         current
        DESCRIPTION    "."
        ::= { tnPotentialQMarginEntry 1 }

    tnPotentialQMarginBaudrate OBJECT-TYPE
        SYNTAX         INTEGER {
                         unassigned(1),
                         gBaud337(2),
                         gBaud450(3),
                         gBaud563(4),
                         gBaud627(5),
                         gBaud675(6)
                       }
        MAX-ACCESS     read-only
        STATUS         current
        DESCRIPTION    "."
        ::= { tnPotentialQMarginEntry 2 }

    tnPotentialQMarginPayloadRate OBJECT-TYPE
        SYNTAX         Integer32 (0..600)
        MAX-ACCESS     read-only
        STATUS         current
        DESCRIPTION    "."
        DEFVAL         { 0 }
        ::= { tnPotentialQMarginEntry 3 }

    tnPotentialQMarginMin OBJECT-TYPE
        SYNTAX         Integer32
        MAX-ACCESS     read-only
        STATUS         current
        DESCRIPTION    "."
        ::= { tnPotentialQMarginEntry 4 }

    tnPotentialQMarginMax OBJECT-TYPE
        SYNTAX         Integer32
        MAX-ACCESS     read-only
        STATUS         current
        DESCRIPTION "."
        ::= { tnPotentialQMarginEntry 5 }

    tnPotentialQMarginAverage OBJECT-TYPE
        SYNTAX         Integer32
        MAX-ACCESS     read-only
        STATUS         current
        DESCRIPTION "."
        ::= { tnPotentialQMarginEntry 6 }

--------------------------------------------------------------------------------
-- Auto TurnUp Table
--------------------------------------------------------------------------------
    tnAutoTurnUpTable OBJECT-TYPE
        SYNTAX         SEQUENCE OF TnAutoTurnUpEntry
        MAX-ACCESS     not-accessible
        STATUS         current
        DESCRIPTION    "."
        ::= { tnOpticalPortObjs 53 }

    tnAutoTurnUpEntry OBJECT-TYPE
        SYNTAX         TnAutoTurnUpEntry
        MAX-ACCESS     not-accessible
        STATUS         current
        DESCRIPTION    "."
        INDEX { ifIndex }
        ::= { tnAutoTurnUpTable 1 }

    TnAutoTurnUpEntry ::=
        SEQUENCE {
            tnAutoTurnUpEnabled                TruthValue,
            tnAutoTurnUpLineType               INTEGER,
            tnAutoTurnUpStatus                 INTEGER,
            tnAutoTurnUpDegreeNumber           Unsigned32,
            tnAutoTurnUpTxFiberType            INTEGER,
            tnAutoTurnUpTxConnectorLoss        Integer32,
            tnAutoTurnUpRxConnectorLoss        Integer32,
            tnAutoTurnUpTxFiberLength          Integer32,
            tnAutoTurnUpOperationType          INTEGER,
            tnAutoTurnUpSummary                INTEGER,
            tnAutoTurnUpIfIndexOtsRx           InterfaceIndexOrZero,
            tnAutoTurnUpIfIndexOtsTx           InterfaceIndexOrZero,
            tnAutoTurnUpLinkSequenceNumber     Unsigned32,
            tnAutoTurnUpLinkState              Unsigned32,
            tnAutoTurnUpLinkStatus             Unsigned32,
            tnAutoTurnUpOtsTxIpv6Address       SnmpAdminString,
            tnAutoTurnUpOtsTxIfIndex           InterfaceIndexOrZero,
            tnAutoTurnUpOtsTxLineType          INTEGER,
            tnAutoTurnUpOtsTxTargetPower       Integer32,
            tnAutoTurnUpOtsRxIpAddress         SnmpAdminString,
            tnAutoTurnUpOtsRxIfIndex           InterfaceIndexOrZero,
            tnAutoTurnUpOtsRxLineType          INTEGER,
            tnAutoTurnUpOtsRxTargetPower       Integer32,
            tnAutoTurnUpActiveTemplate         SnmpAdminString,
            tnAutoTurnUpResetOtsLinks          TnCommand,
            tnAutoTurnUpHoldOff                TruthValue,
            tnAutoTurnUpOtsIngressCardType     SnmpAdminString,
            tnAutoTurnUpOtsIngressSubType      SnmpAdminString,
            tnAutoTurnUpOtsRamanCardType       SnmpAdminString,
            tnAutoTurnUpTxSpanLoss             Integer32
    }

    tnAutoTurnUpEnabled OBJECT-TYPE
        SYNTAX         TruthValue
        MAX-ACCESS     read-create
        STATUS         current
        DESCRIPTION    "."
        DEFVAL         { false }
        ::= { tnAutoTurnUpEntry 1 }

    tnAutoTurnUpLineType OBJECT-TYPE
        SYNTAX         INTEGER {
                         notDefined(1),
                         ila(2),
                         dge(3),
                         oadm(4)
                       }
        MAX-ACCESS     read-only
        STATUS         current
        DESCRIPTION    "."
        DEFVAL         { notDefined }
        ::= { tnAutoTurnUpEntry 2 }

    tnAutoTurnUpStatus OBJECT-TYPE
        SYNTAX         INTEGER {
                         notRecognized(1),
                         topoComplete(2),
                         otsInitializing(3),
                         omsInitializing(4),
                         commissioned(5),
                         topoInComplete(6)
                       }
        MAX-ACCESS     read-only
        STATUS         current
        DESCRIPTION    "."
        DEFVAL         { notRecognized }
        ::= { tnAutoTurnUpEntry 3 }

    tnAutoTurnUpDegreeNumber OBJECT-TYPE
        SYNTAX         Unsigned32
        MAX-ACCESS     read-create
        STATUS         current
        DESCRIPTION    "Current configurable range: 0 to 64."
        DEFVAL         { 0 }
        ::= { tnAutoTurnUpEntry 4 }

    tnAutoTurnUpTxFiberType OBJECT-TYPE
        SYNTAX         INTEGER {
                         ssmf(1),
                         twrs(2),
                         eleaf(3),
                         dsf(4),
                         twc(5),
                         twp(6),
                         ls(7),
                         notConfigured(8)
                       }
        MAX-ACCESS     read-create
        STATUS         current
        DESCRIPTION    "Indicates the fiber type."
        DEFVAL         { ssmf }
        ::= { tnAutoTurnUpEntry 5 }

    tnAutoTurnUpTxConnectorLoss OBJECT-TYPE
        SYNTAX         Integer32
        UNITS          "mB"
        MAX-ACCESS     read-create
        STATUS         current
        DESCRIPTION    "Current configurable range: 0 to 2000."
        DEFVAL         { 50 }
        ::= { tnAutoTurnUpEntry 6 }

    tnAutoTurnUpRxConnectorLoss OBJECT-TYPE
        SYNTAX         Integer32
        UNITS          "mB"
        MAX-ACCESS     read-create
        STATUS         current
        DESCRIPTION    "Current configurable range: 0 to 2000."
        DEFVAL         { 50 }
        ::= { tnAutoTurnUpEntry 7 }

    tnAutoTurnUpTxFiberLength OBJECT-TYPE
        SYNTAX         Integer32
        UNITS          "m"
        MAX-ACCESS     read-create
        STATUS         current
        DESCRIPTION    "Fiber length provisioned by user in span
                        this port transmits towards.
                        Current configurable range: 0 to 300000."
        DEFVAL         { -99 }
        ::= { tnAutoTurnUpEntry 8 }

    tnAutoTurnUpOperationType OBJECT-TYPE
        SYNTAX         INTEGER {
                         none(1),
                         enable(2),
                         disable(3),
                         restart(4),
                         otsReInit(5),
                         omsReInit(6)
                       }
        MAX-ACCESS     read-create
        STATUS         current
        DESCRIPTION    "."
        DEFVAL         { none }
        ::= { tnAutoTurnUpEntry 9 }


    tnAutoTurnUpSummary OBJECT-TYPE
        SYNTAX         INTEGER {
                         autoTurnUpSupportUndetermined(1),
                         autoTurnUpUnsupportedUnsupportedCard(2),
                         autoTurnUpUnsupportedTemplateMismatch(3),
                         autoTurnUpSupportedAndDisabled(4),
                         autoTurnUpSupportedAndBlocked(5),
                         autoTurnUpSupportedAndAvailable(6)
                       }
        MAX-ACCESS     read-create
        STATUS         current
        DESCRIPTION    "."
        DEFVAL         { autoTurnUpSupportUndetermined }
        ::= { tnAutoTurnUpEntry 10 }

    tnAutoTurnUpIfIndexOtsRx OBJECT-TYPE
        SYNTAX         InterfaceIndexOrZero
        MAX-ACCESS     read-only
        STATUS         current
        DESCRIPTION    "."
        ::= { tnAutoTurnUpEntry 11 }

    tnAutoTurnUpIfIndexOtsTx OBJECT-TYPE
        SYNTAX         InterfaceIndexOrZero
        MAX-ACCESS     read-only
        STATUS         current
        DESCRIPTION    "."
        ::= { tnAutoTurnUpEntry 12 }

    tnAutoTurnUpLinkSequenceNumber OBJECT-TYPE
        SYNTAX         Unsigned32
        MAX-ACCESS     read-only
        STATUS         current
        DESCRIPTION    "."
        ::= { tnAutoTurnUpEntry 13 }

    tnAutoTurnUpLinkState OBJECT-TYPE
        SYNTAX         Unsigned32
        MAX-ACCESS     read-only
        STATUS         current
        DESCRIPTION    "."
        ::= { tnAutoTurnUpEntry 14 }

    tnAutoTurnUpLinkStatus OBJECT-TYPE
        SYNTAX         Unsigned32
        MAX-ACCESS     read-only
        STATUS         current
        DESCRIPTION    "."
        ::= { tnAutoTurnUpEntry 15 }

    tnAutoTurnUpOtsTxIpv6Address OBJECT-TYPE
        SYNTAX         SnmpAdminString (SIZE(0..64))
        MAX-ACCESS     read-only
        STATUS         current
        DESCRIPTION    "."
        ::= { tnAutoTurnUpEntry 16 }

    tnAutoTurnUpOtsTxIfIndex OBJECT-TYPE
        SYNTAX         InterfaceIndexOrZero
        MAX-ACCESS     read-only
        STATUS         current
        DESCRIPTION    "."
        ::= { tnAutoTurnUpEntry 17 }


    tnAutoTurnUpOtsTxLineType OBJECT-TYPE
        SYNTAX         INTEGER {
                         notDefined(1),
                         ila(2),
                         dge(3),
                         oadm(4)
                       }
        MAX-ACCESS     read-only
        STATUS         current
        DESCRIPTION    "."
        ::= { tnAutoTurnUpEntry 18 }

    tnAutoTurnUpOtsTxTargetPower OBJECT-TYPE
        SYNTAX         Integer32
        UNITS          "mBm"
        MAX-ACCESS     read-only
        STATUS         current
        DESCRIPTION    "."
        ::= { tnAutoTurnUpEntry 19 }

    tnAutoTurnUpOtsRxIpAddress OBJECT-TYPE
        SYNTAX         SnmpAdminString (SIZE(0..64))
        MAX-ACCESS     read-only
        STATUS         current
        DESCRIPTION    "."
        ::= { tnAutoTurnUpEntry 20 }

    tnAutoTurnUpOtsRxIfIndex OBJECT-TYPE
        SYNTAX         InterfaceIndexOrZero
        MAX-ACCESS     read-only
        STATUS         current
        DESCRIPTION    "."
        ::= { tnAutoTurnUpEntry 21 }

    tnAutoTurnUpOtsRxLineType OBJECT-TYPE
        SYNTAX         INTEGER {
                         notDefined(1),
                         ila(2),
                         dge(3),
                         oadm(4)
                       }
        MAX-ACCESS     read-only
        STATUS         current
        DESCRIPTION    "."
        ::= { tnAutoTurnUpEntry 22 }

    tnAutoTurnUpOtsRxTargetPower OBJECT-TYPE
        SYNTAX         Integer32
        UNITS          "mBm"
        MAX-ACCESS     read-only
        STATUS         current
        DESCRIPTION    "."
        ::= { tnAutoTurnUpEntry 23 }

    tnAutoTurnUpActiveTemplate OBJECT-TYPE
        SYNTAX         SnmpAdminString (SIZE(0..256))
        MAX-ACCESS     read-create
        STATUS         current
        DESCRIPTION    "."
        ::= { tnAutoTurnUpEntry 24 }

    tnAutoTurnUpResetOtsLinks OBJECT-TYPE
        SYNTAX         TnCommand
        MAX-ACCESS     read-create
        STATUS         current
        DESCRIPTION    "Decommission all OTS links associated
                        with the automation line."
        DEFVAL         { noCmd }
        ::= { tnAutoTurnUpEntry 25 }

    tnAutoTurnUpHoldOff OBJECT-TYPE
        SYNTAX         TruthValue
        MAX-ACCESS     read-create
        STATUS         current
        DESCRIPTION    "Hold off calculation for OTS, OMS links."
        DEFVAL         { false }
        ::= { tnAutoTurnUpEntry 26 }

    tnAutoTurnUpOtsIngressCardType  OBJECT-TYPE
        SYNTAX         SnmpAdminString (SIZE(0..64))
        MAX-ACCESS     read-only
        STATUS         current
        DESCRIPTION    "Downstream node ingress card type."
        ::= { tnAutoTurnUpEntry 27 }

    tnAutoTurnUpOtsIngressSubType  OBJECT-TYPE
        SYNTAX         SnmpAdminString (SIZE(0..64))
        MAX-ACCESS     read-only
        STATUS         current
        DESCRIPTION    "Downstream node ingress card sub type."
        ::= { tnAutoTurnUpEntry 28 }

    tnAutoTurnUpOtsRamanCardType OBJECT-TYPE
        SYNTAX         SnmpAdminString (SIZE(0..64))
        MAX-ACCESS     read-only
        STATUS         current
        DESCRIPTION    "Downstream node raman card type."
        ::= { tnAutoTurnUpEntry 29 }

    tnAutoTurnUpTxSpanLoss OBJECT-TYPE
        SYNTAX         Integer32
        UNITS          "mB"
        MAX-ACCESS     read-only
        STATUS         current
        DESCRIPTION    "Span loss used for OTS calculation.
                        range: -9900 to 6000."
        DEFVAL         { -9900 }
        ::= { tnAutoTurnUpEntry 30 }

--------------------------------------------------------------------------------
-- Max Port Table
--------------------------------------------------------------------------------
    tnMaxPortTable OBJECT-TYPE
        SYNTAX         SEQUENCE OF TnMaxPortEntry
        MAX-ACCESS     not-accessible
        STATUS         current
        DESCRIPTION    "."
        ::= { tnOpticalPortObjs 54 }

    tnMaxPortEntry OBJECT-TYPE
        SYNTAX         TnMaxPortEntry
        MAX-ACCESS     not-accessible
        STATUS         current
        DESCRIPTION    "."
        INDEX { ifIndex }
        ::= { tnMaxPortTable 1 }

    TnMaxPortEntry ::=
        SEQUENCE {
            tnMaxPortRate     Unsigned32
    }

    tnMaxPortRate OBJECT-TYPE
        SYNTAX         Unsigned32
        MAX-ACCESS     read-only
        STATUS         current
        DESCRIPTION    "Max Port rate in Gb/s divided by 100."
        ::= { tnMaxPortEntry 1 }

--------------------------------------------------------------------------------
-- Auto TurnUp OMS Table
--------------------------------------------------------------------------------
    tnAutoTurnUpOmsTable OBJECT-TYPE
        SYNTAX         SEQUENCE OF TnAutoTurnUpOmsEntry
        MAX-ACCESS     not-accessible
        STATUS         current
        DESCRIPTION    "."
        ::= { tnOpticalPortObjs 55 }

    tnAutoTurnUpOmsEntry OBJECT-TYPE
        SYNTAX         TnAutoTurnUpOmsEntry
        MAX-ACCESS     not-accessible
        STATUS         current
        DESCRIPTION    "."
        INDEX { ifIndex,
                tnAutoTurnUpOmsOtsLinkId }
        ::= { tnAutoTurnUpOmsTable 1 }

    TnAutoTurnUpOmsEntry ::=
        SEQUENCE {
            tnAutoTurnUpOmsOtsLinkId     SnmpAdminString,
            tnAutoTurnUpOmsData          SnmpAdminString
        }

    tnAutoTurnUpOmsOtsLinkId OBJECT-TYPE
        SYNTAX         SnmpAdminString (SIZE(1..30))
        MAX-ACCESS     not-accessible
        STATUS         current
        DESCRIPTION    "."
        ::= { tnAutoTurnUpOmsEntry 1 }

    tnAutoTurnUpOmsData OBJECT-TYPE
        SYNTAX         SnmpAdminString (SIZE(0..256))
        MAX-ACCESS     read-only
        STATUS         current
        DESCRIPTION    "OMS link information related to the OTS link ID at OMSTX
                        node."
        ::= { tnAutoTurnUpOmsEntry 2 }

--------------------------------------------------------------------------------
-- Optical Port Configuration
--------------------------------------------------------------------------------

--------------------------------------------------------------------------------
-- SDH Optical Port Config Scalar
--------------------------------------------------------------------------------
    tnSdhPortConfigAttributeTotal OBJECT-TYPE
        SYNTAX         Integer32
        MAX-ACCESS     read-only
        STATUS         current
        DESCRIPTION    "."
        ::= { tnOpticalPortConfig 1 }

--------------------------------------------------------------------------------
-- SDH Optical Port Config Table
--------------------------------------------------------------------------------
    tnSdhPortConfigTable OBJECT-TYPE
        SYNTAX         SEQUENCE OF TnSdhPortConfigEntry
        MAX-ACCESS     not-accessible
        STATUS         current
        DESCRIPTION    "The ports on SDH supported cards."
        ::= { tnOpticalPortConfig 2 }

    tnSdhPortConfigEntry OBJECT-TYPE
        SYNTAX         TnSdhPortConfigEntry
        MAX-ACCESS     not-accessible
        STATUS         current
        DESCRIPTION    "."
        INDEX { ifIndex }
        ::= { tnSdhPortConfigTable 1 }

    TnSdhPortConfigEntry ::=
        SEQUENCE {
            tnSdhPortRxSignalDegradeThreshold Unsigned32,
            tnSdhPortRxSignalFailThreshold    Unsigned32,
            tnSdhPortExpectedRxSectionTrace   SnmpAdminString,
            tnSdhPortTxSectionTrace           SnmpAdminString,
            tnSdhPortRxTIMSEnabled            TruthValue,
            tnSdhPortRxSectionTraceMode       INTEGER,
            tnSdhPortTxSectionTraceMode       INTEGER,
            tnSdhPortTxSynchStatusMessageDUS  TruthValue
        }

    tnSdhPortRxSignalDegradeThreshold OBJECT-TYPE
        SYNTAX         Unsigned32 (0..12)
        MAX-ACCESS     read-create
        STATUS         current
        DESCRIPTION    "Integer range 5 to 9, representing 10-5 to 10-9.

                        Current configurable range: 5 to 9."
        DEFVAL         { 7 }
        ::= { tnSdhPortConfigEntry 1 }

    tnSdhPortRxSignalFailThreshold OBJECT-TYPE
        SYNTAX         Unsigned32 (0..12)
        MAX-ACCESS     read-create
        STATUS         current
        DESCRIPTION    "Integer range 3 to 5, representing 10-3 to 10-5.

                        Current configurable range: 3 to 5."
        DEFVAL         { 5 }
        ::= { tnSdhPortConfigEntry 2 }

    tnSdhPortExpectedRxSectionTrace OBJECT-TYPE
        SYNTAX         SnmpAdminString (SIZE(0..255))
        MAX-ACCESS     read-create
        STATUS         current
        DESCRIPTION    "."
        DEFVAL         { "" }
        ::= { tnSdhPortConfigEntry 3 }

    tnSdhPortTxSectionTrace OBJECT-TYPE
        SYNTAX         SnmpAdminString (SIZE(0..255))
        MAX-ACCESS     read-create
        STATUS         current
        DESCRIPTION    "."
        DEFVAL         { "" }
        ::= { tnSdhPortConfigEntry 4 }

    tnSdhPortRxTIMSEnabled OBJECT-TYPE
        SYNTAX         TruthValue
        MAX-ACCESS     read-create
        STATUS         current
        DESCRIPTION    "."
        DEFVAL         { false }
        ::= { tnSdhPortConfigEntry 5 }

    tnSdhPortRxSectionTraceMode OBJECT-TYPE
        SYNTAX         INTEGER {
                         off(1),
                         mode15byte(2)
                       }
        MAX-ACCESS     read-create
        STATUS         current
        DESCRIPTION    "."
        DEFVAL         { off }
        ::= { tnSdhPortConfigEntry 6 }

    tnSdhPortTxSectionTraceMode OBJECT-TYPE
        SYNTAX         INTEGER {
                         off(1),
                         mode15byte(2)
                       }
        MAX-ACCESS     read-create
        STATUS         current
        DESCRIPTION    "."
        DEFVAL         { off }
        ::= { tnSdhPortConfigEntry 7 }

    tnSdhPortTxSynchStatusMessageDUS OBJECT-TYPE
        SYNTAX         TruthValue
        MAX-ACCESS     read-create
        STATUS         current
        DESCRIPTION    "."
        DEFVAL         { false }
        ::= { tnSdhPortConfigEntry 8 }

--    obsolete
--    tnOC48STM16PortConfigAttributeTotal             OBJECT-TYPE ::= { tnOpticalPortConfig 3 }
--    tnOC48STM16PortConfigTable                      OBJECT-TYPE ::= { tnOpticalPortConfig 4 }
--    tnOC192STM64PortConfigAttributeTotal            OBJECT-TYPE ::= { tnOpticalPortConfig 5 }
--    tnOC192STM64PortConfigTable                     OBJECT-TYPE ::= { tnOpticalPortConfig 6 }
--    tnQuadOC48STM16MuxPortConfigAttributeTotal      OBJECT-TYPE ::= { tnOpticalPortConfig 7 }
--    tnQuadOC48STM16MuxPortConfigTable               OBJECT-TYPE ::= { tnOpticalPortConfig 8 }
--    tnQuadOC3or12STM1or4MuxPortConfigAttributeTotal OBJECT-TYPE ::= { tnOpticalPortConfig 9 }
--    tnQuadOC3or12STM1or4MuxPortConfigTable          OBJECT-TYPE ::= { tnOpticalPortConfig 10 }
--    tnBandFilterPortConfigAttributeTotal            OBJECT-TYPE ::= { tnOpticalPortConfig 11 }
--    tnBandFilterPortConfigTable                     OBJECT-TYPE ::= { tnOpticalPortConfig 12 }

--------------------------------------------------------------------------------
-- OSC Optical Port Config Scalar
--------------------------------------------------------------------------------
    tnOscPortConfigAttributeTotal OBJECT-TYPE
        SYNTAX         Integer32
        MAX-ACCESS     read-only
        STATUS         current
        DESCRIPTION    "."
        ::= { tnOpticalPortConfig 13 }

--------------------------------------------------------------------------------
-- OSC Optical Port Config Table
--------------------------------------------------------------------------------
    tnOscPortConfigTable OBJECT-TYPE
        SYNTAX         SEQUENCE OF TnOscPortConfigEntry
        MAX-ACCESS     not-accessible
        STATUS         current
        DESCRIPTION    "The ports on an OSC optical card."
        ::= { tnOpticalPortConfig 14 }

    tnOscPortConfigEntry OBJECT-TYPE
        SYNTAX         TnOscPortConfigEntry
        MAX-ACCESS     not-accessible
        STATUS         current
        DESCRIPTION    "."
        INDEX { ifIndex }
        ::= { tnOscPortConfigTable 1 }

    TnOscPortConfigEntry ::=
        SEQUENCE {
            tnOscPortConfigFunction INTEGER
--            obsolete
--            tnOscPortPhyDeviceReset INTEGER
        }

    tnOscPortConfigFunction OBJECT-TYPE
        SYNTAX         INTEGER {
                         signal(1),
                         line(2),
                         inv(3),
                         osc(4),
                         oscSfp(5)
                       }
        MAX-ACCESS     read-only
        STATUS         current
        DESCRIPTION    "Indicates the functional type of this OSC port."
        ::= { tnOscPortConfigEntry 1 }

--    obsolete
--    tnOscPortPhyDeviceReset               OBJECT-TYPE ::= { tnOscPortConfigEntry 2 }
--    tnChFilterPortConfigAttributeTotal    OBJECT-TYPE ::= { tnOpticalPortConfig 15 }
--    tnChFilterPortConfigTable             OBJECT-TYPE ::= { tnOpticalPortConfig 16 }
--    tnChAddDropPortConfigAttributeTotal   OBJECT-TYPE ::= { tnOpticalPortConfig 17 }
--    tnChAddDropPortConfigTable            OBJECT-TYPE ::= { tnOpticalPortConfig 18 }
--    tnBbaHgPortConfigAttributeTotal       OBJECT-TYPE ::= { tnOpticalPortConfig 19 }
--    tnBbaHgPortConfigTable                OBJECT-TYPE ::= { tnOpticalPortConfig 20 }
--    tnBbaLgPortConfigAttributeTotal       OBJECT-TYPE ::= { tnOpticalPortConfig 21 }
--    tnBbaLgPortConfigTable                OBJECT-TYPE ::= { tnOpticalPortConfig 22 }
--    tnPpsPortConfigAttributeTotal         OBJECT-TYPE ::= { tnOpticalPortConfig 23 }
--    tnPpsPortConfigTable                  OBJECT-TYPE ::= { tnOpticalPortConfig 24 }
--    tnDualGigEMuxPortConfigAttributeTotal OBJECT-TYPE ::= { tnOpticalPortConfig 25 }
--    tnDualGigEMuxPortConfigTable          OBJECT-TYPE ::= { tnOpticalPortConfig 26 }
--    tnRoadmPortConfigAttributeTotal       OBJECT-TYPE ::= { tnOpticalPortConfig 27 }
--    tnRoadmPortConfigTable                OBJECT-TYPE ::= { tnOpticalPortConfig 28 }
--    tn10GigELANPortConfigAttributeTotal   OBJECT-TYPE ::= { tnOpticalPortConfig 29 }
--    tn10GigELANPortConfigTable            OBJECT-TYPE ::= { tnOpticalPortConfig 30 }

--------------------------------------------------------------------------------
-- Dispersion Compensation Module Optical Port Config Scalar
--------------------------------------------------------------------------------
    tnDcmPortConfigAttributeTotal OBJECT-TYPE
        SYNTAX         Integer32
        MAX-ACCESS     read-only
        STATUS         current
        DESCRIPTION    "."
        ::= { tnOpticalPortConfig 31 }

--------------------------------------------------------------------------------
-- Dispersion Compensation Module Optical Port Config Table
--------------------------------------------------------------------------------
    tnDcmPortConfigTable OBJECT-TYPE
        SYNTAX         SEQUENCE OF TnDcmPortConfigEntry
        MAX-ACCESS     not-accessible
        STATUS         current
        DESCRIPTION    "The ports on a DCM optical card."
        ::= { tnOpticalPortConfig 32 }

    tnDcmPortConfigEntry OBJECT-TYPE
        SYNTAX         TnDcmPortConfigEntry
        MAX-ACCESS     not-accessible
        STATUS         current
        DESCRIPTION    "."
        INDEX { ifIndex }
        ::= { tnDcmPortConfigTable 1 }

    TnDcmPortConfigEntry ::=
        SEQUENCE {
            tnDcmPortConfigFunction INTEGER
        }

    tnDcmPortConfigFunction OBJECT-TYPE
        SYNTAX         INTEGER {
                         dcmOutThruIn(1),
                         thruOutDcmIn(2),
                         dcmInOut(3)
                       }
        MAX-ACCESS     read-only
        STATUS         current
        DESCRIPTION    "Indicates the functional type of this Dispersion
                        Compensation Module port."
        ::= { tnDcmPortConfigEntry 1 }

--    obsolete
--    tnDecaGigEMuxPortConfigAttributeTotal OBJECT-TYPE ::= { tnOpticalPortConfig 33 }
--    tnDecaGigEMuxPortConfigTable          OBJECT-TYPE ::= { tnOpticalPortConfig 34 }

--------------------------------------------------------------------------------
-- SONET Optical Port Config Scalar
--------------------------------------------------------------------------------
    tnSonetPortConfigAttributeTotal OBJECT-TYPE
        SYNTAX         Integer32
        MAX-ACCESS     read-only
        STATUS         current
        DESCRIPTION    "."
        ::= { tnOpticalPortConfig 35 }

--------------------------------------------------------------------------------
-- SONET Optical Port Config Table
--------------------------------------------------------------------------------
    tnSonetPortConfigTable OBJECT-TYPE
        SYNTAX         SEQUENCE OF TnSonetPortConfigEntry
        MAX-ACCESS     not-accessible
        STATUS         current
        DESCRIPTION    "The ports on SONET supported cards."
        ::= { tnOpticalPortConfig 36 }

    tnSonetPortConfigEntry OBJECT-TYPE
        SYNTAX         TnSonetPortConfigEntry
        MAX-ACCESS     not-accessible
        STATUS         current
        DESCRIPTION    "."
        INDEX { ifIndex }
        ::= { tnSonetPortConfigTable 1 }

    TnSonetPortConfigEntry ::=
        SEQUENCE {
            tnSonetPortRxSignalDegradeThreshold Unsigned32,
            tnSonetPortRxSignalFailThreshold    Unsigned32,
            tnSonetPortExpectedRxSectionTrace   SnmpAdminString,
            tnSonetPortTxSectionTrace           SnmpAdminString,
            tnSonetPortRxTIMSEnabled            TruthValue,
            tnSonetPortRxSectionTraceMode       INTEGER,
            tnSonetPortTxSectionTraceMode       INTEGER,
            tnSonetPortTxSynchStatusMessageDUS  TruthValue
        }

    tnSonetPortRxSignalDegradeThreshold OBJECT-TYPE
        SYNTAX         Unsigned32 (0..12)
        MAX-ACCESS     read-create
        STATUS         current
        DESCRIPTION    "Integer range 5 to 9, representing 10-5 to 10-9.

                        Current configurable range: 5 to 9."
        DEFVAL         { 7 }
        ::= { tnSonetPortConfigEntry 1 }

    tnSonetPortRxSignalFailThreshold OBJECT-TYPE
        SYNTAX         Unsigned32 (0..12)
        MAX-ACCESS     read-create
        STATUS         current
        DESCRIPTION    "Integer range 3 to 5, representing 10-3 to 10-5.

                        Current configurable range: 3 to 5."
        DEFVAL         { 5 }
        ::= { tnSonetPortConfigEntry 2 }

    tnSonetPortExpectedRxSectionTrace OBJECT-TYPE
        SYNTAX         SnmpAdminString (SIZE(0..255))
        MAX-ACCESS     read-create
        STATUS         current
        DESCRIPTION    "."
        DEFVAL         { "" }
        ::= { tnSonetPortConfigEntry 3 }

    tnSonetPortTxSectionTrace OBJECT-TYPE
        SYNTAX         SnmpAdminString (SIZE(0..255))
        MAX-ACCESS     read-create
        STATUS         current
        DESCRIPTION    "."
        DEFVAL         { "" }
        ::= { tnSonetPortConfigEntry 4 }

    tnSonetPortRxTIMSEnabled OBJECT-TYPE
        SYNTAX         TruthValue
        MAX-ACCESS     read-create
        STATUS         current
        DESCRIPTION    "."
        DEFVAL         { false }
        ::= { tnSonetPortConfigEntry 5 }

    tnSonetPortRxSectionTraceMode OBJECT-TYPE
        SYNTAX         INTEGER {
                         off(1),
                         mode64byteCrLf(2)
                       }
        MAX-ACCESS     read-create
        STATUS         current
        DESCRIPTION    "."
        DEFVAL         { off }
        ::= { tnSonetPortConfigEntry 6 }

    tnSonetPortTxSectionTraceMode OBJECT-TYPE
        SYNTAX         INTEGER {
                         off(1),
                         mode64byteCrLf(2)
                       }
        MAX-ACCESS     read-create
        STATUS         current
        DESCRIPTION    "."
        DEFVAL         { off }
        ::= { tnSonetPortConfigEntry 7 }

    tnSonetPortTxSynchStatusMessageDUS OBJECT-TYPE
        SYNTAX         TruthValue
        MAX-ACCESS     read-create
        STATUS         current
        DESCRIPTION    "."
        DEFVAL         { false }
        ::= { tnSonetPortConfigEntry 8 }

--    obsolete
--    tnExternalDcuPortConfigAttributeTotal OBJECT-TYPE ::= { tnOpticalPortConfig 37 }
--    tnExternalDcuPortConfigTable          OBJECT-TYPE ::= { tnOpticalPortConfig 38 }

--------------------------------------------------------------------------------
-- Digital Wrapper Optical Port Config Scalar
--------------------------------------------------------------------------------
    tnDigitalWrapperPortConfigAttributeTotal OBJECT-TYPE
        SYNTAX         Integer32
        MAX-ACCESS     read-only
        STATUS         current
        DESCRIPTION    "."
        ::= { tnOpticalPortConfig 39 }

--------------------------------------------------------------------------------
-- Digital Wrapper Optical Port Config Table
--------------------------------------------------------------------------------
    tnDigitalWrapperPortConfigTable OBJECT-TYPE
        SYNTAX         SEQUENCE OF TnDigitalWrapperPortConfigEntry
        MAX-ACCESS     not-accessible
        STATUS         current
        DESCRIPTION    "The ports on Digital Wrapper supported cards."
        ::= { tnOpticalPortConfig 40 }

    tnDigitalWrapperPortConfigEntry OBJECT-TYPE
        SYNTAX         TnDigitalWrapperPortConfigEntry
        MAX-ACCESS     not-accessible
        STATUS         current
        DESCRIPTION    "."
        INDEX { ifIndex }
        ::= { tnDigitalWrapperPortConfigTable 1 }

    TnDigitalWrapperPortConfigEntry ::=
        SEQUENCE {
            tnDwPortRxRSBERSDThresh  Unsigned32,
            tnDwPortRxRSBERSFThresh  Unsigned32,
            tnDwPortDwMode           AluWdmFecMode,
            tnDwPortPMTTIEnabled     TruthValue,
            tnDwPortPTIEnabled       TruthValue
        }

    tnDwPortRxRSBERSDThresh OBJECT-TYPE
        SYNTAX         Unsigned32
        MAX-ACCESS     read-create
        STATUS         current
        DESCRIPTION    "BER threshold to raise SD condition on Rx.
                        Specified value n means BER threshold of 10^-n.

                        Current configurable range: 3 to 9."
        DEFVAL         { 4 }
        ::= { tnDigitalWrapperPortConfigEntry 1 }

    tnDwPortRxRSBERSFThresh OBJECT-TYPE
        SYNTAX         Unsigned32
        MAX-ACCESS     read-create
        STATUS         current
        DESCRIPTION    "Sets BER threshold to raise SF condition on Rx.
                        Specified value n means BER threshold of 10^-n.

                        Current configurable range: 3 to 9."
        DEFVAL         { 3 }
        ::= { tnDigitalWrapperPortConfigEntry 2 }

    tnDwPortDwMode OBJECT-TYPE
        SYNTAX         AluWdmFecMode
        MAX-ACCESS     read-create
        STATUS         current
        DESCRIPTION    "Digital Wrapper mode.  Setting this attribute
                        to a value of disabled is not supported."
        DEFVAL         { g709Fec }
        ::= { tnDigitalWrapperPortConfigEntry 3 }

    tnDwPortPMTTIEnabled OBJECT-TYPE
        SYNTAX         TruthValue
        MAX-ACCESS     read-create
        STATUS         current
        DESCRIPTION    "Digital Wrapper Trail Trace Identifier."
        DEFVAL         { false }
        ::= { tnDigitalWrapperPortConfigEntry 4 }

    tnDwPortPTIEnabled OBJECT-TYPE
        SYNTAX         TruthValue
        MAX-ACCESS     read-create
        STATUS         current
        DESCRIPTION    "Digital Wrapper Payload Type Indication."
        DEFVAL         { false }
        ::= { tnDigitalWrapperPortConfigEntry 5 }

--------------------------------------------------------------------------------
-- Network Port Config Scalar
--------------------------------------------------------------------------------
    tnNetworkPortConfigAttributeTotal OBJECT-TYPE
        SYNTAX         Integer32
        MAX-ACCESS     read-only
        STATUS         current
        DESCRIPTION    "."
        ::= { tnOpticalPortConfig 41 }

--------------------------------------------------------------------------------
-- Network Port Config Table
--------------------------------------------------------------------------------
    tnNetworkPortConfigTable OBJECT-TYPE
        SYNTAX         SEQUENCE OF TnNetworkPortConfigEntry
        MAX-ACCESS     not-accessible
        STATUS         current
        DESCRIPTION    "The network ports on optical transponder cards."
        ::= { tnOpticalPortConfig 42 }

    tnNetworkPortConfigEntry OBJECT-TYPE
        SYNTAX         TnNetworkPortConfigEntry
        MAX-ACCESS     not-accessible
        STATUS         current
        DESCRIPTION    "."
        INDEX { ifIndex }
        ::= { tnNetworkPortConfigTable 1 }

    TnNetworkPortConfigEntry ::=
        SEQUENCE {
--            obsolete
--            tnNwPortOchStatusRx                            TnOchStatus,
--            tnNwPortOchStatusTx                            TnOchStatus,
            tnNwPortProgrammedChannel                      Unsigned32,
            tnNwPortChannelRx                              Unsigned32,
            tnNwPortChannelSpacing                         Unsigned32,
            tnNwPortLaserOffRequest                        INTEGER,
            tnNwPortForcedLaserState                       INTEGER,
            tnNwPortProgrammedITUNumOffsetTx               Integer32,
            tnNwPortProgrammedITUNumOffsetRx               Integer32,
            tnNwPortProgrammedITUNumOffsetGridStepSize     INTEGER,
            tnNwPortCalculatedRxFreq                       Unsigned32,
            tnNwPortCalculatedTxFreq                       Unsigned32,
            tnNwPortLinkSpan                               INTEGER,
            tnNwPortChannelTxLane                          SnmpAdminString,
            tnNwPortChannelRxLane                          SnmpAdminString,
            tnNwPortRxFineOffSet                           Integer32,
            tnNwPortTxFineOffSet                           Integer32
        }

--    obsolete
--    tnNwPortOchStatusRx OBJECT-TYPE ::= { tnNetworkPortConfigEntry 1 }
--    tnNwPortOchStatusTx OBJECT-TYPE ::= { tnNetworkPortConfigEntry 2 }

    tnNwPortProgrammedChannel OBJECT-TYPE
        SYNTAX         Unsigned32
        MAX-ACCESS     read-create
        STATUS         current
        DESCRIPTION    "The programmed ITU channel.

                        Current configurable range: 0 to 10119."
        DEFVAL         { 0 }
        ::= { tnNetworkPortConfigEntry 3 }

    tnNwPortChannelRx OBJECT-TYPE
        SYNTAX         Unsigned32
        MAX-ACCESS     read-create
        STATUS         current
        DESCRIPTION    "The Rx ITU channel.

                        Current configurable range: 0 to 10119."
        DEFVAL         { 0 }
        ::= { tnNetworkPortConfigEntry 4 }

    tnNwPortChannelSpacing OBJECT-TYPE
        SYNTAX         Unsigned32
        UNITS          "GHz"
        MAX-ACCESS     read-create
        STATUS         current
        DESCRIPTION    "This Specifies the channel spacing to use for
                        line ports.
                        1 - 100GHz
                        2 - 50GHz."
        DEFVAL         { 1 }
        ::= { tnNetworkPortConfigEntry 5 }


    tnNwPortLaserOffRequest OBJECT-TYPE
        SYNTAX         INTEGER {
                         forcedOff(1),
                         forcedOn(2)
                       }
        MAX-ACCESS     read-create
        STATUS         current
        DESCRIPTION    "The laserOff request state."
        ::= { tnNetworkPortConfigEntry 6 }

    tnNwPortForcedLaserState OBJECT-TYPE
        SYNTAX         INTEGER {
                         off(1),
                         on(2),
                         auto(3)
                       }
        MAX-ACCESS     read-create
        STATUS         current
        DESCRIPTION    "The forced laser state."
        ::= { tnNetworkPortConfigEntry 7 }

    tnNwPortProgrammedITUNumOffsetTx OBJECT-TYPE
        SYNTAX         Integer32
        MAX-ACCESS     read-create
        STATUS         current
        DESCRIPTION    "The Tx ITU channel offset.

                        Current configurable range: -2 to 2."
        DEFVAL         { 0 }
        ::= { tnNetworkPortConfigEntry 8 }

    tnNwPortProgrammedITUNumOffsetRx OBJECT-TYPE
        SYNTAX         Integer32
        MAX-ACCESS     read-create
        STATUS         current
        DESCRIPTION    "The Rx ITU channel offset.

                        Current configurable range: -2 to 2."
        DEFVAL         { 0 }
        ::= { tnNetworkPortConfigEntry 9 }

    tnNwPortProgrammedITUNumOffsetGridStepSize OBJECT-TYPE
        SYNTAX         INTEGER {
                         gridStep6Pt25GHz(1),
                         gridStep1Pt25GHz(2),
                         gridStep0Pt10GHz(3)
                       }
        MAX-ACCESS     read-create
        STATUS         current
        DESCRIPTION    "The GridStepSize."
        DEFVAL         { gridStep6Pt25GHz }
        ::= { tnNetworkPortConfigEntry 10 }

    tnNwPortCalculatedRxFreq OBJECT-TYPE
        SYNTAX         Unsigned32
        MAX-ACCESS     read-only
        STATUS         current
        DESCRIPTION    "Rx Calculated center frequency."
        ::= { tnNetworkPortConfigEntry 11 }

    tnNwPortCalculatedTxFreq OBJECT-TYPE
        SYNTAX         Unsigned32
        MAX-ACCESS     read-only
        STATUS         current
        DESCRIPTION    "Tx Calculated center frequency."
        ::= { tnNetworkPortConfigEntry 12 }

    tnNwPortLinkSpan OBJECT-TYPE
        SYNTAX         INTEGER {
                         amplified(1),
                         unamplified(2)
                       }
        MAX-ACCESS     read-create
        STATUS         current
        DESCRIPTION    "."
        DEFVAL         { amplified }
        ::= { tnNetworkPortConfigEntry 13 }

    tnNwPortChannelTxLane OBJECT-TYPE
        SYNTAX         SnmpAdminString (SIZE(0..400))
        MAX-ACCESS     read-only
        STATUS         current
        DESCRIPTION    "Displays CFP receive lane frequency for the number of
                        lanes supported by a CFP type.  Receive lane frequencies
                        will not be displayed for the following conditions:
                          - A CFP does not provide lane powers
                          - A CFP is not equipped (not present)
                          - A port is not provisioned.
                        For a CFP with 4 lanes, here is a sample output:
                          'TxChannel Lane 1 : 9160
                           TxChannel Lane 2 : 9170
                           TxChannel Lane 3 : 9180
                           TxChannel Lane 4 : 9190'
                        including the new line characters."
        ::= { tnNetworkPortConfigEntry 14 }

    tnNwPortChannelRxLane OBJECT-TYPE
        SYNTAX         SnmpAdminString (SIZE(0..400))
        MAX-ACCESS     read-only
        STATUS         current
        DESCRIPTION    "Displays CFP receive lane frequency for the number of
                        lanes supported by a CFP type.  Receive lane frequencies
                        will not be displayed for the following conditions:
                          - A CFP does not provide lane powers
                          - A CFP is not equipped (not present)
                          - A port is not provisioned.
                        For a CFP with 4 lanes, here is a sample output:
                          'RxChannel Lane 1 : 9240
                           RxChannel Lane 2 : 9250
                           RxChannel Lane 3 : 9260
                           RxChannel Lane 4 : 9270."
        ::= { tnNetworkPortConfigEntry 15 }

    tnNwPortRxFineOffSet OBJECT-TYPE
        SYNTAX         Integer32
        MAX-ACCESS     read-create
        STATUS         current
        DESCRIPTION    "Specifies the receive fine frequency offset of the port
                        in GHz."
        DEFVAL         { 0 }
        ::= { tnNetworkPortConfigEntry 16 }

    tnNwPortTxFineOffSet OBJECT-TYPE
        SYNTAX         Integer32
        MAX-ACCESS     read-create
        STATUS         current
        DESCRIPTION    "Specifies the transmit fine frequency offset of the port
                        in GHz."
        DEFVAL         { 0 }
        ::= { tnNetworkPortConfigEntry 17 }

--    obsolete
--    tnMsaHgPortConfigAttributeTotal OBJECT-TYPE ::= { tnOpticalPortConfig 43 }
--    tnMsaHgPortConfigTable          OBJECT-TYPE ::= { tnOpticalPortConfig 44 }
--    tnCmd42PortConfigAttributeTotal OBJECT-TYPE ::= { tnOpticalPortConfig 45 }
--    tnCmd42PortConfigTable          OBJECT-TYPE ::= { tnOpticalPortConfig 46 }
--    tnWssX9PortConfigAttributeTotal OBJECT-TYPE ::= { tnOpticalPortConfig 47 }
--    tnWssX9PortConfigTable          OBJECT-TYPE ::= { tnOpticalPortConfig 48 }

--------------------------------------------------------------------------------
-- Sfp Port Config Scalar
--------------------------------------------------------------------------------
    tnSfpPortConfigAttributeTotal OBJECT-TYPE
        SYNTAX         Integer32
        MAX-ACCESS     read-only
        STATUS         current
        DESCRIPTION    "."
        ::= { tnOpticalPortConfig 49 }

--------------------------------------------------------------------------------
-- SFP Port Config Table
--------------------------------------------------------------------------------
    tnSfpPortConfigTable OBJECT-TYPE
        SYNTAX         SEQUENCE OF TnSfpPortConfigEntry
        MAX-ACCESS     not-accessible
        STATUS         current
        DESCRIPTION    "The SFP supported ports."
        ::= { tnOpticalPortConfig 50 }

    tnSfpPortConfigEntry OBJECT-TYPE
        SYNTAX         TnSfpPortConfigEntry
        MAX-ACCESS     not-accessible
        STATUS         current
        DESCRIPTION    "."
        INDEX { ifIndex }
        ::= { tnSfpPortConfigTable 1 }

    TnSfpPortConfigEntry ::=
        SEQUENCE {
            tnSfpPortType                             TnSfpType,
            tnSfpPortModuleName                       SnmpAdminString,
            tnSfpPortLifeCycleState                   SnmpAdminString,
            tnSfpPortProductCode                      SnmpAdminString,
            tnSfpPortDueDate                          SnmpAdminString,
            tnSfpPortProductCodeSup                   INTEGER,
            tnSfpPortModuleCustomerLifeCycleState     SnmpAdminString,
            tnSfpPortCircuitId                        SnmpAdminString,
            tnSfpPortIdModuleXponder                  Unsigned32,
            tnSfpPortModuleDescription                SnmpAdminString
        }

    tnSfpPortType OBJECT-TYPE
        SYNTAX         TnSfpType
        MAX-ACCESS     read-create
        STATUS         current
        DESCRIPTION    "."
        ::= { tnSfpPortConfigEntry 1 }

    tnSfpPortModuleName OBJECT-TYPE
        SYNTAX         SnmpAdminString (SIZE(0..45))
        MAX-ACCESS     read-create
        STATUS         current
        DESCRIPTION    "."
        ::= { tnSfpPortConfigEntry 2 }

    tnSfpPortLifeCycleState OBJECT-TYPE
        SYNTAX         SnmpAdminString (SIZE(0..45))
        MAX-ACCESS     read-create
        STATUS         current
        DESCRIPTION    "."
        ::= { tnSfpPortConfigEntry 3 }

    tnSfpPortProductCode OBJECT-TYPE
        SYNTAX         SnmpAdminString (SIZE(0..16))
        MAX-ACCESS     read-create
        STATUS         current
        DESCRIPTION    "."
        ::= { tnSfpPortConfigEntry 4 }

    tnSfpPortDueDate OBJECT-TYPE
        SYNTAX         SnmpAdminString (SIZE(0..20))
        MAX-ACCESS     read-create
        STATUS         current
        DESCRIPTION    "."
        ::= { tnSfpPortConfigEntry 5 }

    tnSfpPortProductCodeSup OBJECT-TYPE
        SYNTAX         INTEGER {
                         disabled(1),
                         enabled(2)
                       }
        MAX-ACCESS     read-create
        STATUS         current
        DESCRIPTION    "."
        ::= { tnSfpPortConfigEntry 6 }

    tnSfpPortModuleCustomerLifeCycleState OBJECT-TYPE
        SYNTAX         SnmpAdminString (SIZE(0..45))
        MAX-ACCESS     read-create
        STATUS         current
        DESCRIPTION    "Module Customer Life Cycle State."
        ::= { tnSfpPortConfigEntry 7 }

    tnSfpPortCircuitId OBJECT-TYPE
        SYNTAX         SnmpAdminString (SIZE(0..45))
        MAX-ACCESS     read-create
        STATUS         current
        DESCRIPTION    "."
        ::= { tnSfpPortConfigEntry 8 }

    tnSfpPortIdModuleXponder OBJECT-TYPE
        SYNTAX         Unsigned32
        MAX-ACCESS     read-create
        STATUS         current
        DESCRIPTION    "Module Xponder Port Id."
        ::= { tnSfpPortConfigEntry 9 }

    tnSfpPortModuleDescription OBJECT-TYPE
        SYNTAX         SnmpAdminString (SIZE(0..255))
        MAX-ACCESS     read-create
        STATUS         current
        DESCRIPTION    "."
        ::= { tnSfpPortConfigEntry 10 }

--    obsolete
--    tn1xMR2dot5GPortConfigAttributeTotal OBJECT-TYPE ::= { tnOpticalPortConfig 51 }
--    tn1xMR2dot5GPortConfigTable          OBJECT-TYPE ::= { tnOpticalPortConfig 52 }

--------------------------------------------------------------------------------
-- OPSA Optical Port Config Scalar
--------------------------------------------------------------------------------
    tnOpsaPortConfigAttributeTotal OBJECT-TYPE
        SYNTAX         Integer32
        MAX-ACCESS     read-only
        STATUS         current
        DESCRIPTION    "."
        ::= { tnOpticalPortConfig 53 }

--------------------------------------------------------------------------------
-- OPSA Optical Port Config Table
--------------------------------------------------------------------------------
    tnOpsaPortConfigTable OBJECT-TYPE
        SYNTAX         SEQUENCE OF TnOpsaPortConfigEntry
        MAX-ACCESS     not-accessible
        STATUS         current
        DESCRIPTION    "The ports on an OPSA optical card."
        ::= { tnOpticalPortConfig 54 }

    tnOpsaPortConfigEntry OBJECT-TYPE
        SYNTAX         TnOpsaPortConfigEntry
        MAX-ACCESS     not-accessible
        STATUS         current
        DESCRIPTION    "."
        INDEX { ifIndex }
        ::= { tnOpsaPortConfigTable 1 }

    TnOpsaPortConfigEntry ::=
        SEQUENCE {
            tnOpsaPortConfigFunction              INTEGER
--            obsolete
--            tnOpsaPortSwitchingThreshold          Integer32,
--            tnOpsaPortSwitchingThresholdTolerance Unsigned32,
--            tnOpsaPortTransmitAttenuation         Integer32,
--            tnOpsaPortSwitchingThreshCalcControl  INTEGER
        }

    tnOpsaPortConfigFunction OBJECT-TYPE
        SYNTAX         INTEGER {
                         signal(1),
                         workingProtected(2)
                       }
        MAX-ACCESS     read-only
        STATUS         current
        DESCRIPTION    "Indicates the functional type of this OPSA port."
        ::= { tnOpsaPortConfigEntry 1 }

--    obsolete
--    tnOpsaPortSwitchingThreshold          OBJECT-TYPE ::= { tnOpsaPortConfigEntry 2 }
--    tnOpsaPortSwitchingThresholdTolerance OBJECT-TYPE ::= { tnOpsaPortConfigEntry 3 }
--    tnOpsaPortTransmitAttenuation         OBJECT-TYPE ::= { tnOpsaPortConfigEntry 4 }
--    tnOpsaPortSwitchingThreshCalcControl  OBJECT-TYPE ::= { tnOpsaPortConfigEntry 5 }

--------------------------------------------------------------------------------
-- 11STMM10 Optical Port Config Scalar
--------------------------------------------------------------------------------
    tn11stmm10PortConfigAttributeTotal OBJECT-TYPE
        SYNTAX         Integer32
        MAX-ACCESS     read-only
        STATUS         current
        DESCRIPTION    "."
        ::= { tnOpticalPortConfig 55 }

--------------------------------------------------------------------------------
-- 11STMM10 Optical Port Config Table
--------------------------------------------------------------------------------
    tn11stmm10PortConfigTable OBJECT-TYPE
        SYNTAX         SEQUENCE OF Tn11stmm10PortConfigEntry
        MAX-ACCESS     not-accessible
        STATUS         current
        DESCRIPTION    "The ports on a 11STMM10 optical card."
        ::= { tnOpticalPortConfig 56 }

    tn11stmm10PortConfigEntry OBJECT-TYPE
        SYNTAX         Tn11stmm10PortConfigEntry
        MAX-ACCESS     not-accessible
        STATUS         current
        DESCRIPTION    "."
        INDEX { ifIndex }
        ::= { tn11stmm10PortConfigTable 1 }

    Tn11stmm10PortConfigEntry ::=
        SEQUENCE {
            tn11stmm10PortConfigFunction INTEGER
        }

    tn11stmm10PortConfigFunction OBJECT-TYPE
        SYNTAX         INTEGER {
                         network(1),
                         client(2)
                       }
        MAX-ACCESS     read-only
        STATUS         current
        DESCRIPTION    "Indicates the functional type of this 11STMM10
                        port."
        ::= { tn11stmm10PortConfigEntry 1 }

--------------------------------------------------------------------------------
-- 11STAR1 Optical Port Config Scalar
--------------------------------------------------------------------------------
    tn11star1PortConfigAttributeTotal OBJECT-TYPE
        SYNTAX         Integer32
        MAX-ACCESS     read-only
        STATUS         current
        DESCRIPTION    "."
        ::= { tnOpticalPortConfig 57 }

--------------------------------------------------------------------------------
-- 11STAR1 Optical Port Config Table
--------------------------------------------------------------------------------
    tn11star1PortConfigTable OBJECT-TYPE
        SYNTAX         SEQUENCE OF Tn11star1PortConfigEntry
        MAX-ACCESS     not-accessible
        STATUS         current
        DESCRIPTION    "The ports on a 11STAR1 optical card."
        ::= { tnOpticalPortConfig 58 }

    tn11star1PortConfigEntry OBJECT-TYPE
        SYNTAX         Tn11star1PortConfigEntry
        MAX-ACCESS     not-accessible
        STATUS         current
        DESCRIPTION    "."
        INDEX { ifIndex }
        ::= { tn11star1PortConfigTable 1 }

    Tn11star1PortConfigEntry ::=
        SEQUENCE {
            tn11star1PortConfigFunction INTEGER
        }

    tn11star1PortConfigFunction OBJECT-TYPE
        SYNTAX         INTEGER {
                         network(1),
                         client(2)
                       }
        MAX-ACCESS     read-only
        STATUS         current
        DESCRIPTION    "Indicates the functional type of this 11STAR1 port."
        ::= { tn11star1PortConfigEntry 1 }

--------------------------------------------------------------------------------
-- AHPHG Optical Port Config Scalar
--------------------------------------------------------------------------------
    tnAhphgPortConfigAttributeTotal OBJECT-TYPE
        SYNTAX         Integer32
        MAX-ACCESS     read-only
        STATUS         current
        DESCRIPTION    "."
        ::= { tnOpticalPortConfig 59 }

--------------------------------------------------------------------------------
-- AHPHG Optical Port Config Table
--------------------------------------------------------------------------------
    tnAhphgPortConfigTable OBJECT-TYPE
        SYNTAX         SEQUENCE OF TnAhphgPortConfigEntry
        MAX-ACCESS     not-accessible
        STATUS         current
        DESCRIPTION    "The ports on an AHPHG optical card."
        ::= { tnOpticalPortConfig 60 }

    tnAhphgPortConfigEntry OBJECT-TYPE
        SYNTAX         TnAhphgPortConfigEntry
        MAX-ACCESS     not-accessible
        STATUS         current
        DESCRIPTION    "."
        INDEX { ifIndex }
        ::= { tnAhphgPortConfigTable 1 }

    TnAhphgPortConfigEntry ::=
        SEQUENCE {
            tnAhphgPortConfigFunction INTEGER
        }

    tnAhphgPortConfigFunction OBJECT-TYPE
        SYNTAX         INTEGER {
                         line(1),
                         signal(2),
                         dcm(3),
                         inv(4),
                         osc(5),
                         custLan(6)
                       }
        MAX-ACCESS     read-only
        STATUS         current
        DESCRIPTION    "Indicates the functional type of this AHPHG port."
        ::= { tnAhphgPortConfigEntry 1 }

--------------------------------------------------------------------------------
-- ALPHG Optical Port Config Scalar
--------------------------------------------------------------------------------
    tnAlphgPortConfigAttributeTotal OBJECT-TYPE
        SYNTAX         Integer32
        MAX-ACCESS     read-only
        STATUS         current
        DESCRIPTION    "."
        ::= { tnOpticalPortConfig 61 }

--------------------------------------------------------------------------------
-- ALPHG Optical Port Config Table
--------------------------------------------------------------------------------
    tnAlphgPortConfigTable OBJECT-TYPE
        SYNTAX         SEQUENCE OF TnAlphgPortConfigEntry
        MAX-ACCESS     not-accessible
        STATUS         current
        DESCRIPTION    "The ports on an ALPHG optical card."
        ::= { tnOpticalPortConfig 62 }

    tnAlphgPortConfigEntry OBJECT-TYPE
        SYNTAX         TnAlphgPortConfigEntry
        MAX-ACCESS     not-accessible
        STATUS         current
        DESCRIPTION    "."
        INDEX { ifIndex }
        ::= { tnAlphgPortConfigTable 1 }

    TnAlphgPortConfigEntry ::=
        SEQUENCE {
            tnAlphgPortConfigFunction INTEGER
        }

    tnAlphgPortConfigFunction OBJECT-TYPE
        SYNTAX         INTEGER {
                         line(1),
                         signal(2),
                         dcm(3),
                         inv(4),
                         osc(5),
                         custLan(6)
                       }
        MAX-ACCESS     read-only
        STATUS         current
        DESCRIPTION    "Indicates the functional type of this ALPHG port."
        ::= { tnAlphgPortConfigEntry 1 }

--------------------------------------------------------------------------------
-- CWR8 Optical Port Config Scalar
--------------------------------------------------------------------------------
    tnCwr8PortConfigAttributeTotal OBJECT-TYPE
        SYNTAX         Integer32
        MAX-ACCESS     read-only
        STATUS         current
        DESCRIPTION    "."
        ::= { tnOpticalPortConfig 63 }

--------------------------------------------------------------------------------
-- CWR8 Optical Port Config Table
--------------------------------------------------------------------------------
    tnCwr8PortConfigTable OBJECT-TYPE
        SYNTAX         SEQUENCE OF TnCwr8PortConfigEntry
        MAX-ACCESS     not-accessible
        STATUS         current
        DESCRIPTION    "The ports on a CWR8 optical card."
        ::= { tnOpticalPortConfig 64 }

    tnCwr8PortConfigEntry OBJECT-TYPE
        SYNTAX         TnCwr8PortConfigEntry
        MAX-ACCESS     not-accessible
        STATUS         current
        DESCRIPTION    "."
        INDEX { ifIndex }
        ::= { tnCwr8PortConfigTable 1 }

    TnCwr8PortConfigEntry ::=
        SEQUENCE {
            tnCwr8PortConfigFunction  INTEGER,
--            obsolete
--            tnCwr8PortBlockerAging    Unsigned32,
            tnCwr8PortDropTargetPower Integer32
        }

    tnCwr8PortConfigFunction OBJECT-TYPE
        SYNTAX         INTEGER {
                         signal(1),
                         test(2),
                         thru(3),
                         colorless(4),
                         omd(5),
                         inv(6)
                       }
        MAX-ACCESS     read-only
        STATUS         current
        DESCRIPTION    "Indicates the functional type of this CWR8 port."
        ::= { tnCwr8PortConfigEntry 1 }

--    obsolete
--    tnCwr8PortBlockerAging OBJECT-TYPE ::= { tnCwr8PortConfigEntry 2 }

    tnCwr8PortDropTargetPower OBJECT-TYPE
        SYNTAX         Integer32
        UNITS          "mBm"
        MAX-ACCESS     read-create
        STATUS         current
        DESCRIPTION    "The following description applies to the
                        colorless port of the CWR8 card:

                        The drop target power.

                        Current configurable range: -2650 to -400."
        DEFVAL         { -1200 }
        ::= { tnCwr8PortConfigEntry 3 }

--------------------------------------------------------------------------------
-- 11STGE12 Optical Port Config Scalar
--------------------------------------------------------------------------------
    tn11stge12PortConfigAttributeTotal OBJECT-TYPE
        SYNTAX         Integer32
        MAX-ACCESS     read-only
        STATUS         current
        DESCRIPTION    "."
        ::= { tnOpticalPortConfig 65 }

--------------------------------------------------------------------------------
-- 11STGE12 Optical Port Config Table
--------------------------------------------------------------------------------
    tn11stge12PortConfigTable OBJECT-TYPE
        SYNTAX         SEQUENCE OF Tn11stge12PortConfigEntry
        MAX-ACCESS     not-accessible
        STATUS         current
        DESCRIPTION    "The ports on a 11STGE12 optical card."
        ::= { tnOpticalPortConfig 66 }

    tn11stge12PortConfigEntry OBJECT-TYPE
        SYNTAX         Tn11stge12PortConfigEntry
        MAX-ACCESS     not-accessible
        STATUS         current
        DESCRIPTION    "."
        INDEX { ifIndex }
        ::= { tn11stge12PortConfigTable 1 }

    Tn11stge12PortConfigEntry ::=
        SEQUENCE {
            tn11stge12PortConfigFunction INTEGER
        }

    tn11stge12PortConfigFunction OBJECT-TYPE
        SYNTAX         INTEGER {
                         network(1),
                         client(2)
                       }
        MAX-ACCESS     read-only
        STATUS         current
        DESCRIPTION    "Indicates the functional type of this 11STGE12 port."
        ::= { tn11stge12PortConfigEntry 1 }

--------------------------------------------------------------------------------
-- 11DPGE12 Optical Port Config Scalar
--------------------------------------------------------------------------------
    tn11dpge12PortConfigAttributeTotal OBJECT-TYPE
        SYNTAX         Integer32
        MAX-ACCESS     read-only
        STATUS         current
        DESCRIPTION    "."
        ::= { tnOpticalPortConfig 67 }

--------------------------------------------------------------------------------
-- 11DPGE12 Optical Port Config Table
--------------------------------------------------------------------------------
    tn11dpge12PortConfigTable OBJECT-TYPE
        SYNTAX         SEQUENCE OF Tn11dpge12PortConfigEntry
        MAX-ACCESS     not-accessible
        STATUS         current
        DESCRIPTION    "The ports on a 11DPGE12 optical card."
        ::= { tnOpticalPortConfig 68 }

    tn11dpge12PortConfigEntry OBJECT-TYPE
        SYNTAX         Tn11dpge12PortConfigEntry
        MAX-ACCESS     not-accessible
        STATUS         current
        DESCRIPTION    "."
        INDEX { ifIndex }
        ::= { tn11dpge12PortConfigTable 1 }

    Tn11dpge12PortConfigEntry ::=
        SEQUENCE {
            tn11dpge12PortConfigFunction INTEGER
        }

    tn11dpge12PortConfigFunction OBJECT-TYPE
        SYNTAX         INTEGER {
                         network(1),
                         client(2),
                         evoa(3),
                         backplane(4)
                       }
        MAX-ACCESS     read-only
        STATUS         current
        DESCRIPTION    "Indicates the functional type of this 11DPGE12 port."
        ::= { tn11dpge12PortConfigEntry 1 }

--------------------------------------------------------------------------------
-- SFD44 Optical Port Config Scalar
--------------------------------------------------------------------------------
    tnSfd44PortConfigAttributeTotal OBJECT-TYPE
        SYNTAX         Integer32
        MAX-ACCESS     read-only
        STATUS         current
        DESCRIPTION    "."
        ::= { tnOpticalPortConfig 69 }

--------------------------------------------------------------------------------
-- SFD44 Optical Port Config Table
--------------------------------------------------------------------------------
    tnSfd44PortConfigTable OBJECT-TYPE
        SYNTAX         SEQUENCE OF TnSfd44PortConfigEntry
        MAX-ACCESS     not-accessible
        STATUS         current
        DESCRIPTION    "The ports on a SFD44 optical card."
        ::= { tnOpticalPortConfig 70 }

    tnSfd44PortConfigEntry OBJECT-TYPE
        SYNTAX         TnSfd44PortConfigEntry
        MAX-ACCESS     not-accessible
        STATUS         current
        DESCRIPTION    "."
        INDEX { ifIndex }
        ::= { tnSfd44PortConfigTable 1 }

    TnSfd44PortConfigEntry ::=
        SEQUENCE {
            tnSfd44PortConfigFunction INTEGER
        }

    tnSfd44PortConfigFunction OBJECT-TYPE
        SYNTAX         INTEGER {
                         channel(1),
                         mux(2)
                       }
        MAX-ACCESS     read-only
        STATUS         current
        DESCRIPTION    "Indicates the functional type of this SFD44 port:

                        port 1-44 - channel
                        port 45 - mux"
        ::= { tnSfd44PortConfigEntry 1 }

--------------------------------------------------------------------------------
-- DWDM Common Port Config Table
--------------------------------------------------------------------------------
    tnDwdmCmnPortConfigTable OBJECT-TYPE
        SYNTAX         SEQUENCE OF TnDwdmCmnPortConfigEntry
        MAX-ACCESS     not-accessible
        STATUS         current
        DESCRIPTION    "Common attributes against DWDM ports."
        ::= { tnOpticalPortConfig 71 }

    tnDwdmCmnPortConfigEntry OBJECT-TYPE
        SYNTAX         TnDwdmCmnPortConfigEntry
        MAX-ACCESS     not-accessible
        STATUS         current
        DESCRIPTION    "."
        INDEX { ifIndex }
        ::= { tnDwdmCmnPortConfigTable 1 }

    TnDwdmCmnPortConfigEntry ::=
        SEQUENCE {
            tnDwdmCmnPortXfpType                    INTEGER,
            tnDwdmCmnPortAlmProfName                OCTET STRING,
            tnDwdmCmnPortMgracd                     INTEGER,
            tnDwdmCmnPortPowerClassMod              INTEGER,
            tnDwdmCmnPortCustomerLifeCycleState     SnmpAdminString
        }

    tnDwdmCmnPortXfpType OBJECT-TYPE
        SYNTAX         INTEGER {
                         auto(1),
                         user(2),
                         ctSi11(3),
                         ctSs11(4),
                         ctSs12(5),
                         ctSl11(6),
                         ctSl12(7),
                         ctSi161(8),
                         ctSs161(9),
                         ctSs162(10),
                         ctSl161(11),
                         ctSl162(12),
                         ctXi641(13),
                         ctXi642(14),
                         ctXi643(15),
                         ctXi645(16),
                         ctXs641(17),
                         ctXs642B(18),
                         ctXs643(19),
                         ctXs645(20),
                         ctXl641(21),
                         ctXl642(22),
                         ctXl643(23),
                         ctXv642(24),
                         ctXv643(25),
                         ctSs162C(26),
                         ctSl162C(27),
                         ctXi642C(28),
                         ct1000B(29),
                         ct10GB(30),
                         ctSs161AR(31),
                         ctETHEMR(32),
                         ctXP1L12D2(33),
                         ctS41(34),
                         ctL41(35),
                         ctL42(36),
                         ctAnyOC3(37),
                         ctAnyOC12(38),
                         ctAnyOC48(39),
                         ctAnyOC192(40),
                         ctAnyDATAS(41),
                         ctAnyDATAX(42),
                         ctXL642C(43),
                         ctXL642D(44),
                         ctSl162D(45),
                         ctSul11(46),
                         ctSi41(47),
                         ctSs41(48),
                         ctSs42(49),
                         ctSl41(50),
                         ctSl42(51),
                         ct2FCSNI(52),
                         ct2FCLCL(53),
                         ct4FCSNI(54),
                         ct4FCLCL(55),
                         ct8FCSNI(56),
                         ct8FCLCL(57),
                         ct8FCLCLC(58),
                         ct8FCLCLD(59),
                         ctSul12(60),
                         ctSs161A(61),
                         ct1000BT(62),
                         ct1000BCX(63),
                         ct1000BSX(64),
                         ct1000BLX(65),
                         ct1000BZX(66),
                         ctXi641R(67),
                         ctXi642R(68),
                         ctXs642A(69),
                         ctXs643A(70),
                         ctXs645A(71),
                         ctXl642A(72),
                         ctXv642A(73),
                         ct10GBSR(74),
                         ct10GBLR(75),
                         ct10GBER(76),
                         ct10GBLRM(77),
                         ct10GBSW(78),
                         ct10GBLW(79),
                         ct10GBEW(80),
                         ctXs642C(81),
                         ctSul12O(82),
                         ctSs162O(83),
                         ctSl162O(84),
                         ctEvoaFast(85),
                         ctEvoaSlow(86),
                         ct10GBZR(87),
                         ct100BLX10(88),
                         ctSEU12O(89),
                         ctXl64Tu(90),
                         ctBncdvRx(91),
                         ctBncdvTx(92),
                         ctC113G4C(93),
                         ctC113G10C(94),
                         ct4FCOC(95),
                         ct4FCOD(96),
                         ctGeBx20U(97),
                         ctGeBx20D(98),
                         ctGeBx40U(99),
                         ctGeBx40D(100),
                         ctFeBx40U(101),
                         ctFeBx40D(102),
                         ctL642(103),
                         ct100BFXS(104),
                         ctX8FCLCL(105),
                         ctC113G4Cd(106),
                         ctX8FCSNI(107),
                         ct3GSDISH(108),
                         ct3GSDIMH(109),
                         ct1000BT2(110),
                         ctSFEBTEE(111),
                         ctC11G4C(112),
                         ctC43G4C(113),
                         ctC113S10(114),
                         ct16FCLCL(115),
                         ct16FCSNI(116),
                         ctC113G4D(117),
                         ct1000GT2(118),
                         ctS10GBLR(119),
                         ctS10GBSR(120),
                         ctS8FCLCL(121),
                         ctC113G4T(122),
                         ctXL64TCW(123),
                         ct100BULHO(124),
                         ctXs642D(125),
                         ctC2Clr4E(126),
                         ctSxi641(127),
                         ctQ40Gsr4(128),
                         ctQ40Glr4(129),
                         ctSxs642B(130),
                         ctS1E(131),
                         ctSgS11(132),
                         ctSgL11(133),
                         ctSgS41(134),
                         ctSgL41(135),
                         ctSxs642C(136),
                         ctC2Csr10E(137),
                         ctC2Clr4D(138),
                         ct2CBx10U(139),
                         ct2CBx10D(140),
                         ctC4Clr4E(141),
                         ctC4Clr4D(142),
                         ctCFP2ALUMetro(143),
                         ctCFP2ALULH(144),
                         ctC2CER4E(145),
                         ctSL64TUW(146),
                         ct1DC100M(147),
                         ctSWR120(148),
                         ct2Ac100H(149),
                         ct2Ac100(150),
                         ctSXL642(151),
                         ctSXL642C(152),
                         ctSgE1(153),
                         ctSgS11C(154),
                         ctSULS1BOU(155),
                         ctSULS1BOD(156),
                         ct3GSDIE(157),
                         ctQ28CWDM4(158),
                         ctQ28LR4D(159),
                         ctSi641BU(160),
                         ctSi641BD(161),
                         ctSs642BU(162),
                         ctSs642BD(163),
                         ctC4csr4E(164),
                         ctC2cer4D(165),
                         ctXi641BU(166),
                         ctXi641BD(167),
                         ctXs642BU(168),
                         ctXs642BD(169),
                         ctSeul12O(170),
                         ct100BLXS(171),
                         ctQ28LR4E(172),
                         ctQ28SR4E(173),
                         ctSxs642D(174),
                         ctSgT1(175),
                         ctS10GBSRO(176),
                         ctS161BU(177),
                         ctS161BD(178),
                         ctC2ACO(179),
                         ctC2ACOD(180),
                         ctSL64TU(181),
                         ctC4ACO(182),
                         ctSS1GOU(183),
                         ctSS1GOD(184),
                         ctSWR12OL(185),
                         ctSWU12O(186),
                         ct3GSDIM30(187),
                         ctS28SR(188),
                         ctS28LR(189),
                         ctC2Csr10D(190),
                         ctQ28C10E(191),
                         ctQ28ER4D(192),
                         ctSSC38N(193),
                         ctS03C68(194),
                         ctQ28W10m(195),
                         ctSS64TU(196),
--                         obsolete
--                         ctSXS642D(197),
                         ctC2ACOA(198),
                         ctXL64TC(199),
                         ctSWU1GO(200),
                         ctQ56FR4(201),
                         ctQ56LR8(202),
                         ctQ28P2C(203),
                         ctQ28C20u(204),
                         ctQ28C20d(205),
                         ctS28C30u(206),
                         ctS28C30d(207),
                         ctS28C10(208),
                         ctS28D13(209),
                         ctSUL1GOU(210),
                         ctSUL1GOD(211),
                         ctQ28SR4D(212),
                         ctC2DCO4(213),
                         ctS28F32L(214),
                         ctQ40PLR4(215),
                         ctC4ACOO(216),
                         ctSULS1OU(217),
                         ctSULS1OD(218),
                         ctGNSSGM(219),
                         ctS28C10U(220),
                         ctS28C10D(221),
                         ctSLC28D(222),
                         ctQ28DAC(223),
                         ctQ28FR1E(224),
                         ctSGS161(225),
                         ctBMDCO6(226),
                         ctSS64CTU(227),
                         ctC2DCO4O(228),
                         ctBMDCO6EL(229),
                         ctC2DCO4OD(230),
                         ctGeBx80U(231),
                         ctGeBx80D(232),
                         ctQ56LR4(233),
                         ctQ28LR1E(234),
                         ctQ56DR4(235),
                         ctBMDCO6E(236),
                         ctBMDCO6L(237),
                         ctBMDCO12(238),
                         ctQ28P2CS(239),
                         ctSWR1GO(240),
                         ctSWL12O(241)
                       }
        MAX-ACCESS     read-create
        STATUS         current
        DESCRIPTION    "The programmed XFP or SFP type."
        ::= { tnDwdmCmnPortConfigEntry 1 }

    tnDwdmCmnPortAlmProfName OBJECT-TYPE
        SYNTAX         OCTET STRING
        MAX-ACCESS     read-create
        STATUS         current
        DESCRIPTION    "."
        ::= { tnDwdmCmnPortConfigEntry 2 }

    tnDwdmCmnPortMgracd OBJECT-TYPE
        SYNTAX         INTEGER {
                          none(1),
                          cp(2),
                          mgnpln(3),
                          cpmgnpln(4)
                       }
        MAX-ACCESS     read-create
        STATUS         current
        DESCRIPTION    "Indicates if managed by CP, MGNPLN, shared by both or free."
        DEFVAL         { none }
        ::= { tnDwdmCmnPortConfigEntry 3 }

    tnDwdmCmnPortPowerClassMod OBJECT-TYPE
        SYNTAX         INTEGER {
                          any(1),
                          reduced(2)
                       }
        MAX-ACCESS     read-only
        STATUS         current
        DESCRIPTION    "Display the power class info which is needed for pluggable module
                        any     - modules of any power class can be used
                        reduced - only modules with reduced power class can be used."
        ::= { tnDwdmCmnPortConfigEntry 4 }

    tnDwdmCmnPortCustomerLifeCycleState OBJECT-TYPE
        SYNTAX         SnmpAdminString (SIZE(0..45))
        MAX-ACCESS     read-create
        STATUS         current
        DESCRIPTION    "Customer Life Cycle State."
        ::= { tnDwdmCmnPortConfigEntry 5 }

--------------------------------------------------------------------------------
-- DWDM Common and OTU2/ODU2 Line Port Config Table
--------------------------------------------------------------------------------
    tnDwdmCmnLinePortConfigTable OBJECT-TYPE
        SYNTAX         SEQUENCE OF TnDwdmCmnLinePortConfigEntry
        MAX-ACCESS     not-accessible
        STATUS         current
        DESCRIPTION    "Common attributes against DWDM line ports."
        ::= { tnOpticalPortConfig 72 }

    tnDwdmCmnLinePortConfigEntry OBJECT-TYPE
        SYNTAX         TnDwdmCmnLinePortConfigEntry
        MAX-ACCESS     not-accessible
        STATUS         current
        DESCRIPTION    "."
        INDEX { ifIndex }
        ::= { tnDwdmCmnLinePortConfigTable 1 }

    TnDwdmCmnLinePortConfigEntry ::=
        SEQUENCE {
--            obsolete
--            tnDwdmCmnLinePortLoopType                          INTEGER,
            tnDwdmCmnLinePortTransmissionMode                  INTEGER,
            tnDwdmCmnLinePortOchOtu2FecMode                    AluWdmFecMode,
            tnDwdmCmnLinePortOchOtu2Rate                       AluWdmPortOchOtuRate,
            tnDwdmCmnLinePortOtu2TransmittedTti                OCTET STRING,
            tnDwdmCmnLinePortOtu2ExpectedTti                   OCTET STRING,
            tnDwdmCmnLinePortOtu2TimConsequenceAction          AluWdmDisabledEnabled,
            tnDwdmCmnLinePortOtu2TimDetectionMode              AluWdmTimDetectionMode,
            tnDwdmCmnLinePortOdu2PayloadType                   Unsigned32,
            tnDwdmCmnLinePortOdu2OchSignalDefConsequenceAction AluWdmOduOchSignalDefConsequenceAction,
            tnDwdmCmnLinePortOdu2PlmConsequenceAction          TruthValue,
            tnDwdmCmnLinePortOdu2MappingMode                   AluWdmMappingMode,
            tnDwdmCmnLinePortOdu2TpMode                        TruthValue,
            tnDwdmCmnLinePortOdu2TransmittedTti                OCTET STRING,
            tnDwdmCmnLinePortOdu2ExpectedTti                   OCTET STRING,
            tnDwdmCmnLinePortOdu2TimConsequenceAction          AluWdmDisabledEnabled,
            tnDwdmCmnLinePortOdu2TimDetectionMode              AluWdmTimDetectionMode,
            tnDwdmCmnLinePortCrossRegPartner                   Unsigned32,
            tnDwdmCmnLinePortBroadcastFrom                     Unsigned32,
            tnDwdmCmnLinePortRegenResponse                     INTEGER,
            tnDwdmCmnLinePortOtu2holdofftimer                  AluWdmDisabledEnabled,  -- deprecated
            tnDwdmCmnLinePortDemandName                        OCTET STRING,
            tnDwdmCmnLinePortApsEnable                         INTEGER,
            tnDwdmCmnLinePortHoldOffTimer                      AluWdmDisabledEnabled,
            tnDwdmCmnLinePortDMConfigCMEPMode                  INTEGER,
            tnDwdmCmnLinePortDMConfigEnable                    INTEGER,
            tnDwdmCmnLinePortCluster                           SnmpAdminString,
            tnDwdmCmnLinePortDegInterval                       Unsigned32,
            tnDwdmCmnLinePortDegThreshold                      Unsigned32,
            tnDwdmCmnLinePorttxShape                           INTEGER,
            tnDwdmCmnLinePortCdPreComp                         Integer32,
            tnDwdmCmnLinePortPhasenCode                        INTEGER,
            tnDwdmCmnLinePortPolarizationTrack                 INTEGER,
            tnDwdmCmnLinePortClusterConnFrom                   SnmpAdminString,
            tnDwdmCmnLinePortWtpsProtection                    INTEGER,
            tnDwdmCmnLinePortDegUcbIntvl                       Integer32,
            tnDwdmCmnLinePortDegUcbThr                         Integer32,
            tnDwdmCmnLinePortDegUcbMon                         AluWdmEnabledDisabled,
            tnDwdmCmnLinePortDegUcbCa                          AluWdmEnabledDisabled,
            tnDwdmCmnLinePortDesignatedPortMode                INTEGER,
            tnDwdmCmnLinePortDesignatedRegenPair               SnmpAdminString,
            tnDwdmCmnLinePortManagementMode                    INTEGER,
            tnDwdmCmnLinePortOtuOtsigId                        Integer32,
            tnDwdmCmnLinePortOtsigOTSiList                     SnmpAdminString,
            tnDwdmCmnLinePortOtsigOtuStruct                    SnmpAdminString,
            tnDwdmCmnLinePortOtsigProfileId                    Integer32,
            tnDwdmCmnLinePortOtsigCapacity                     Integer32,
            tnDwdmCmnLinePortOtsiPayloadRate                   Integer32,
            tnDwdmCmnLinePortOtsigMgracd                       INTEGER,
            tnDwdmCmnLinePortDegPrefecThr                      Integer32
        }

--    obsolete
--    tnDwdmCmnLinePortLoopType OBJECT-TYPE ::= { tnDwdmCmnLinePortConfigEntry 1 }

    tnDwdmCmnLinePortTransmissionMode OBJECT-TYPE
        SYNTAX         INTEGER {
                         addDrop(1),
                         dropOnly(2),
                         addOnly(3),
                         thru(4),
                         dropContinue(5),
                         crossRegen(6)
                       }
        MAX-ACCESS     read-create
        STATUS         current
        DESCRIPTION    "The transmission mode."
        DEFVAL         { addDrop }
        ::= { tnDwdmCmnLinePortConfigEntry 2 }

    tnDwdmCmnLinePortOchOtu2FecMode OBJECT-TYPE
        SYNTAX         AluWdmFecMode
        MAX-ACCESS     read-create
        STATUS         current
        DESCRIPTION    "OTU2 FEC mode."
        ::= { tnDwdmCmnLinePortConfigEntry 3 }

    tnDwdmCmnLinePortOchOtu2Rate OBJECT-TYPE
        SYNTAX         AluWdmPortOchOtuRate
        MAX-ACCESS     read-create
        STATUS         current
        DESCRIPTION    "OTU2 rate."
        DEFVAL         { otm11G096 }
        ::= { tnDwdmCmnLinePortConfigEntry 4 }

    tnDwdmCmnLinePortOtu2TransmittedTti OBJECT-TYPE
        SYNTAX         OCTET STRING
        MAX-ACCESS     read-create
        STATUS         current
        DESCRIPTION    "OTU2 transmitted TTI."
        DEFVAL         { "" }
        ::= { tnDwdmCmnLinePortConfigEntry 5 }

    tnDwdmCmnLinePortOtu2ExpectedTti OBJECT-TYPE
        SYNTAX         OCTET STRING
        MAX-ACCESS     read-create
        STATUS         current
        DESCRIPTION    "OTU2 expected TTI."
        DEFVAL         { "" }
        ::= { tnDwdmCmnLinePortConfigEntry 6 }

    tnDwdmCmnLinePortOtu2TimConsequenceAction OBJECT-TYPE
        SYNTAX         AluWdmDisabledEnabled
        MAX-ACCESS     read-create
        STATUS         current
        DESCRIPTION    "OTU2 TIM consequence action."
        DEFVAL         { disabled }
        ::= { tnDwdmCmnLinePortConfigEntry 7 }

    tnDwdmCmnLinePortOtu2TimDetectionMode OBJECT-TYPE
        SYNTAX         AluWdmTimDetectionMode
        MAX-ACCESS     read-create
        STATUS         current
        DESCRIPTION    "OTU2 TIM detection mode."
        DEFVAL         { off }
        ::= { tnDwdmCmnLinePortConfigEntry 8 }

    tnDwdmCmnLinePortOdu2PayloadType OBJECT-TYPE
        SYNTAX         Unsigned32
        MAX-ACCESS     read-create
        STATUS         current
        DESCRIPTION    "ODU2 payload type.

                        Current configurable range: 0 to 255."
        DEFVAL         { 253 }
        ::= { tnDwdmCmnLinePortConfigEntry 9 }

    tnDwdmCmnLinePortOdu2OchSignalDefConsequenceAction OBJECT-TYPE
        SYNTAX         AluWdmOduOchSignalDefConsequenceAction
        MAX-ACCESS     read-create
        STATUS         current
        DESCRIPTION    "ODU2 OCH signal def consequence action."
        DEFVAL         { genericAis }
        ::= { tnDwdmCmnLinePortConfigEntry 10 }

    tnDwdmCmnLinePortOdu2PlmConsequenceAction OBJECT-TYPE
        SYNTAX         TruthValue
        MAX-ACCESS     read-create
        STATUS         current
        DESCRIPTION    "PLM consequence action."
        DEFVAL         { false }
        ::= { tnDwdmCmnLinePortConfigEntry 11 }

    tnDwdmCmnLinePortOdu2MappingMode OBJECT-TYPE
        SYNTAX         AluWdmMappingMode
        MAX-ACCESS     read-create
        STATUS         current
        DESCRIPTION    "ODU2 mapping mode."
        DEFVAL         { rsB }
        ::= { tnDwdmCmnLinePortConfigEntry 12 }

    tnDwdmCmnLinePortOdu2TpMode OBJECT-TYPE
        SYNTAX         TruthValue
        MAX-ACCESS     read-create
        STATUS         current
        DESCRIPTION    "ODU2 TP mode."
        DEFVAL         { true }
        ::= { tnDwdmCmnLinePortConfigEntry 13 }

    tnDwdmCmnLinePortOdu2TransmittedTti OBJECT-TYPE
        SYNTAX         OCTET STRING
        MAX-ACCESS     read-create
        STATUS         current
        DESCRIPTION    "ODU2 transmitted TTI."
        DEFVAL         { "" }
        ::= { tnDwdmCmnLinePortConfigEntry 14 }

    tnDwdmCmnLinePortOdu2ExpectedTti OBJECT-TYPE
        SYNTAX         OCTET STRING
        MAX-ACCESS     read-create
        STATUS         current
        DESCRIPTION    "ODU2 expected TTI."
        DEFVAL         { "" }
        ::= { tnDwdmCmnLinePortConfigEntry 15 }

    tnDwdmCmnLinePortOdu2TimConsequenceAction OBJECT-TYPE
        SYNTAX         AluWdmDisabledEnabled
        MAX-ACCESS     read-create
        STATUS         current
        DESCRIPTION    "ODU2 TIM consequence action."
        DEFVAL         { disabled }
        ::= { tnDwdmCmnLinePortConfigEntry 16 }

    tnDwdmCmnLinePortOdu2TimDetectionMode OBJECT-TYPE
        SYNTAX         AluWdmTimDetectionMode
        MAX-ACCESS     read-create
        STATUS         current
        DESCRIPTION    "ODU2 TIM detection mode."
        DEFVAL         { off }
        ::= { tnDwdmCmnLinePortConfigEntry 17 }

    tnDwdmCmnLinePortCrossRegPartner OBJECT-TYPE
        SYNTAX         Unsigned32
        MAX-ACCESS     read-create
        STATUS         current
        DESCRIPTION    "Cross reg partner port."
        DEFVAL         { 0 }
        ::= { tnDwdmCmnLinePortConfigEntry 18 }

    tnDwdmCmnLinePortBroadcastFrom OBJECT-TYPE
        SYNTAX         Unsigned32
        MAX-ACCESS     read-create
        STATUS         current
        DESCRIPTION    "Broadcast From Port."
        DEFVAL         { 0 }
        ::= { tnDwdmCmnLinePortConfigEntry 19 }

    tnDwdmCmnLinePortRegenResponse OBJECT-TYPE
        SYNTAX         INTEGER {
                         laserOn(1),
                         laserOff(2)
                       }
        MAX-ACCESS     read-create
        STATUS         current
        DESCRIPTION    "The regen response mode."
        DEFVAL         { laserOn }
        ::= { tnDwdmCmnLinePortConfigEntry 20 }

    tnDwdmCmnLinePortOtu2holdofftimer OBJECT-TYPE
        SYNTAX         AluWdmDisabledEnabled
        MAX-ACCESS     read-create
        STATUS         deprecated
        DESCRIPTION    "Line port consequent action (whether AIS insertion or
                        laser off) must be delayed by a hold-off timer."
        DEFVAL         { disabled }
        ::= { tnDwdmCmnLinePortConfigEntry 21 }

    tnDwdmCmnLinePortDemandName OBJECT-TYPE
        SYNTAX         OCTET STRING (SIZE(0..140))
        MAX-ACCESS     read-create
        STATUS         current
        DESCRIPTION    "Demand name, which is a string of up to 138 characters
                        to be used as a signal label or identifier."
        DEFVAL         { "" }
        ::= { tnDwdmCmnLinePortConfigEntry 22 }

    tnDwdmCmnLinePortApsEnable OBJECT-TYPE
        SYNTAX         INTEGER {
                         proprietary(1),
                         standard(2)
                       }
        MAX-ACCESS     read-create
        STATUS         current
        DESCRIPTION    "Enable or disable the proprietary APS bytes insertion
                        in the ODU2 overhead."
        DEFVAL         { proprietary }
        ::= { tnDwdmCmnLinePortConfigEntry 23 }

    tnDwdmCmnLinePortHoldOffTimer OBJECT-TYPE
        SYNTAX         AluWdmDisabledEnabled
        MAX-ACCESS     read-create
        STATUS         current
        DESCRIPTION    "Line port consequent action (whether AIS insertion or
                        laser off) must be delayed by a hold-off timer."
        DEFVAL         { disabled }
        ::= { tnDwdmCmnLinePortConfigEntry 24 }

    tnDwdmCmnLinePortDMConfigCMEPMode OBJECT-TYPE
        SYNTAX         INTEGER {
                         bypass(1),
                         source(2),
                         destination(3)
                       }
        MAX-ACCESS     read-create
        STATUS         current
        DESCRIPTION    "Connection Monitoring End Point Mode defined for delay
                        measurement on the specified entity."
        DEFVAL         { bypass }
        ::= { tnDwdmCmnLinePortConfigEntry 25 }

    tnDwdmCmnLinePortDMConfigEnable OBJECT-TYPE
        SYNTAX         INTEGER {
                         enable(1),
                         disable(2)
                       }
        MAX-ACCESS     read-create
        STATUS         current
        DESCRIPTION    "This attribute is used to enable or disable the DM function."
        DEFVAL         { disable }
        ::= { tnDwdmCmnLinePortConfigEntry 26 }

    tnDwdmCmnLinePortCluster OBJECT-TYPE
        SYNTAX         SnmpAdminString (SIZE(0..64))
        MAX-ACCESS     read-create
        STATUS         current
        DESCRIPTION    "This attribute is used to find the corresponding optical
                        line node TID and connection point."
        ::= { tnDwdmCmnLinePortConfigEntry 27 }

    tnDwdmCmnLinePortDegInterval OBJECT-TYPE
        SYNTAX         Unsigned32 (2..10)
        MAX-ACCESS     read-create
        STATUS         current
        DESCRIPTION    "Signal Degrade Interval."
        DEFVAL         { 7 }
        ::= { tnDwdmCmnLinePortConfigEntry 28 }

    tnDwdmCmnLinePortDegThreshold OBJECT-TYPE
        SYNTAX         Unsigned32 (1..856388)
        MAX-ACCESS     read-create
        STATUS         current
        DESCRIPTION    "Signal Degrade threshold."
        DEFVAL         { 40000 }
        ::= { tnDwdmCmnLinePortConfigEntry 29 }

    tnDwdmCmnLinePorttxShape OBJECT-TYPE
        SYNTAX         INTEGER {
                         single(1),
                         super(2),
                         alien(3),
                         superRRC01(4)
                       }
        MAX-ACCESS     read-create
        STATUS         current
        DESCRIPTION    "Specifies the transmit waveshape applied to the optical
                        carrier of a line port."
        DEFVAL         { single }
        ::= { tnDwdmCmnLinePortConfigEntry 30 }

    tnDwdmCmnLinePortCdPreComp OBJECT-TYPE
        SYNTAX         Integer32 (-3100..3100)
        UNITS          "ps/nm"
        MAX-ACCESS     read-create
        STATUS         current
        DESCRIPTION    "Specifies the transmit chromatic dispersion pre-compensation."
        DEFVAL         { 0 }
        ::= { tnDwdmCmnLinePortConfigEntry 31 }

    tnDwdmCmnLinePortPhasenCode OBJECT-TYPE
        SYNTAX         INTEGER {
                         absolute(1),
                         differential(2)
                       }
        MAX-ACCESS     read-create
        STATUS         current
        DESCRIPTION    "Specifies the phase encoding mode."
        DEFVAL         { absolute }
        ::= { tnDwdmCmnLinePortConfigEntry 32 }

    tnDwdmCmnLinePortPolarizationTrack OBJECT-TYPE
        SYNTAX         INTEGER {
                         normal(1),
                         fast(2)
                       }
        MAX-ACCESS     read-create
        STATUS         current
        DESCRIPTION    "State of polarization."
        DEFVAL         { normal }
        ::= { tnDwdmCmnLinePortConfigEntry 33 }

    tnDwdmCmnLinePortClusterConnFrom OBJECT-TYPE
        SYNTAX         SnmpAdminString (SIZE(0..64))
        MAX-ACCESS     read-create
        STATUS         current
        DESCRIPTION    "This attribute is used to find the corresponding optical
                        line node TID and connection from point."
        ::= { tnDwdmCmnLinePortConfigEntry 34 }

    tnDwdmCmnLinePortWtpsProtection OBJECT-TYPE
        SYNTAX         INTEGER {
                         disable(1),
                         enable(2)
                       }
        MAX-ACCESS     read-create
        STATUS         current
        DESCRIPTION    "This attribute is used to enable or disable the WT-PS
                        Protection."
        DEFVAL         { disable }
        ::= { tnDwdmCmnLinePortConfigEntry 35 }

    tnDwdmCmnLinePortDegUcbIntvl OBJECT-TYPE
        SYNTAX         Integer32
        MAX-ACCESS     read-create
        STATUS         current
        DESCRIPTION    "Degrade interval specifies the number of consecutive
                        bad intervals (base unit 5 ms) to be de-tected before
                        declaring a dDEGUCB (signal degrade) defect for a line
                        port.  The defect is cleared if degintvl consecutive
                        good intervals are detected."
        DEFVAL         { 1 }
        ::= { tnDwdmCmnLinePortConfigEntry 36 }

    tnDwdmCmnLinePortDegUcbThr OBJECT-TYPE
        SYNTAX         Integer32
        MAX-ACCESS     read-create
        STATUS         current
        DESCRIPTION    "Degrade threshold (degucbthr) specifies a number of
                        uncorrectable errored blocks from the FEC decoder in
                        the interval degucbintvl as used for dDEGUCB detection
                        for a line port."
        DEFVAL         { 11 }
        ::= { tnDwdmCmnLinePortConfigEntry 37 }

    tnDwdmCmnLinePortDegUcbMon OBJECT-TYPE
        SYNTAX         AluWdmEnabledDisabled
        MAX-ACCESS     read-create
        STATUS         current
        DESCRIPTION    "degraded UCB monitor enables/disables dDEGUCB detection."
        DEFVAL         { enabled }
        ::= { tnDwdmCmnLinePortConfigEntry 38 }

    tnDwdmCmnLinePortDegUcbCa OBJECT-TYPE
        SYNTAX         AluWdmEnabledDisabled
        MAX-ACCESS     read-create
        STATUS         current
        DESCRIPTION    "Configures the consequent action for the dDEGUCB defect
                        (signal degrade)."
        DEFVAL         { enabled }
        ::= { tnDwdmCmnLinePortConfigEntry 39 }

    tnDwdmCmnLinePortDesignatedPortMode OBJECT-TYPE
        SYNTAX         INTEGER {
                         addDrop(1),
                         dropOnly(2),
                         addOnly(3),
                         thru(4),
                         dropContinue(5),
                         crossRegen(6)
                       }
        MAX-ACCESS     read-create
        STATUS         current
        DESCRIPTION    "."
        DEFVAL         { addDrop }
        ::= { tnDwdmCmnLinePortConfigEntry 40 }

    tnDwdmCmnLinePortDesignatedRegenPair OBJECT-TYPE
        SYNTAX         SnmpAdminString (SIZE(0..32))
        MAX-ACCESS     read-create
        STATUS         current
        DESCRIPTION    "."
        DEFVAL         { "" }
        ::= { tnDwdmCmnLinePortConfigEntry 41 }

    tnDwdmCmnLinePortManagementMode OBJECT-TYPE
        SYNTAX         INTEGER {
                         unknown(1),
                         otu(2),
                         otsig(3)
                       }
        MAX-ACCESS     read-create
        STATUS         current
        DESCRIPTION    "."
        DEFVAL         { otu }
        ::= { tnDwdmCmnLinePortConfigEntry 42 }

    tnDwdmCmnLinePortOtuOtsigId OBJECT-TYPE
        SYNTAX         Integer32 (0..255)
        MAX-ACCESS     read-only
        STATUS         current
        DESCRIPTION    "Line Port Otu OtsigId."
        DEFVAL         { 0 }
        ::= { tnDwdmCmnLinePortConfigEntry 43 }

    tnDwdmCmnLinePortOtsigOTSiList OBJECT-TYPE
        SYNTAX         SnmpAdminString (SIZE(0..16))
        MAX-ACCESS     read-only
        STATUS         current
        DESCRIPTION    "."
        ::= { tnDwdmCmnLinePortConfigEntry 44 }

    tnDwdmCmnLinePortOtsigOtuStruct OBJECT-TYPE
        SYNTAX         SnmpAdminString (SIZE(0..192))
        MAX-ACCESS     read-create
        STATUS         current
        DESCRIPTION    "."
        ::= { tnDwdmCmnLinePortConfigEntry 45 }

    tnDwdmCmnLinePortOtsigProfileId OBJECT-TYPE
        SYNTAX         Integer32 (0..255)
        MAX-ACCESS     read-create
        STATUS         current
        DESCRIPTION    "."
        DEFVAL         { 0 }
        ::= { tnDwdmCmnLinePortConfigEntry 46 }

    tnDwdmCmnLinePortOtsigCapacity OBJECT-TYPE
        SYNTAX         Integer32 (0..500)
        MAX-ACCESS     read-only
        STATUS         current
        DESCRIPTION    "."
        DEFVAL         { 0 }
        ::= { tnDwdmCmnLinePortConfigEntry 47 }

    tnDwdmCmnLinePortOtsiPayloadRate OBJECT-TYPE
        SYNTAX         Integer32 (0..500)
        MAX-ACCESS     read-only
        STATUS         current
        DESCRIPTION    "."
        DEFVAL         { 0 }
        ::= { tnDwdmCmnLinePortConfigEntry 48 }

    tnDwdmCmnLinePortOtsigMgracd OBJECT-TYPE
        SYNTAX         INTEGER {
                         none(1),
                         cp(2),
                         mgnpln(3),
                         cpmgnpln(4)
                       }
        MAX-ACCESS     read-create
        STATUS         current
        DESCRIPTION    "."
        DEFVAL         { none }
        ::= { tnDwdmCmnLinePortConfigEntry 49 }

    tnDwdmCmnLinePortDegPrefecThr OBJECT-TYPE
        SYNTAX         Integer32
        MAX-ACCESS     read-create
        STATUS         current
        DESCRIPTION    "Pre-FEC BER threshold.
                        current range 0 to 4000.
                        1.00E+00 -> 0
                        1.00E-02 -> 200 ( -log(1.00E-02)*100 = 200)
                        0.00E+00 ->> 4000"
        DEFVAL         { 170 }
        ::= { tnDwdmCmnLinePortConfigEntry 50 }

--------------------------------------------------------------------------------
-- DWDM Common OTU2/ODU2 Client Port Config Table
--------------------------------------------------------------------------------
    tnDwdmCmnClientPortConfigTable OBJECT-TYPE
        SYNTAX         SEQUENCE OF TnDwdmCmnClientPortConfigEntry
        MAX-ACCESS     not-accessible
        STATUS         current
        DESCRIPTION    "Common attributes against DWDM client ports."
        ::= { tnOpticalPortConfig 73 }

    tnDwdmCmnClientPortConfigEntry OBJECT-TYPE
        SYNTAX         TnDwdmCmnClientPortConfigEntry
        MAX-ACCESS     not-accessible
        STATUS         current
        DESCRIPTION    "."
        INDEX { ifIndex }
        ::= { tnDwdmCmnClientPortConfigTable 1 }

    TnDwdmCmnClientPortConfigEntry ::=
        SEQUENCE {
--            obsolete
--            tnDwdmCmnClientPortLoopType                 INTEGER,
            tnDwdmCmnClientPortLosProp                  INTEGER,
            tnDwdmCmnClientPortTs1                      Unsigned32,
            tnDwdmCmnClientPortTs2                      Unsigned32,
            tnDwdmCmnClientPortOchOtu2FecMode           AluWdmFecMode,
            tnDwdmCmnClientPortOchOtu2Rate              AluWdmPortOchOtuRate,
            tnDwdmCmnClientPortOtu2TransmittedTti       OCTET STRING,
            tnDwdmCmnClientPortOtu2ExpectedTti          OCTET STRING,
            tnDwdmCmnClientPortOtu2TimConsequenceAction AluWdmDisabledEnabled,
            tnDwdmCmnClientPortOtu2TimDetectionMode     AluWdmTimDetectionMode,
            tnDwdmCmnClientPortOdu2TransmittedTti       OCTET STRING,
            tnDwdmCmnClientPortOdu2ExpectedTti          OCTET STRING,
            tnDwdmCmnClientPortOdu2TimDetectionMode     AluWdmTimDetectionMode,
            tnDwdmCmnClientPortProtectionTs1            Unsigned32,
            tnDwdmCmnClientPortProtectionTs2            Unsigned32,
            tnDwdmCmnClientPortTsMap                    OCTET STRING,
            tnDwdmCmnClientPortContainer                INTEGER,
            tnDwdmCmnClientPortCSF                      INTEGER,
            tnDwdmCmnClientPortSSF                      INTEGER,
            tnDwdmCmnClientPortScramMode                INTEGER,
            tnDwdmCmnClientPortDegInterval              Unsigned32,
            tnDwdmCmnClientPortDegThreshold             Unsigned32,
            tnDwdmCmnClientPortHoldOffTimer             AluWdmEnabledDisabled,
            tnDwdmCmnClientPortYcableMode               AluPortYcableMode,
            tnDwdmCmnClientPortEthFecMode               INTEGER,
            tnDwdmCmnClientPortHoldOffTimerValue        Unsigned32,
            tnDwdmCmnClientPortFlsState                 INTEGER,
            tnDwdmCmnClientPortServerPort               INTEGER,
            tnDwdmCmnClientPortInOpsbAction             INTEGER,
            tnDwdmCmnClientPortSSFDelayTimer            Unsigned32,
            tnDwdmCmnClientPortFecBypassInd             INTEGER,
            tnDwdmCmnClientPortSSFDelayCa               INTEGER,
            tnDwdmCmnClientPortSsdca                    INTEGER,
            tnDwdmCmnClientPortFlexGfpSize              Unsigned32,
            tnDwdmCmnClientPortSdiRate                  INTEGER,
            tnDwdmCmnClientPortGfpFcs                   INTEGER,
            tnDwdmCmnClientPortCSFHoldOff               INTEGER,
            tnDwdmCmnClientPortSSFHoldOff               INTEGER,
            tnDwdmCmnClientPortSignalMode               INTEGER,
            tnDwdmCmnClientPortCSFDelayTimer            Unsigned32,
            tnDwdmCmnClientPortSSFOnOCIAction           AluWdmDisabledEnabled
        }

--    obsolete tnDwdmCmnClientPortLoopType OBJECT-TYPE ::= { tnDwdmCmnClientPortConfigEntry 1 }

    tnDwdmCmnClientPortLosProp OBJECT-TYPE
        SYNTAX         INTEGER {
                         laserOn(1),
                         laserOff(2)
                       }
        MAX-ACCESS     read-create
        STATUS         current
        DESCRIPTION    "The LOS propagation."
        DEFVAL         { laserOn }
        ::= { tnDwdmCmnClientPortConfigEntry 2 }

    tnDwdmCmnClientPortTs1 OBJECT-TYPE
        SYNTAX         Unsigned32
        MAX-ACCESS     read-create
        STATUS         current
        DESCRIPTION    "Working time slot 1, ODU1 tributary (11STMM10),
                        ODU2-like structure (11DPGE12).  Unassigned is
                        represented by value 0.

                        Current configurable range (11STMM10): 0, 1 to 4
                        Current configurable range (11DPGE12): 0, 1 to 2."
        DEFVAL         { 0 }
        ::= { tnDwdmCmnClientPortConfigEntry 3 }

    tnDwdmCmnClientPortTs2 OBJECT-TYPE
        SYNTAX         Unsigned32
        MAX-ACCESS     read-create
        STATUS         current
        DESCRIPTION    "Working time slot 2, STS1/STS3c (11STMM10).
                        Unassigned is represented by value 0.

                        Current configurable range (11STMM10): 0, 1, 4, 7, 10, ... 46
                        Current configurable range (11DPGE12): 0 to 10."
        DEFVAL         { 0 }
        ::= { tnDwdmCmnClientPortConfigEntry 4 }

    tnDwdmCmnClientPortOchOtu2FecMode OBJECT-TYPE
        SYNTAX         AluWdmFecMode
        MAX-ACCESS     read-create
        STATUS         current
        DESCRIPTION    "OTU2 FEC mode."
        DEFVAL         { g709Fec }
        ::= { tnDwdmCmnClientPortConfigEntry 5 }

    tnDwdmCmnClientPortOchOtu2Rate OBJECT-TYPE
        SYNTAX         AluWdmPortOchOtuRate
        MAX-ACCESS     read-create
        STATUS         current
        DESCRIPTION    "OTU2 rate."
        DEFVAL         { otm10G709 }
        ::= { tnDwdmCmnClientPortConfigEntry 6 }

    tnDwdmCmnClientPortOtu2TransmittedTti OBJECT-TYPE
        SYNTAX         OCTET STRING
        MAX-ACCESS     read-create
        STATUS         current
        DESCRIPTION    "OTU2 transmitted TTI."
        DEFVAL         { "" }
        ::= { tnDwdmCmnClientPortConfigEntry 7 }

    tnDwdmCmnClientPortOtu2ExpectedTti OBJECT-TYPE
        SYNTAX         OCTET STRING
        MAX-ACCESS     read-create
        STATUS         current
        DESCRIPTION    "OTU2 expected TTI."
        DEFVAL         { "" }
        ::= { tnDwdmCmnClientPortConfigEntry 8 }

    tnDwdmCmnClientPortOtu2TimConsequenceAction OBJECT-TYPE
        SYNTAX         AluWdmDisabledEnabled
        MAX-ACCESS     read-create
        STATUS         current
        DESCRIPTION    "OTU2 TIM consequence action."
        DEFVAL         { disabled }
        ::= { tnDwdmCmnClientPortConfigEntry 9 }

    tnDwdmCmnClientPortOtu2TimDetectionMode OBJECT-TYPE
        SYNTAX         AluWdmTimDetectionMode
        MAX-ACCESS     read-create
        STATUS         current
        DESCRIPTION    "OTU2 TIM detection mode."
        DEFVAL         { off }
        ::= { tnDwdmCmnClientPortConfigEntry 10 }

    tnDwdmCmnClientPortOdu2TransmittedTti OBJECT-TYPE
        SYNTAX         OCTET STRING
        MAX-ACCESS     read-create
        STATUS         current
        DESCRIPTION    "ODU2 transmitted TTI."
        DEFVAL         { "" }
        ::= { tnDwdmCmnClientPortConfigEntry 11 }

    tnDwdmCmnClientPortOdu2ExpectedTti OBJECT-TYPE
        SYNTAX         OCTET STRING
        MAX-ACCESS     read-create
        STATUS         current
        DESCRIPTION    "ODU2 expected TTI."
        DEFVAL         { "" }
        ::= { tnDwdmCmnClientPortConfigEntry 12 }

    tnDwdmCmnClientPortOdu2TimDetectionMode OBJECT-TYPE
        SYNTAX         AluWdmTimDetectionMode
        MAX-ACCESS     read-create
        STATUS         current
        DESCRIPTION    "ODU2 TIM detection mode."
        DEFVAL         { off }
        ::= { tnDwdmCmnClientPortConfigEntry 13 }

    tnDwdmCmnClientPortProtectionTs1 OBJECT-TYPE
        SYNTAX         Unsigned32
        MAX-ACCESS     read-create
        STATUS         current
        DESCRIPTION    "Protection time slot 1, ODU1 tributary (11STMM10),
                        line port number (11DPGE12).  Unassigned is
                        represented by value 0.

                        Current configurable range (11STMM10): 0, 1 to 4
                        Current configurable range (11DPGE12): 0, 1 to 2."
        DEFVAL         { 0 }
        ::= { tnDwdmCmnClientPortConfigEntry 14 }

    tnDwdmCmnClientPortProtectionTs2 OBJECT-TYPE
        SYNTAX         Unsigned32
        MAX-ACCESS     read-create
        STATUS         current
        DESCRIPTION    "Protection time slot 2, STS1/STS3c (11STMM10).
                        Unassigned is represented by value 0.

                        Current configurable range (11STMM10): 0, 1, 4, 7, 10, ... 46
                        Current configurable range (11DPGE12): 0 to 10."
        DEFVAL         { 0 }
        ::= { tnDwdmCmnClientPortConfigEntry 15 }

    tnDwdmCmnClientPortTsMap OBJECT-TYPE
        SYNTAX         OCTET STRING (SIZE(0..4))
        MAX-ACCESS     read-create
        STATUS         current
        DESCRIPTION    "Client port time slot bit map.  First 2 bytes
                        are for line 2 and the next 2 bytes are for
                        line 1."
        DEFVAL         { "" }
        ::= { tnDwdmCmnClientPortConfigEntry 16 }

    tnDwdmCmnClientPortContainer OBJECT-TYPE
        SYNTAX         INTEGER {
                         none(1),
                         optsg(2),
                         odu0(3),
                         odu1(4),
                         oduflex(5),
                         odu2(6),
                         odu2e(7),
                         odu3(8),
                         odu3e(9),
                         odu3e2(10),
                         odu4(11),
                         oduf(12),
                         oduflex3gsdi(13),
                         oduflexsdr(14),
                         oduflexfc400(15),
                         odutc1(16),
                         odutc4(17)
                       }
        MAX-ACCESS     read-create
        STATUS         current
        DESCRIPTION    "Specifies the mapping mode that will be used
                        for client signal."
        DEFVAL         { none }
        ::= { tnDwdmCmnClientPortConfigEntry 17 }

    tnDwdmCmnClientPortCSF OBJECT-TYPE
        SYNTAX         INTEGER {
                         disabled(1),
                         laserOff(2)
                       }
        MAX-ACCESS     read-create
        STATUS         current
        DESCRIPTION    "Defines the port consequent action behavior
                        in case of CSF"
        DEFVAL         { laserOff }
        ::= { tnDwdmCmnClientPortConfigEntry 18 }

    tnDwdmCmnClientPortSSF OBJECT-TYPE
        SYNTAX         INTEGER {
                         disabled(1),
                         laserOff(2)
                       }
        MAX-ACCESS     read-create
        STATUS         current
        DESCRIPTION    "Defines the port consequent action behavior
                        in case of SSF"
        DEFVAL         { disabled }
        ::= { tnDwdmCmnClientPortConfigEntry 19 }

    tnDwdmCmnClientPortScramMode OBJECT-TYPE
        SYNTAX         INTEGER {
                         enable(1),
                         disable(2)
                       }
        MAX-ACCESS     read-create
        STATUS         current
        DESCRIPTION    "."
        DEFVAL         { disable }
        ::= { tnDwdmCmnClientPortConfigEntry 20 }

    tnDwdmCmnClientPortDegInterval OBJECT-TYPE
        SYNTAX         Unsigned32 (2..10)
        MAX-ACCESS     read-create
        STATUS         current
        DESCRIPTION    "ODU2 Degrade Interval."
        DEFVAL         { 7 }
        ::= { tnDwdmCmnClientPortConfigEntry 21 }

    tnDwdmCmnClientPortDegThreshold OBJECT-TYPE
        SYNTAX         Unsigned32 (0..'ffffffff'h)
        MAX-ACCESS     read-create
        STATUS         current
        DESCRIPTION    "Degrade threshold."
        ::= { tnDwdmCmnClientPortConfigEntry 22 }

    tnDwdmCmnClientPortHoldOffTimer OBJECT-TYPE
        SYNTAX         AluWdmEnabledDisabled
        MAX-ACCESS     read-create
        STATUS         current
        DESCRIPTION    "Hold Off Timer for client port."
        DEFVAL         { enabled }
        ::= { tnDwdmCmnClientPortConfigEntry 23 }

    tnDwdmCmnClientPortYcableMode OBJECT-TYPE
        SYNTAX         AluPortYcableMode
        MAX-ACCESS     read-create
        STATUS         current
        DESCRIPTION    "The desired administrative Y-Cable mode of this port."
        DEFVAL         { legacy }
        ::= { tnDwdmCmnClientPortConfigEntry 24 }

    tnDwdmCmnClientPortEthFecMode OBJECT-TYPE
        SYNTAX         INTEGER {
                         ethNoFec(1),
                         ethBjfec(2)
                       }
        MAX-ACCESS     read-create
        STATUS         current
        DESCRIPTION    "Ethernet Fec Mode."
        DEFVAL         { ethNoFec }
        ::= { tnDwdmCmnClientPortConfigEntry 25 }

    tnDwdmCmnClientPortHoldOffTimerValue OBJECT-TYPE
        SYNTAX         Unsigned32 (0..10000)
        UNITS          "milli-seconds"
        MAX-ACCESS     read-create
        STATUS         current
        DESCRIPTION    "Hold Off Timer Value for client port."
        DEFVAL         { 0 }
        ::= { tnDwdmCmnClientPortConfigEntry 26 }

    tnDwdmCmnClientPortFlsState OBJECT-TYPE
        SYNTAX         INTEGER {
                         off(1),
                         on(2),
                         auto(3)
                       }
        MAX-ACCESS     read-only
        STATUS         current
        DESCRIPTION    "Shows whether a forced laser shutdown state is present
                        triggered by a Y-cable protection group or by the LPT feature."
        DEFVAL         { off }
        ::= { tnDwdmCmnClientPortConfigEntry 27 }

    tnDwdmCmnClientPortServerPort OBJECT-TYPE
        SYNTAX         INTEGER {
                         spunassigned(1),
                         spotu1(2),
                         spotu2(3),
                         spotu3(4),
                         spotu4(5),
                         spotu5(6),
                         spotu6(7),
                         spotu7(8),
                         spotu8(9),
                         spotu9(10),
                         spotu10(11)
                       }
        MAX-ACCESS     read-create
        STATUS         current
        DESCRIPTION    "Specifies the server port values."
        DEFVAL         { spunassigned }
        ::= { tnDwdmCmnClientPortConfigEntry 28 }

    tnDwdmCmnClientPortInOpsbAction OBJECT-TYPE
        SYNTAX         INTEGER {
                         yes(1),
                         no(2)
                       }
        MAX-ACCESS     read-create
        STATUS         current
        DESCRIPTION    "yes - The port is used as input port for an OPSB
                              group and therefore the laser is switched off
                              in case of equipment failure.
                        no  - The port is not used as input port for an
                              OPSB group and therefore the laser is not
                              switched off in case of equipment failure."
        DEFVAL         { no }
        ::= { tnDwdmCmnClientPortConfigEntry 29 }

    tnDwdmCmnClientPortSSFDelayTimer OBJECT-TYPE
        SYNTAX         Unsigned32
        MAX-ACCESS     read-create
        STATUS         current
        DESCRIPTION    "Controls the period in which laser off CA triggered
                        by a SSF condition is delayed, i.e., the laser shut
                        down is performed after ssfdelaytimer is expired and
                        SSF condition is still pre-sent.

                        Current configurable range:

                        0 to 255 period in steps of 10 milli-second."
        DEFVAL         { 20 }
        ::= { tnDwdmCmnClientPortConfigEntry 30 }

    tnDwdmCmnClientPortFecBypassInd OBJECT-TYPE
        SYNTAX         INTEGER {
                         disable(1),
                         enable(2)
                       }
        MAX-ACCESS     read-create
        STATUS         current
        DESCRIPTION    "FEC bypass indication."
        DEFVAL         { disable }
        ::= { tnDwdmCmnClientPortConfigEntry 31 }

    tnDwdmCmnClientPortSSFDelayCa OBJECT-TYPE
        SYNTAX         INTEGER {
                         lfi(1),
                         idle(2)
                       }
        MAX-ACCESS     read-create
        STATUS         current
        DESCRIPTION    "The parameter controls the inserted ETH maintenance signal
                        after ODU SSF detection while ssfdelaytimer is running.

                        lfi  - LFI is inserted while ssfdelaytimer is running
                        idle - Idle is inserted while ssfdelaytimer is running."
        DEFVAL         { lfi }
        ::= { tnDwdmCmnClientPortConfigEntry 32 }

    tnDwdmCmnClientPortSsdca OBJECT-TYPE
        SYNTAX         INTEGER {
                         disabled(1),
                         laseroff(2)
                       }
        MAX-ACCESS     read-create
        STATUS         current
        DESCRIPTION    "Specifies whether the client laser is switched off if
                        server signal degrade defect is present.

                        disabled - no laser shutdown in case of ssd
                        laseroff - laser shutdown in case of ssd."
        DEFVAL         { disabled }
        ::= { tnDwdmCmnClientPortConfigEntry 33 }

    tnDwdmCmnClientPortFlexGfpSize OBJECT-TYPE
        SYNTAX         Unsigned32
        MAX-ACCESS     read-create
        STATUS         current
        DESCRIPTION    "Flex Gfp Size."
        DEFVAL         { 1 }
        ::= { tnDwdmCmnClientPortConfigEntry 34 }

    tnDwdmCmnClientPortSdiRate OBJECT-TYPE
        SYNTAX         INTEGER {
                         nominal(1),
                         subrate(2)
                       }
        MAX-ACCESS     read-create
        STATUS         current
        DESCRIPTION    "Bit rate factor for SDI video signals, either nominal rate
                        or 1/1.001 subrate."
        DEFVAL         { nominal }
        ::= { tnDwdmCmnClientPortConfigEntry 35 }

    tnDwdmCmnClientPortGfpFcs OBJECT-TYPE
        SYNTAX         INTEGER {
                         standard(1),
                         legacy(2)
                       }
        MAX-ACCESS     read-create
        STATUS         current
        DESCRIPTION    "Specifies how to perform GFP-F framer FCS (Frame Check
                        Sequence) overhead on the source and sink point.  To
                        interwork with other cards, it shall be provisioned as
                        standard."
        DEFVAL         { standard }
        ::= { tnDwdmCmnClientPortConfigEntry 36 }

    tnDwdmCmnClientPortCSFHoldOff OBJECT-TYPE
        SYNTAX         INTEGER {
                         off(1),
                         on(2)
                       }
        MAX-ACCESS     read-create
        STATUS         current
        DESCRIPTION    "CSF Hold Off."
        DEFVAL         { on }
        ::= { tnDwdmCmnClientPortConfigEntry 37 }

    tnDwdmCmnClientPortSSFHoldOff OBJECT-TYPE
        SYNTAX         INTEGER {
                         off(1),
                         on(2)
                       }
        MAX-ACCESS     read-create
        STATUS         current
        DESCRIPTION    "SSF Hold Off."
        DEFVAL         { on }
        ::= { tnDwdmCmnClientPortConfigEntry 38 }

    tnDwdmCmnClientPortSignalMode OBJECT-TYPE
        SYNTAX         INTEGER {
                         transparent(1),
                         terminated(2)
                       }
        MAX-ACCESS     read-create
        STATUS         current
        DESCRIPTION    "Specifies whether 100GBE PCS layer should be terminated
                        or transparent."
        DEFVAL         { transparent }
        ::= { tnDwdmCmnClientPortConfigEntry 39 }

    tnDwdmCmnClientPortCSFDelayTimer OBJECT-TYPE
        SYNTAX         Unsigned32
        MAX-ACCESS     read-create
        STATUS         current
        DESCRIPTION    "controls the period for which laser off CA triggered by
                        a CSF condition is delayed. i.e. the laser shutdown is
                        performed after CSF Delay Timer is expired and CSF
                        condition is still present."
        DEFVAL         { 0 }
        ::= { tnDwdmCmnClientPortConfigEntry 40 }

    tnDwdmCmnClientPortSSFOnOCIAction OBJECT-TYPE
        SYNTAX         AluWdmDisabledEnabled
        MAX-ACCESS     read-create
        STATUS         current
        DESCRIPTION    "."
        DEFVAL         { disabled }
        ::= { tnDwdmCmnClientPortConfigEntry 41 }

--------------------------------------------------------------------------------
-- RSMON Ingress Port Config Table
--------------------------------------------------------------------------------
    tnRsmonIngrPortConfigTable OBJECT-TYPE
        SYNTAX         SEQUENCE OF TnRsmonIngrPortConfigEntry
        MAX-ACCESS     not-accessible
        STATUS         current
        DESCRIPTION    "Common attributes against RSMON Ingress supported ports."
        ::= { tnOpticalPortConfig 74 }

    tnRsmonIngrPortConfigEntry OBJECT-TYPE
        SYNTAX         TnRsmonIngrPortConfigEntry
        MAX-ACCESS     not-accessible
        STATUS         current
        DESCRIPTION    "."
        INDEX { ifIndex }
        ::= { tnRsmonIngrPortConfigTable 1 }

    TnRsmonIngrPortConfigEntry ::=
        SEQUENCE {
            tnRsmonIngrPortTransmittedTti       OCTET STRING,
            tnRsmonIngrPortExpectedTti          OCTET STRING,
            tnRsmonIngrPortTimod                INTEGER,
            tnRsmonIngrPortTimDetection         TruthValue,
            tnRsmonIngrPortTimConsequenceAction AluWdmDisabledEnabled,
--            obsolete
--            tnRsmonIngrPortTimDetectionMode     INTEGER,
            tnRsmonIngrPortSigMode              INTEGER
        }

    tnRsmonIngrPortTransmittedTti OBJECT-TYPE
        SYNTAX         OCTET STRING
        MAX-ACCESS     read-create
        STATUS         current
        DESCRIPTION    "RSMON transmitted TTI."
        DEFVAL         { "" }
        ::= { tnRsmonIngrPortConfigEntry 1 }

    tnRsmonIngrPortExpectedTti OBJECT-TYPE
        SYNTAX         OCTET STRING
        MAX-ACCESS     read-create
        STATUS         current
        DESCRIPTION    "RSMON expected TTI."
        DEFVAL         { "" }
        ::= { tnRsmonIngrPortConfigEntry 2 }

    tnRsmonIngrPortTimod OBJECT-TYPE
        SYNTAX         INTEGER {
                         notApplicable(1),
                         specific16Byte(2),
                         nonSpecificSingleByte(3),
                         specificSingleByte(4),
                         string64(5)
                       }
        MAX-ACCESS     read-create
        STATUS         current
        DESCRIPTION    "RSMON TIMOD."
        DEFVAL         { specific16Byte }
        ::= { tnRsmonIngrPortConfigEntry 3 }

    tnRsmonIngrPortTimDetection OBJECT-TYPE
        SYNTAX         TruthValue
        MAX-ACCESS     read-create
        STATUS         current
        DESCRIPTION    "RSMON TIM detection."
        DEFVAL         { false }
        ::= { tnRsmonIngrPortConfigEntry 4 }

    tnRsmonIngrPortTimConsequenceAction OBJECT-TYPE
        SYNTAX         AluWdmDisabledEnabled
        MAX-ACCESS     read-create
        STATUS         current
        DESCRIPTION    "RSMON TIM consequence action."
        DEFVAL         { disabled }
        ::= { tnRsmonIngrPortConfigEntry 5 }

--    obsolete tnRsmonIngrPortTimDetectionMode OBJECT-TYPE ::= { tnRsmonIngrPortConfigEntry 6 }

    tnRsmonIngrPortSigMode OBJECT-TYPE
        SYNTAX         INTEGER {
                         transparent(1),
                         terminated(2)
                       }
        MAX-ACCESS     read-create
        STATUS         current
        DESCRIPTION    "RSMON signal mode."
        DEFVAL         { transparent }
        ::= { tnRsmonIngrPortConfigEntry 7 }

--------------------------------------------------------------------------------
-- MSMON Port Config Table
--------------------------------------------------------------------------------
    tnMsmonPortConfigTable OBJECT-TYPE
        SYNTAX         SEQUENCE OF TnMsmonPortConfigEntry
        MAX-ACCESS     not-accessible
        STATUS         current
        DESCRIPTION    "Common attributes against MSMON supported ports."
        ::= { tnOpticalPortConfig 75 }

    tnMsmonPortConfigEntry OBJECT-TYPE
        SYNTAX         TnMsmonPortConfigEntry
        MAX-ACCESS     not-accessible
        STATUS         current
        DESCRIPTION    "."
        INDEX { ifIndex }
        ::= { tnMsmonPortConfigTable 1 }

    TnMsmonPortConfigEntry ::=
        SEQUENCE {
            tnMsmonPortMappingMode AluWdmMappingMode,
            tnMsmonPortExcThLevel  INTEGER,
            tnMsmonPortDegThLevel  INTEGER
        }

    tnMsmonPortMappingMode OBJECT-TYPE
        SYNTAX         AluWdmMappingMode
        MAX-ACCESS     read-create
        STATUS         current
        DESCRIPTION    "MSMON mapping mode."
        DEFVAL         { rsB }
        ::= { tnMsmonPortConfigEntry 1 }

    tnMsmonPortExcThLevel OBJECT-TYPE
        SYNTAX         INTEGER {
                         e3(1),
                         e4(2),
                         e5(3)
                       }
        MAX-ACCESS     read-create
        STATUS         current
        DESCRIPTION    "BER Threshold for excessive BER defect (SFTH)."
        DEFVAL         { e3 }
        ::= { tnMsmonPortConfigEntry 2 }

    tnMsmonPortDegThLevel OBJECT-TYPE
        SYNTAX         INTEGER {
                         e5(1),
                         e6(2),
                         e7(3),
                         e8(4),
                         e9(5)
                       }
        MAX-ACCESS     read-create
        STATUS         current
        DESCRIPTION    "BER Threshold for SD defect (SDTH)."
        DEFVAL         { e6 }
        ::= { tnMsmonPortConfigEntry 3 }

--------------------------------------------------------------------------------
-- OSC SFP Port Config Table
--------------------------------------------------------------------------------
    tnOscSfpPortConfigTable OBJECT-TYPE
        SYNTAX         SEQUENCE OF TnOscSfpPortConfigEntry
        MAX-ACCESS     not-accessible
        STATUS         current
        DESCRIPTION    "OSC SFP attributes."
        ::= { tnOpticalPortConfig 76 }

    tnOscSfpPortConfigEntry OBJECT-TYPE
        SYNTAX         TnOscSfpPortConfigEntry
        MAX-ACCESS     not-accessible
        STATUS         current
        DESCRIPTION    "."
        INDEX { ifIndex }
        ::= { tnOscSfpPortConfigTable 1 }

    TnOscSfpPortConfigEntry ::=
        SEQUENCE {
--            obsolete
--            tnOscSfpPortType                  INTEGER,
            tnOscSfpTemperature               Integer32,
            tnOscMtu                          Integer32,
            tnOscMtuNeg                       Integer32,
            tnOscEnable                       TruthValue,
            tnOscConnId                       Unsigned32,
            tnOscPortInfoETR                  TruthValue,
            tnOscIPv6LinkLocalInetAddress     InetAddress,
            tnOscLcpEchoInterval              Unsigned32,
            tnOscLcpEchoFailure               Unsigned32
        }

--    obsolete
--    tnOscSfpPortType OBJECT-TYPE ::= { tnOscSfpPortConfigEntry 1 }

    tnOscSfpTemperature OBJECT-TYPE
        SYNTAX         Integer32
        UNITS          "Celsius"
        MAX-ACCESS     read-only
        STATUS         current
        DESCRIPTION    "The current temperature of the Osc Sfp."
        DEFVAL         { 0 }
        ::= { tnOscSfpPortConfigEntry 2 }

    tnOscMtu OBJECT-TYPE
        SYNTAX         Integer32
        MAX-ACCESS     read-create
        STATUS         current
        DESCRIPTION    "The MTU size for OSC interface, which to allow
                        remote monitoring of RAMAN/EDFA devices as well
                        as to limit overall packet fragmentation in the
                        network.

                        Current configurable range: 576 to 1500."
        DEFVAL         { 1500 }
        ::= { tnOscSfpPortConfigEntry 3 }

    tnOscMtuNeg OBJECT-TYPE
        SYNTAX         Integer32 (-1..1500)
        MAX-ACCESS     read-only
        STATUS         current
        DESCRIPTION    "The actual (negotiated) Maximum Transmission Unit
                        size, in units of bytes with default value -1,
                        when the MTU size has not yet been negotiated.
                        The default value -1 should be interpreted by
                        UIs as '-'."
        DEFVAL         { -1 }
        ::= { tnOscSfpPortConfigEntry 4 }

    tnOscEnable OBJECT-TYPE
        SYNTAX         TruthValue
        MAX-ACCESS     read-create
        STATUS         current
        DESCRIPTION    "OSC Enable."
        DEFVAL         { false }
        ::= { tnOscSfpPortConfigEntry 5 }

    tnOscConnId OBJECT-TYPE
        SYNTAX         Unsigned32 (1..2)
        MAX-ACCESS     read-create
        STATUS         current
        DESCRIPTION    "OSC Enable."
        ::= { tnOscSfpPortConfigEntry 6 }

    tnOscPortInfoETR OBJECT-TYPE
        SYNTAX         TruthValue
        MAX-ACCESS     read-create
        STATUS         current
        DESCRIPTION    "OSC extended temperature range setting for the port."
        DEFVAL         { true }
        ::= { tnOscSfpPortConfigEntry 7 }

    tnOscIPv6LinkLocalInetAddress OBJECT-TYPE
        SYNTAX         InetAddress
        MAX-ACCESS     read-only
        STATUS         current
        DESCRIPTION    "OSC IPv6 Link Local Address."
        DEFVAL         { ''H }
        ::= { tnOscSfpPortConfigEntry 8 }

    tnOscLcpEchoInterval OBJECT-TYPE
        SYNTAX         Unsigned32
        MAX-ACCESS     read-create
        STATUS         current
        DESCRIPTION    "Osc LCP Echo Interval."
        DEFVAL         { 3 }
        ::= { tnOscSfpPortConfigEntry 9 }

    tnOscLcpEchoFailure OBJECT-TYPE
        SYNTAX         Unsigned32
        MAX-ACCESS     read-create
        STATUS         current
        DESCRIPTION    "Osc LCP Echo Failure."
        DEFVAL         { 3 }
        ::= { tnOscSfpPortConfigEntry 10 }

--------------------------------------------------------------------------------
-- DWDM GP Phy Port Config Table
--------------------------------------------------------------------------------
    tnDwdmGpPhyPortConfigTable OBJECT-TYPE
        SYNTAX         SEQUENCE OF TnDwdmGpPhyPortConfigEntry
        MAX-ACCESS     not-accessible
        STATUS         current
        DESCRIPTION    "Attributes against DWDM GP Phy ports."
        ::= { tnOpticalPortConfig 77 }

    tnDwdmGpPhyPortConfigEntry OBJECT-TYPE
        SYNTAX         TnDwdmGpPhyPortConfigEntry
        MAX-ACCESS     not-accessible
        STATUS         current
        DESCRIPTION    "."
        INDEX { ifIndex }
        ::= { tnDwdmGpPhyPortConfigTable 1 }

    TnDwdmGpPhyPortConfigEntry ::=
        SEQUENCE {
            tnDwdmGpPhyPortPacketIfType      INTEGER,
            tnDwdmGpPhyPortErroredFrameDrop  AluWdmDisabledEnabled,
            tnDwdmGpPhyPortAutoNegotiation   AluWdmDisabledEnabled,
            tnDwdmGpPhyPortPacketFcMode      INTEGER,
            tnDwdmGpPhyPortGfpcrc            INTEGER
        }

    tnDwdmGpPhyPortPacketIfType OBJECT-TYPE
        SYNTAX         INTEGER {
                         escon(1),
                         ficon(2),
                         isc3(3),
                         ficonE(4),
                         gmpGfpT(5),
                         fddi(6),
                         fc1G(7),
                         fc2G(8),
                         fc4G(9),
                         base100Fx(10),
                         dvbAsi(11),
                         dvi6000(12),
                         dv6000(13),
                         ge10GfpF(14),
                         ge10GfpFp(15),
                         ge10Cbr11049(16),
                         ge10Cbr11096(17),
                         fc10G(18),
                         ge1GfpF(19),
                         ge1GfpT(20),
                         ge10(21),
                         fc8GfpT(22),
                         gecbr100(23),
                         fc1200cbr(24),
                         ge10GfpPpos(25),
                         ge10GfpPposOld(26),
                         ge1cbrlan1(27),
                         gecbr400(28)
                       }
        MAX-ACCESS     read-create
        STATUS         current
        DESCRIPTION    "The packet interface type."
        ::= { tnDwdmGpPhyPortConfigEntry 1 }

    tnDwdmGpPhyPortErroredFrameDrop OBJECT-TYPE
        SYNTAX         AluWdmDisabledEnabled
        MAX-ACCESS     read-create
        STATUS         current
        DESCRIPTION    "The errored frame drop status."
        DEFVAL         { disabled }
        ::= { tnDwdmGpPhyPortConfigEntry 2 }

    tnDwdmGpPhyPortAutoNegotiation OBJECT-TYPE
        SYNTAX         AluWdmDisabledEnabled
        MAX-ACCESS     read-create
        STATUS         current
        DESCRIPTION    "The auto negotiation status."
        DEFVAL         { disabled }
        ::= { tnDwdmGpPhyPortConfigEntry 3 }

    tnDwdmGpPhyPortPacketFcMode OBJECT-TYPE
        SYNTAX         INTEGER {
                         fc(1),
                         ficon(2),
                         isc(3)
                       }
        MAX-ACCESS     read-create
        STATUS         current
        DESCRIPTION    "The fiber channel mode."
        DEFVAL         { fc }
        ::= { tnDwdmGpPhyPortConfigEntry 4 }

    tnDwdmGpPhyPortGfpcrc OBJECT-TYPE
        SYNTAX         INTEGER {
                         nonStd(1),
                         std(2)
                       }
        MAX-ACCESS     read-create
        STATUS         current
        DESCRIPTION    "Indication of the GFP CRC framing.
                        nonStd: Non-standard GFP CRC framing.
                        std :   Standard GFP CRC framing."
        DEFVAL         { std }
        ::= { tnDwdmGpPhyPortConfigEntry 5 }

--    obsolete
--    tnGccPortConfigTable OBJECT-TYPE ::= { tnOpticalPortConfig 78 }

--------------------------------------------------------------------------------
-- SVAC Optical Port Config Table
--------------------------------------------------------------------------------
    tnSvacPortConfigTable OBJECT-TYPE
        SYNTAX         SEQUENCE OF TnSvacPortConfigEntry
        MAX-ACCESS     not-accessible
        STATUS         current
        DESCRIPTION    "The ports on a SVAC optical card."
        ::= { tnOpticalPortConfig 79 }

    tnSvacPortConfigEntry OBJECT-TYPE
        SYNTAX         TnSvacPortConfigEntry
        MAX-ACCESS     not-accessible
        STATUS         current
        DESCRIPTION    "."
        INDEX { ifIndex }
        ::= { tnSvacPortConfigTable 1 }

    TnSvacPortConfigEntry ::=
        SEQUENCE {
            tnSvacPortConfigFunction INTEGER
        }

    tnSvacPortConfigFunction OBJECT-TYPE
        SYNTAX         INTEGER {
                         network(1),
                         client(2)
                       }
        MAX-ACCESS     read-only
        STATUS         current
        DESCRIPTION    "Indicates the functional type of this SVAC port."
        ::= { tnSvacPortConfigEntry 1 }

--------------------------------------------------------------------------------
-- SFD Optical Port Config Table
--------------------------------------------------------------------------------
    tnSfdPortConfigTable OBJECT-TYPE
        SYNTAX         SEQUENCE OF TnSfdPortConfigEntry
        MAX-ACCESS     not-accessible
        STATUS         current
        DESCRIPTION    "The ports on a SFD optical card."
        ::= { tnOpticalPortConfig 80 }

    tnSfdPortConfigEntry OBJECT-TYPE
        SYNTAX         TnSfdPortConfigEntry
        MAX-ACCESS     not-accessible
        STATUS         current
        DESCRIPTION    "."
        INDEX { ifIndex }
        ::= { tnSfdPortConfigTable 1 }

    TnSfdPortConfigEntry ::=
        SEQUENCE {
            tnSfd5aPortConfigFunction  AluWdmSfdPortType,
            tnSfd5bPortConfigFunction  AluWdmSfdPortType,
            tnSfd5cPortConfigFunction  AluWdmSfdPortType,
            tnSfd5dPortConfigFunction  AluWdmSfdPortType,
            tnSfd5ePortConfigFunction  AluWdmSfdPortType,
            tnSfd5fPortConfigFunction  AluWdmSfdPortType,
            tnSfd5gPortConfigFunction  AluWdmSfdPortType,
            tnSfd5hPortConfigFunction  AluWdmSfdPortType,
            tnSfd10aPortConfigFunction AluWdmSfdPortType,
            tnSfd10bPortConfigFunction AluWdmSfdPortType,
            tnSfd10cPortConfigFunction AluWdmSfdPortType,
            tnSfd10dPortConfigFunction AluWdmSfdPortType,
            tnSfd8aPortConfigFunction  AluWdmSfdPortType,
            tnSfd8bPortConfigFunction  AluWdmSfdPortType,
            tnSfd8cPortConfigFunction  AluWdmSfdPortType,
            tnSfd8dPortConfigFunction  AluWdmSfdPortType,
            tnSfd4aPortConfigFunction  AluWdmSfdPortType,
            tnSfd4bPortConfigFunction  AluWdmSfdPortType,
            tnSfd4cPortConfigFunction  AluWdmSfdPortType,
            tnSfd4dPortConfigFunction  AluWdmSfdPortType,
            tnSfd4ePortConfigFunction  AluWdmSfdPortType,
            tnSfd4fPortConfigFunction  AluWdmSfdPortType,
            tnSfd4gPortConfigFunction  AluWdmSfdPortType,
            tnSfd4hPortConfigFunction  AluWdmSfdPortType,
            tnSfd2aPortConfigFunction  AluWdmSfdPortType,
            tnSfd2bPortConfigFunction  AluWdmSfdPortType,
            tnSfd2cPortConfigFunction  AluWdmSfdPortType,
            tnSfd2dPortConfigFunction  AluWdmSfdPortType,
            tnSfd2ePortConfigFunction  AluWdmSfdPortType,
            tnSfd2fPortConfigFunction  AluWdmSfdPortType,
            tnSfd2gPortConfigFunction  AluWdmSfdPortType,
            tnSfd2hPortConfigFunction  AluWdmSfdPortType,
            tnSfd2iPortConfigFunction  AluWdmSfdPortType,
            tnSfd2lPortConfigFunction  AluWdmSfdPortType,
            tnSfd2mPortConfigFunction  AluWdmSfdPortType,
            tnSfd2nPortConfigFunction  AluWdmSfdPortType,
            tnSfd2oPortConfigFunction  AluWdmSfdPortType,
            tnSfd2pPortConfigFunction  AluWdmSfdPortType,
            tnSfd2qPortConfigFunction  AluWdmSfdPortType,
            tnSfd2rPortConfigFunction  AluWdmSfdPortType,
            tnVwmSfd8aPortConfigFunction AluWdmSfdPortType,
            tnVwmSfd8bPortConfigFunction AluWdmSfdPortType,
            tnVwmSfd8cPortConfigFunction AluWdmSfdPortType,
            tnVwmSfd8dPortConfigFunction AluWdmSfdPortType,
            tnSfdc8aPortConfigFunction  AluWdmSfdPortType,
            tnSfdc8bPortConfigFunction  AluWdmSfdPortType,
            tnSfdc8cPortConfigFunction  AluWdmSfdPortType,
            tnSfdc8dPortConfigFunction  AluWdmSfdPortType,
            tnSfdc8ePortConfigFunction  AluWdmSfdPortType
        }

    tnSfd5aPortConfigFunction OBJECT-TYPE
        SYNTAX         AluWdmSfdPortType
        MAX-ACCESS     read-only
        STATUS         current
        DESCRIPTION    "Indicates the functional type of this SFD5A port."
        ::= { tnSfdPortConfigEntry 1 }

    tnSfd5bPortConfigFunction OBJECT-TYPE
        SYNTAX         AluWdmSfdPortType
        MAX-ACCESS     read-only
        STATUS         current
        DESCRIPTION    "Indicates the functional type of this SFD5B port."
        ::= { tnSfdPortConfigEntry 2 }

    tnSfd5cPortConfigFunction OBJECT-TYPE
        SYNTAX         AluWdmSfdPortType
        MAX-ACCESS     read-only
        STATUS         current
        DESCRIPTION    "Indicates the functional type of this SFD5C port."
        ::= { tnSfdPortConfigEntry 3 }

    tnSfd5dPortConfigFunction OBJECT-TYPE
        SYNTAX         AluWdmSfdPortType
        MAX-ACCESS     read-only
        STATUS         current
        DESCRIPTION    "Indicates the functional type of this SFD5D port."
        ::= { tnSfdPortConfigEntry 4 }

    tnSfd5ePortConfigFunction OBJECT-TYPE
        SYNTAX         AluWdmSfdPortType
        MAX-ACCESS     read-only
        STATUS         current
        DESCRIPTION    "Indicates the functional type of this SFD5E port."
        ::= { tnSfdPortConfigEntry 5 }

    tnSfd5fPortConfigFunction OBJECT-TYPE
        SYNTAX         AluWdmSfdPortType
        MAX-ACCESS     read-only
        STATUS         current
        DESCRIPTION    "Indicates the functional type of this SFD5F port."
        ::= { tnSfdPortConfigEntry 6 }

    tnSfd5gPortConfigFunction OBJECT-TYPE
        SYNTAX         AluWdmSfdPortType
        MAX-ACCESS     read-only
        STATUS         current
        DESCRIPTION    "Indicates the functional type of this SFD5G port."
        ::= { tnSfdPortConfigEntry 7 }

    tnSfd5hPortConfigFunction OBJECT-TYPE
        SYNTAX         AluWdmSfdPortType
        MAX-ACCESS     read-only
        STATUS         current
        DESCRIPTION    "Indicates the functional type of this SFD5H port."
        ::= { tnSfdPortConfigEntry 8 }

    tnSfd10aPortConfigFunction OBJECT-TYPE
        SYNTAX         AluWdmSfdPortType
        MAX-ACCESS     read-only
        STATUS         current
        DESCRIPTION    "Indicates the functional type of this SFD10A port."
        ::= { tnSfdPortConfigEntry 9 }

    tnSfd10bPortConfigFunction OBJECT-TYPE
        SYNTAX         AluWdmSfdPortType
        MAX-ACCESS     read-only
        STATUS         current
        DESCRIPTION    "Indicates the functional type of this SFD10B port."
        ::= { tnSfdPortConfigEntry 10 }

    tnSfd10cPortConfigFunction OBJECT-TYPE
        SYNTAX         AluWdmSfdPortType
        MAX-ACCESS     read-only
        STATUS         current
        DESCRIPTION    "Indicates the functional type of this SFD10C port."
        ::= { tnSfdPortConfigEntry 11 }

    tnSfd10dPortConfigFunction OBJECT-TYPE
        SYNTAX         AluWdmSfdPortType
        MAX-ACCESS     read-only
        STATUS         current
        DESCRIPTION    "Indicates the functional type of this SFD10D port."
        ::= { tnSfdPortConfigEntry 12 }

    tnSfd8aPortConfigFunction OBJECT-TYPE
        SYNTAX         AluWdmSfdPortType
        MAX-ACCESS     read-only
        STATUS         current
        DESCRIPTION    "Indicates the functional type of this SFD8A port."
        ::= { tnSfdPortConfigEntry 13 }

    tnSfd8bPortConfigFunction OBJECT-TYPE
        SYNTAX         AluWdmSfdPortType
        MAX-ACCESS     read-only
        STATUS         current
        DESCRIPTION    "Indicates the functional type of this SFD8B port."
        ::= { tnSfdPortConfigEntry 14 }

    tnSfd8cPortConfigFunction OBJECT-TYPE
        SYNTAX         AluWdmSfdPortType
        MAX-ACCESS     read-only
        STATUS         current
        DESCRIPTION    "Indicates the functional type of this SFD8C port."
        ::= { tnSfdPortConfigEntry 15 }

    tnSfd8dPortConfigFunction OBJECT-TYPE
        SYNTAX         AluWdmSfdPortType
        MAX-ACCESS     read-only
        STATUS         current
        DESCRIPTION    "Indicates the functional type of this SFD8D port."
        ::= { tnSfdPortConfigEntry 16 }

    tnSfd4aPortConfigFunction OBJECT-TYPE
        SYNTAX         AluWdmSfdPortType
        MAX-ACCESS     read-only
        STATUS         current
        DESCRIPTION    "Indicates the functional type of this SFD4A port."
        ::= { tnSfdPortConfigEntry 17 }

    tnSfd4bPortConfigFunction OBJECT-TYPE
        SYNTAX         AluWdmSfdPortType
        MAX-ACCESS     read-only
        STATUS         current
        DESCRIPTION    "Indicates the functional type of this SFD4B port."
        ::= { tnSfdPortConfigEntry 18 }

    tnSfd4cPortConfigFunction OBJECT-TYPE
        SYNTAX         AluWdmSfdPortType
        MAX-ACCESS     read-only
        STATUS         current
        DESCRIPTION    "Indicates the functional type of this SFD4C port."
        ::= { tnSfdPortConfigEntry 19 }

    tnSfd4dPortConfigFunction OBJECT-TYPE
        SYNTAX         AluWdmSfdPortType
        MAX-ACCESS     read-only
        STATUS         current
        DESCRIPTION    "Indicates the functional type of this SFD4D port."
        ::= { tnSfdPortConfigEntry 20 }

    tnSfd4ePortConfigFunction OBJECT-TYPE
        SYNTAX         AluWdmSfdPortType
        MAX-ACCESS     read-only
        STATUS         current
        DESCRIPTION    "Indicates the functional type of this SFD4E port."
        ::= { tnSfdPortConfigEntry 21 }

    tnSfd4fPortConfigFunction OBJECT-TYPE
        SYNTAX         AluWdmSfdPortType
        MAX-ACCESS     read-only
        STATUS         current
        DESCRIPTION    "Indicates the functional type of this SFD4F port."
        ::= { tnSfdPortConfigEntry 22 }

    tnSfd4gPortConfigFunction OBJECT-TYPE
        SYNTAX         AluWdmSfdPortType
        MAX-ACCESS     read-only
        STATUS         current
        DESCRIPTION    "Indicates the functional type of this SFD4G port."
        ::= { tnSfdPortConfigEntry 23 }

    tnSfd4hPortConfigFunction OBJECT-TYPE
        SYNTAX         AluWdmSfdPortType
        MAX-ACCESS     read-only
        STATUS         current
        DESCRIPTION    "Indicates the functional type of this SFD4H port."
        ::= { tnSfdPortConfigEntry 24 }

    tnSfd2aPortConfigFunction OBJECT-TYPE
        SYNTAX         AluWdmSfdPortType
        MAX-ACCESS     read-only
        STATUS         current
        DESCRIPTION    "Indicates the functional type of this SFD2A port."
        ::= { tnSfdPortConfigEntry 25 }

    tnSfd2bPortConfigFunction OBJECT-TYPE
        SYNTAX         AluWdmSfdPortType
        MAX-ACCESS     read-only
        STATUS         current
        DESCRIPTION    "Indicates the functional type of this SFD2B port."
        ::= { tnSfdPortConfigEntry 26 }

    tnSfd2cPortConfigFunction OBJECT-TYPE
        SYNTAX         AluWdmSfdPortType
        MAX-ACCESS     read-only
        STATUS         current
        DESCRIPTION    "Indicates the functional type of this SFD2C port."
        ::= { tnSfdPortConfigEntry 27 }

    tnSfd2dPortConfigFunction OBJECT-TYPE
        SYNTAX         AluWdmSfdPortType
        MAX-ACCESS     read-only
        STATUS         current
        DESCRIPTION    "Indicates the functional type of this SFD2D port."
        ::= { tnSfdPortConfigEntry 28 }

    tnSfd2ePortConfigFunction OBJECT-TYPE
        SYNTAX         AluWdmSfdPortType
        MAX-ACCESS     read-only
        STATUS         current
        DESCRIPTION    "Indicates the functional type of this SFD2E port."
        ::= { tnSfdPortConfigEntry 29 }

    tnSfd2fPortConfigFunction OBJECT-TYPE
        SYNTAX         AluWdmSfdPortType
        MAX-ACCESS     read-only
        STATUS         current
        DESCRIPTION    "Indicates the functional type of this SFD2F port."
        ::= { tnSfdPortConfigEntry 30 }

    tnSfd2gPortConfigFunction OBJECT-TYPE
        SYNTAX         AluWdmSfdPortType
        MAX-ACCESS     read-only
        STATUS         current
        DESCRIPTION    "Indicates the functional type of this SFD2G port."
        ::= { tnSfdPortConfigEntry 31 }

    tnSfd2hPortConfigFunction OBJECT-TYPE
        SYNTAX         AluWdmSfdPortType
        MAX-ACCESS     read-only
        STATUS         current
        DESCRIPTION    "Indicates the functional type of this SFD2H port."
        ::= { tnSfdPortConfigEntry 32 }

    tnSfd2iPortConfigFunction OBJECT-TYPE
        SYNTAX         AluWdmSfdPortType
        MAX-ACCESS     read-only
        STATUS         current
        DESCRIPTION    "Indicates the functional type of this SFD2I port."
        ::= { tnSfdPortConfigEntry 33 }

    tnSfd2lPortConfigFunction OBJECT-TYPE
        SYNTAX         AluWdmSfdPortType
        MAX-ACCESS     read-only
        STATUS         current
        DESCRIPTION    "Indicates the functional type of this SFD2L port."
        ::= { tnSfdPortConfigEntry 34 }

    tnSfd2mPortConfigFunction OBJECT-TYPE
        SYNTAX         AluWdmSfdPortType
        MAX-ACCESS     read-only
        STATUS         current
        DESCRIPTION    "Indicates the functional type of this SFD2M port."
        ::= { tnSfdPortConfigEntry 35 }

    tnSfd2nPortConfigFunction OBJECT-TYPE
        SYNTAX         AluWdmSfdPortType
        MAX-ACCESS     read-only
        STATUS         current
        DESCRIPTION    "Indicates the functional type of this SFD2N port."
        ::= { tnSfdPortConfigEntry 36 }

    tnSfd2oPortConfigFunction OBJECT-TYPE
        SYNTAX         AluWdmSfdPortType
        MAX-ACCESS     read-only
        STATUS         current
        DESCRIPTION    "Indicates the functional type of this SFD2O port."
        ::= { tnSfdPortConfigEntry 37 }

    tnSfd2pPortConfigFunction OBJECT-TYPE
        SYNTAX         AluWdmSfdPortType
        MAX-ACCESS     read-only
        STATUS         current
        DESCRIPTION    "Indicates the functional type of this SFD2P port."
        ::= { tnSfdPortConfigEntry 38 }

    tnSfd2qPortConfigFunction OBJECT-TYPE
        SYNTAX         AluWdmSfdPortType
        MAX-ACCESS     read-only
        STATUS         current
        DESCRIPTION    "Indicates the functional type of this SFD2Q port."
        ::= { tnSfdPortConfigEntry 39 }

    tnSfd2rPortConfigFunction OBJECT-TYPE
        SYNTAX         AluWdmSfdPortType
        MAX-ACCESS     read-only
        STATUS         current
        DESCRIPTION    "Indicates the functional type of this SFD2R port."
        ::= { tnSfdPortConfigEntry 40 }

    tnVwmSfd8aPortConfigFunction OBJECT-TYPE
        SYNTAX         AluWdmSfdPortType
        MAX-ACCESS     read-only
        STATUS         current
        DESCRIPTION    "Indicates the functional type of this VWMSFD8A port."
        ::= { tnSfdPortConfigEntry 41 }

    tnVwmSfd8bPortConfigFunction OBJECT-TYPE
        SYNTAX         AluWdmSfdPortType
        MAX-ACCESS     read-only
        STATUS         current
        DESCRIPTION    "Indicates the functional type of this VWMSFD8B port."
        ::= { tnSfdPortConfigEntry 42 }

    tnVwmSfd8cPortConfigFunction OBJECT-TYPE
        SYNTAX         AluWdmSfdPortType
        MAX-ACCESS     read-only
        STATUS         current
        DESCRIPTION    "Indicates the functional type of this VWMSFD8C port."
        ::= { tnSfdPortConfigEntry 43 }

    tnVwmSfd8dPortConfigFunction OBJECT-TYPE
        SYNTAX         AluWdmSfdPortType
        MAX-ACCESS     read-only
        STATUS         current
        DESCRIPTION    "Indicates the functional type of this VWMSFD8D port."
        ::= { tnSfdPortConfigEntry 44 }

    tnSfdc8aPortConfigFunction OBJECT-TYPE
        SYNTAX         AluWdmSfdPortType
        MAX-ACCESS     read-only
        STATUS         current
        DESCRIPTION    "Indicates the functional type of this SFDC8A port."
        ::= { tnSfdPortConfigEntry 45 }

    tnSfdc8bPortConfigFunction OBJECT-TYPE
        SYNTAX         AluWdmSfdPortType
        MAX-ACCESS     read-only
        STATUS         current
        DESCRIPTION    "Indicates the functional type of this SFDC8B port."
        ::= { tnSfdPortConfigEntry 46 }

    tnSfdc8cPortConfigFunction OBJECT-TYPE
        SYNTAX         AluWdmSfdPortType
        MAX-ACCESS     read-only
        STATUS         current
        DESCRIPTION    "Indicates the functional type of this SFDC8C port."
        ::= { tnSfdPortConfigEntry 47 }

    tnSfdc8dPortConfigFunction OBJECT-TYPE
        SYNTAX         AluWdmSfdPortType
        MAX-ACCESS     read-only
        STATUS         current
        DESCRIPTION    "Indicates the functional type of this SFDC8D port."
        ::= { tnSfdPortConfigEntry 48 }

    tnSfdc8ePortConfigFunction OBJECT-TYPE
        SYNTAX         AluWdmSfdPortType
        MAX-ACCESS     read-only
        STATUS         current
        DESCRIPTION    "Indicates the functional type of this SFDC8E port."
        ::= { tnSfdPortConfigEntry 49 }

--------------------------------------------------------------------------------
-- SFC Optical Port Config Table
--------------------------------------------------------------------------------
    tnSfcPortConfigTable OBJECT-TYPE
        SYNTAX         SEQUENCE OF TnSfcPortConfigEntry
        MAX-ACCESS     not-accessible
        STATUS         current
        DESCRIPTION    "The ports on a SFC optical card."
        ::= { tnOpticalPortConfig 81 }

    tnSfcPortConfigEntry OBJECT-TYPE
        SYNTAX         TnSfcPortConfigEntry
        MAX-ACCESS     not-accessible
        STATUS         current
        DESCRIPTION    "."
        INDEX { ifIndex }
        ::= { tnSfcPortConfigTable 1 }

    TnSfcPortConfigEntry ::=
        SEQUENCE {
            tnSfc2aPortConfigFunction INTEGER,
            tnSfc2bPortConfigFunction INTEGER,
            tnSfc2cPortConfigFunction INTEGER,
            tnSfc2dPortConfigFunction INTEGER,
            tnSfc4aPortConfigFunction INTEGER,
            tnSfc4bPortConfigFunction INTEGER,
            tnSfc8PortConfigFunction  INTEGER,
            tnSfc1aPortConfigFunction INTEGER,
            tnSfc1bPortConfigFunction INTEGER,
            tnSfc1cPortConfigFunction INTEGER,
            tnSfc1dPortConfigFunction INTEGER,
            tnSfc1ePortConfigFunction INTEGER,
            tnSfc1fPortConfigFunction INTEGER,
            tnSfc1gPortConfigFunction INTEGER,
            tnSfc1hPortConfigFunction INTEGER,
            tnVwmSfc8PortConfigFunction INTEGER
        }

    tnSfc2aPortConfigFunction OBJECT-TYPE
        SYNTAX         INTEGER {
                         channel(1),
                         mux(2),
                         exp(3)
                       }
        MAX-ACCESS     read-only
        STATUS         current
        DESCRIPTION    "Indicates the functional type of this SFC2A port."
        ::= { tnSfcPortConfigEntry 1 }

    tnSfc2bPortConfigFunction OBJECT-TYPE
        SYNTAX         INTEGER {
                         channel(1),
                         mux(2),
                         exp(3)
                       }
        MAX-ACCESS     read-only
        STATUS         current
        DESCRIPTION    "Indicates the functional type of this SFC2B port."
        ::= { tnSfcPortConfigEntry 2 }

    tnSfc2cPortConfigFunction OBJECT-TYPE
        SYNTAX         INTEGER {
                         channel(1),
                         mux(2),
                         exp(3)
                       }
        MAX-ACCESS     read-only
        STATUS         current
        DESCRIPTION    "Indicates the functional type of this SFC2C port."
        ::= { tnSfcPortConfigEntry 3 }

    tnSfc2dPortConfigFunction OBJECT-TYPE
        SYNTAX         INTEGER {
                         channel(1),
                         mux(2),
                         exp(3)
                       }
        MAX-ACCESS     read-only
        STATUS         current
        DESCRIPTION    "Indicates the functional type of this SFC2D port."
        ::= { tnSfcPortConfigEntry 4 }

    tnSfc4aPortConfigFunction OBJECT-TYPE
        SYNTAX         INTEGER {
                         channel(1),
                         mux(2),
                         exp(3)
                       }
        MAX-ACCESS     read-only
        STATUS         current
        DESCRIPTION    "Indicates the functional type of this SFC4A port."
        ::= { tnSfcPortConfigEntry 5 }

    tnSfc4bPortConfigFunction OBJECT-TYPE
        SYNTAX         INTEGER {
                         channel(1),
                         mux(2),
                         exp(3)
                       }
        MAX-ACCESS     read-only
        STATUS         current
        DESCRIPTION    "Indicates the functional type of this SFC4B port."
        ::= { tnSfcPortConfigEntry 6 }

    tnSfc8PortConfigFunction OBJECT-TYPE
        SYNTAX         INTEGER {
                         channel(1),
                         mux(2)
                       }
        MAX-ACCESS     read-only
        STATUS         current
        DESCRIPTION    "Indicates the functional type of this SFC8 port."
        ::= { tnSfcPortConfigEntry 7 }

    tnSfc1aPortConfigFunction OBJECT-TYPE
        SYNTAX         INTEGER {
                         channel(1),
                         mux(2),
                         exp(3)
                       }
        MAX-ACCESS     read-only
        STATUS         current
        DESCRIPTION    "Indicates the functional type of this SFC1A port."
        ::= { tnSfcPortConfigEntry 8 }

    tnSfc1bPortConfigFunction OBJECT-TYPE
        SYNTAX         INTEGER {
                         channel(1),
                         mux(2),
                         exp(3)
                       }
        MAX-ACCESS     read-only
        STATUS         current
        DESCRIPTION    "Indicates the functional type of this SFC1B port."
        ::= { tnSfcPortConfigEntry 9 }

    tnSfc1cPortConfigFunction OBJECT-TYPE
        SYNTAX         INTEGER {
                         channel(1),
                         mux(2),
                         exp(3)
                       }
        MAX-ACCESS     read-only
        STATUS         current
        DESCRIPTION    "Indicates the functional type of this SFC1C port."
        ::= { tnSfcPortConfigEntry 10 }

    tnSfc1dPortConfigFunction OBJECT-TYPE
        SYNTAX         INTEGER {
                         channel(1),
                         mux(2),
                         exp(3)
                       }
        MAX-ACCESS     read-only
        STATUS         current
        DESCRIPTION    "Indicates the functional type of this SFC1D port."
        ::= { tnSfcPortConfigEntry 11 }

    tnSfc1ePortConfigFunction OBJECT-TYPE
        SYNTAX         INTEGER {
                         channel(1),
                         mux(2),
                         exp(3)
                       }
        MAX-ACCESS     read-only
        STATUS         current
        DESCRIPTION    "Indicates the functional type of this SFC1E port."
        ::= { tnSfcPortConfigEntry 12 }

    tnSfc1fPortConfigFunction OBJECT-TYPE
        SYNTAX         INTEGER {
                         channel(1),
                         mux(2),
                         exp(3)
                       }
        MAX-ACCESS     read-only
        STATUS         current
        DESCRIPTION    "Indicates the functional type of this SFC1F port."
        ::= { tnSfcPortConfigEntry 13 }

    tnSfc1gPortConfigFunction OBJECT-TYPE
        SYNTAX         INTEGER {
                         channel(1),
                         mux(2),
                         exp(3)
                       }
        MAX-ACCESS     read-only
        STATUS         current
        DESCRIPTION    "Indicates the functional type of this SFC1G port."
        ::= { tnSfcPortConfigEntry 14 }

    tnSfc1hPortConfigFunction OBJECT-TYPE
        SYNTAX         INTEGER {
                         channel(1),
                         mux(2),
                         exp(3)
                       }
        MAX-ACCESS     read-only
        STATUS         current
        DESCRIPTION    "Indicates the functional type of this SFC1H port."
        ::= { tnSfcPortConfigEntry 15 }

    tnVwmSfc8PortConfigFunction OBJECT-TYPE
        SYNTAX         INTEGER {
                         channel(1),
                         mux(2),
                         exp(3)
                       }
        MAX-ACCESS     read-only
        STATUS         current
        DESCRIPTION    "Indicates the functional type of this VWMSFC8 port."
        ::= { tnSfcPortConfigEntry 16 }

--------------------------------------------------------------------------------
-- VTS Port Config Table
--------------------------------------------------------------------------------
    tnVtsPortConfigTable OBJECT-TYPE
        SYNTAX         SEQUENCE OF TnVtsPortConfigEntry
        MAX-ACCESS     not-accessible
        STATUS         current
        DESCRIPTION    "The VTS attributes on OT ports."
        ::= { tnOpticalPortConfig 82 }

    tnVtsPortConfigEntry OBJECT-TYPE
        SYNTAX         TnVtsPortConfigEntry
        MAX-ACCESS     not-accessible
        STATUS         current
        DESCRIPTION    "."
        INDEX { ifIndex }
        ::= { tnVtsPortConfigTable 1 }

    TnVtsPortConfigEntry ::=
        SEQUENCE {
            tnVtsPortVts1Source AluWdmVtsSource,
            tnVtsPortVts2Source AluWdmVtsSource,
            tnVtsPortVts3Source AluWdmVtsSource,
            tnVtsPortVts4Source AluWdmVtsSource,
            tnVtsPortVts5Source AluWdmVtsSource,
            tnVtsPortVts6Source AluWdmVtsSource,
            tnVtsPortVts7Source AluWdmVtsSource,
            tnVtsPortVts8Source AluWdmVtsSource,
            tnVtsPortVts9Source AluWdmVtsSource,
            tnVtsPortVts10Source AluWdmVtsSource
        }

    tnVtsPortVts1Source OBJECT-TYPE
        SYNTAX         AluWdmVtsSource
        MAX-ACCESS     read-create
        STATUS         current
        DESCRIPTION    "."
        DEFVAL         { none }
        ::= { tnVtsPortConfigEntry 1 }

    tnVtsPortVts2Source OBJECT-TYPE
        SYNTAX         AluWdmVtsSource
        MAX-ACCESS     read-create
        STATUS         current
        DESCRIPTION    "."
        DEFVAL         { none }
        ::= { tnVtsPortConfigEntry 2 }

    tnVtsPortVts3Source OBJECT-TYPE
        SYNTAX         AluWdmVtsSource
        MAX-ACCESS     read-create
        STATUS         current
        DESCRIPTION    "."
        DEFVAL         { none }
        ::= { tnVtsPortConfigEntry 3 }

    tnVtsPortVts4Source OBJECT-TYPE
        SYNTAX         AluWdmVtsSource
        MAX-ACCESS     read-create
        STATUS         current
        DESCRIPTION    "."
        DEFVAL         { none }
        ::= { tnVtsPortConfigEntry 4 }

    tnVtsPortVts5Source OBJECT-TYPE
        SYNTAX         AluWdmVtsSource
        MAX-ACCESS     read-create
        STATUS         current
        DESCRIPTION    "."
        DEFVAL         { none }
        ::= { tnVtsPortConfigEntry 5 }

    tnVtsPortVts6Source OBJECT-TYPE
        SYNTAX         AluWdmVtsSource
        MAX-ACCESS     read-create
        STATUS         current
        DESCRIPTION    "."
        DEFVAL         { none }
        ::= { tnVtsPortConfigEntry 6 }

    tnVtsPortVts7Source OBJECT-TYPE
        SYNTAX         AluWdmVtsSource
        MAX-ACCESS     read-create
        STATUS         current
        DESCRIPTION    "."
        DEFVAL         { none }
        ::= { tnVtsPortConfigEntry 7 }

    tnVtsPortVts8Source OBJECT-TYPE
        SYNTAX         AluWdmVtsSource
        MAX-ACCESS     read-create
        STATUS         current
        DESCRIPTION    "."
        DEFVAL         { none }
        ::= { tnVtsPortConfigEntry 8 }

    tnVtsPortVts9Source OBJECT-TYPE
        SYNTAX         AluWdmVtsSource
        MAX-ACCESS     read-create
        STATUS         current
        DESCRIPTION    "."
        DEFVAL         { none }
        ::= { tnVtsPortConfigEntry 9 }

    tnVtsPortVts10Source OBJECT-TYPE
        SYNTAX         AluWdmVtsSource
        MAX-ACCESS     read-create
        STATUS         current
        DESCRIPTION    "."
        DEFVAL         { none }
        ::= { tnVtsPortConfigEntry 10 }

--------------------------------------------------------------------------------
-- OMD Common Port Config Table
--------------------------------------------------------------------------------
    tnOmdPortConfigTable OBJECT-TYPE
        SYNTAX         SEQUENCE OF TnOmdPortConfigEntry
        MAX-ACCESS     not-accessible
        STATUS         current
        DESCRIPTION    "Common attributes against OMD ports for SFC and
                        SFD packs."
        ::= { tnOpticalPortConfig 83 }

    tnOmdPortConfigEntry OBJECT-TYPE
        SYNTAX         TnOmdPortConfigEntry
        MAX-ACCESS     not-accessible
        STATUS         current
        DESCRIPTION    "."
        INDEX { ifIndex }
        ::= { tnOmdPortConfigTable 1 }

    TnOmdPortConfigEntry ::=
        SEQUENCE {
            tnOmdPortLosThreshold              Integer32,
            tnOmdPortLosThresholdTolerance     Unsigned32,
            tnOmdPortLosOutThreshold           Integer32,
            tnOmdPortLosOutThresholdTolerance  Unsigned32
        }

    tnOmdPortLosThreshold OBJECT-TYPE
        SYNTAX         Integer32
        UNITS          "mBm"
        MAX-ACCESS     read-create
        STATUS         current
        DESCRIPTION    "The following description applies to the SIG_IN
                        of the OMD port of the SFC1, SFC2, SFC4, SFC8,
                        SFD5, and SFD8 cards:

                        Current configurable ranges and defaults:

                        SFC1:  (-2600.. 980), -2600
                        SFC2:  (-2600.. 980), -2600
                        SFC4:  (-2600.. 980), -2600
                        SFC8:  (-2600.. 980), -2600
                        SFD4:  (-3200..2000), -3200
                        SFD5:  (-3200..2000), -3200
                        SFD8:  (-3200..1700), -3200."
        ::= { tnOmdPortConfigEntry 1 }

    tnOmdPortLosThresholdTolerance OBJECT-TYPE
        SYNTAX         Unsigned32
        UNITS          "mB"
        MAX-ACCESS     read-create
        STATUS         current
        DESCRIPTION    "This is the difference above the LOS set and
                        clear points and applies to the SIG_IN of the
                        OMD port of the SFC1, SFC2, SFC4, SFC8, SFD5,
                        and SFD8 cards:

                        Current configurable range: 50 to 600."
        DEFVAL         { 200 }
        ::= { tnOmdPortConfigEntry 2 }

    tnOmdPortLosOutThreshold OBJECT-TYPE
        SYNTAX         Integer32
        UNITS          "mBm"
        MAX-ACCESS     read-create
        STATUS         current
        DESCRIPTION    "The following description applies to the SIG_OUT
                        of the OMD port of the SFD5 and SFD8 cards:

                        Current configurable range:

                        SFD5: -3200 to 2000
                        SFD8: -3200 to 1700."
        DEFVAL         { -3200 }
        ::= { tnOmdPortConfigEntry 3 }

    tnOmdPortLosOutThresholdTolerance OBJECT-TYPE
        SYNTAX         Unsigned32
        UNITS          "mB"
        MAX-ACCESS     read-create
        STATUS         current
        DESCRIPTION    "This is the difference above the LOS set and
                        clear points and applies to the SIG_out of the
                        OMD port of the SFD5 and SFD8 cards:

                        Current configurable range: 50 to 600."
        DEFVAL         { 200 }
        ::= { tnOmdPortConfigEntry 4 }

--------------------------------------------------------------------------------
-- 4DPA4 Optical Port Config Scalar
--------------------------------------------------------------------------------
    tn4dpa4PortConfigAttributeTotal OBJECT-TYPE
        SYNTAX         Integer32
        MAX-ACCESS     read-only
        STATUS         current
        DESCRIPTION    "."
        ::= { tnOpticalPortConfig 84 }

--------------------------------------------------------------------------------
-- 4DPA4 Optical Port Config Table
--------------------------------------------------------------------------------
    tn4dpa4PortConfigTable OBJECT-TYPE
        SYNTAX         SEQUENCE OF Tn4dpa4PortConfigEntry
        MAX-ACCESS     not-accessible
        STATUS         current
        DESCRIPTION    "The ports on a 4DPA4 optical card."
        ::= { tnOpticalPortConfig 85 }

    tn4dpa4PortConfigEntry OBJECT-TYPE
        SYNTAX         Tn4dpa4PortConfigEntry
        MAX-ACCESS     not-accessible
        STATUS         current
        DESCRIPTION    "."
        INDEX { ifIndex }
        ::= { tn4dpa4PortConfigTable 1 }

    Tn4dpa4PortConfigEntry ::=
        SEQUENCE {
            tn4dpa4PortConfigFunction INTEGER
        }

    tn4dpa4PortConfigFunction OBJECT-TYPE
        SYNTAX         INTEGER {
                         network(1),
                         client(2),
                         evoa(3)
                       }
        MAX-ACCESS     read-only
        STATUS         current
        DESCRIPTION    "Indicates the functional type of this 4DPA4 port."
        ::= { tn4dpa4PortConfigEntry 1 }

--------------------------------------------------------------------------------
-- CWR8-88 Optical Port Config Scalar
--------------------------------------------------------------------------------
    tnCwr8c88PortConfigAttributeTotal OBJECT-TYPE
        SYNTAX         Integer32
        MAX-ACCESS     read-only
        STATUS         current
        DESCRIPTION    "."
        ::= { tnOpticalPortConfig 86 }

--------------------------------------------------------------------------------
-- CWR8-88 Optical Port Config Table
--------------------------------------------------------------------------------
    tnCwr8c88PortConfigTable OBJECT-TYPE
        SYNTAX         SEQUENCE OF TnCwr8c88PortConfigEntry
        MAX-ACCESS     not-accessible
        STATUS         current
        DESCRIPTION    "The ports on a CWR8-88 optical card."
        ::= { tnOpticalPortConfig 87 }

    tnCwr8c88PortConfigEntry OBJECT-TYPE
        SYNTAX         TnCwr8c88PortConfigEntry
        MAX-ACCESS     not-accessible
        STATUS         current
        DESCRIPTION    "."
        INDEX { ifIndex }
        ::= { tnCwr8c88PortConfigTable 1 }

    TnCwr8c88PortConfigEntry ::=
        SEQUENCE {
            tnCwr8c88PortConfigFunction  INTEGER,
--            obsolete
--            tnCwr8c88PortBlockerAging    Unsigned32,
            tnCwr8c88PortDropTargetPower Integer32
        }

    tnCwr8c88PortConfigFunction OBJECT-TYPE
        SYNTAX         INTEGER {
                         signal(1),
                         test(2),
                         thru(3),
                         colorless(4),
                         omd(5),
                         inv(6)
                       }
        MAX-ACCESS     read-only
        STATUS         current
        DESCRIPTION    "Indicates the functional type of this CWR8-88 port."
        ::= { tnCwr8c88PortConfigEntry 1 }

--    obsolete
--    tnCwr8c88PortBlockerAging OBJECT-TYPE ::= { tnCwr8c88PortConfigEntry 2 }

    tnCwr8c88PortDropTargetPower OBJECT-TYPE
        SYNTAX         Integer32
        UNITS          "mBm"
        MAX-ACCESS     read-create
        STATUS         current
        DESCRIPTION    "The following description applies to the
                        colorless port of the CWR8-88 card:

                        The drop target power.

                        Current configurable range: -2650 to -400."
        DEFVAL         { -1200 }
        ::= { tnCwr8c88PortConfigEntry 3 }

--------------------------------------------------------------------------------
-- SFD44B Optical Port Config Scalar
--------------------------------------------------------------------------------
    tnSfd44bPortConfigAttributeTotal OBJECT-TYPE
        SYNTAX         Integer32
        MAX-ACCESS     read-only
        STATUS         current
        DESCRIPTION    "."
        ::= { tnOpticalPortConfig 88 }

--------------------------------------------------------------------------------
-- SFD44B Optical Port Config Table
--------------------------------------------------------------------------------
    tnSfd44bPortConfigTable OBJECT-TYPE
        SYNTAX         SEQUENCE OF TnSfd44bPortConfigEntry
        MAX-ACCESS     not-accessible
        STATUS         current
        DESCRIPTION    "The ports on a SFD44B optical card."
        ::= { tnOpticalPortConfig 89 }

    tnSfd44bPortConfigEntry OBJECT-TYPE
        SYNTAX         TnSfd44bPortConfigEntry
        MAX-ACCESS     not-accessible
        STATUS         current
        DESCRIPTION    "."
        INDEX { ifIndex }
        ::= { tnSfd44bPortConfigTable 1 }

    TnSfd44bPortConfigEntry ::=
        SEQUENCE {
            tnSfd44bPortConfigFunction INTEGER
        }

    tnSfd44bPortConfigFunction OBJECT-TYPE
        SYNTAX         INTEGER {
                         channel(1),
                         mux(2)
                       }
        MAX-ACCESS     read-only
        STATUS         current
        DESCRIPTION    "Indicates the functional type of this SFD44B port:

                        port 1-44 - channel
                        port 45 - mux"
        ::= { tnSfd44bPortConfigEntry 1 }

--------------------------------------------------------------------------------
-- ITLB Optical Port Config Scalar
--------------------------------------------------------------------------------
    tnItlbPortConfigAttributeTotal OBJECT-TYPE
        SYNTAX         Integer32
        MAX-ACCESS     read-only
        STATUS         current
        DESCRIPTION    "."
        ::= { tnOpticalPortConfig 90 }

--------------------------------------------------------------------------------
-- ITLB Optical Port Config Table
--------------------------------------------------------------------------------
    tnItlbPortConfigTable OBJECT-TYPE
        SYNTAX         SEQUENCE OF TnItlbPortConfigEntry
        MAX-ACCESS     not-accessible
        STATUS         current
        DESCRIPTION    "The ports on an ITLB optical card."
        ::= { tnOpticalPortConfig 91 }

    tnItlbPortConfigEntry OBJECT-TYPE
        SYNTAX         TnItlbPortConfigEntry
        MAX-ACCESS     not-accessible
        STATUS         current
        DESCRIPTION    "."
        INDEX { ifIndex }
        ::= { tnItlbPortConfigTable 1 }

    TnItlbPortConfigEntry ::=
        SEQUENCE {
            tnItlbPortConfigFunction INTEGER
        }

    tnItlbPortConfigFunction OBJECT-TYPE
        SYNTAX         INTEGER {
                         signal(1),
                         even(2),
                         odd(3)
                       }
        MAX-ACCESS     read-only
        STATUS         current
        DESCRIPTION    "Indicates the functional type of this ITLB port:

                        port 1 - signal
                        port 2 - even
                        port 3 - odd"
        ::= { tnItlbPortConfigEntry 1 }

--------------------------------------------------------------------------------
-- AHPLG Optical Port Config Scalar
--------------------------------------------------------------------------------
    tnAhplgPortConfigAttributeTotal OBJECT-TYPE
        SYNTAX         Integer32
        MAX-ACCESS     read-only
        STATUS         current
        DESCRIPTION    "."
        ::= { tnOpticalPortConfig 92 }

--------------------------------------------------------------------------------
-- AHPLG Optical Port Config Table
--------------------------------------------------------------------------------
    tnAhplgPortConfigTable OBJECT-TYPE
        SYNTAX         SEQUENCE OF TnAhplgPortConfigEntry
        MAX-ACCESS     not-accessible
        STATUS         current
        DESCRIPTION    "The ports on an AHPLG optical card."
        ::= { tnOpticalPortConfig 93 }

    tnAhplgPortConfigEntry OBJECT-TYPE
        SYNTAX         TnAhplgPortConfigEntry
        MAX-ACCESS     not-accessible
        STATUS         current
        DESCRIPTION    "."
        INDEX { ifIndex }
        ::= { tnAhplgPortConfigTable 1 }

    TnAhplgPortConfigEntry ::=
        SEQUENCE {
            tnAhplgPortConfigFunction INTEGER
        }

    tnAhplgPortConfigFunction OBJECT-TYPE
        SYNTAX         INTEGER {
                         line(1),
                         signal(2),
                         dcm(3),
                         inv(4),
                         osc(5),
                         custLan(6)
                       }
        MAX-ACCESS     read-only
        STATUS         current
        DESCRIPTION    "Indicates the functional type of this AHPLG port."
        ::= { tnAhplgPortConfigEntry 1 }

--------------------------------------------------------------------------------
-- DWDM Common OTU1/ODU1 Line Port Config Table
--------------------------------------------------------------------------------
    tnDwdmCmnOtu1Odu1LinePortConfigTable OBJECT-TYPE
        SYNTAX         SEQUENCE OF TnDwdmCmnOtu1Odu1LinePortConfigEntry
        MAX-ACCESS     not-accessible
        STATUS         current
        DESCRIPTION    "Common attributes against DWDM line ports."
        ::= { tnOpticalPortConfig 94 }

    tnDwdmCmnOtu1Odu1LinePortConfigEntry OBJECT-TYPE
        SYNTAX         TnDwdmCmnOtu1Odu1LinePortConfigEntry
        MAX-ACCESS     not-accessible
        STATUS         current
        DESCRIPTION    "."
        INDEX { ifIndex }
        ::= { tnDwdmCmnOtu1Odu1LinePortConfigTable 1 }

    TnDwdmCmnOtu1Odu1LinePortConfigEntry ::=
        SEQUENCE {
            tnDwdmCmnLinePortOchOtu1FecMode                    AluWdmFecMode,
            tnDwdmCmnLinePortOchOtu1Rate                       AluWdmPortOchOtuRate,
            tnDwdmCmnLinePortOtu1TransmittedTti                OCTET STRING,
            tnDwdmCmnLinePortOtu1ExpectedTti                   OCTET STRING,
            tnDwdmCmnLinePortOtu1TimConsequenceAction          AluWdmDisabledEnabled,
            tnDwdmCmnLinePortOtu1TimDetectionMode              AluWdmTimDetectionMode,
            tnDwdmCmnLinePortOdu1PayloadType                   Unsigned32,
            tnDwdmCmnLinePortOdu1OchSignalDefConsequenceAction AluWdmOduOchSignalDefConsequenceAction,
            tnDwdmCmnLinePortOdu1PlmConsequenceAction          TruthValue,
            tnDwdmCmnLinePortOdu1MappingMode                   AluWdmMappingMode,
            tnDwdmCmnLinePortOdu1TpMode                        TruthValue,
            tnDwdmCmnLinePortOdu1TransmittedTti                OCTET STRING,
            tnDwdmCmnLinePortOdu1ExpectedTti                   OCTET STRING,
            tnDwdmCmnLinePortOdu1TimConsequenceAction          AluWdmDisabledEnabled,
            tnDwdmCmnLinePortOdu1TimDetectionMode              AluWdmTimDetectionMode,
            tnDwdmCmnLinePortOdu1Interworking                  TruthValue
        }

    tnDwdmCmnLinePortOchOtu1FecMode OBJECT-TYPE
        SYNTAX         AluWdmFecMode
        MAX-ACCESS     read-create
        STATUS         current
        DESCRIPTION    "OTU1 FEC mode."
        DEFVAL         { g709Fec }
        ::= { tnDwdmCmnOtu1Odu1LinePortConfigEntry 1 }

    tnDwdmCmnLinePortOchOtu1Rate OBJECT-TYPE
        SYNTAX         AluWdmPortOchOtuRate
        MAX-ACCESS     read-create
        STATUS         current
        DESCRIPTION    "OTU1 rate."
        DEFVAL         { otm2G66 }
        ::= { tnDwdmCmnOtu1Odu1LinePortConfigEntry 2 }

    tnDwdmCmnLinePortOtu1TransmittedTti OBJECT-TYPE
        SYNTAX         OCTET STRING
        MAX-ACCESS     read-create
        STATUS         current
        DESCRIPTION    "OTU1 transmitted TTI."
        DEFVAL         { "" }
        ::= { tnDwdmCmnOtu1Odu1LinePortConfigEntry 3 }

    tnDwdmCmnLinePortOtu1ExpectedTti OBJECT-TYPE
        SYNTAX         OCTET STRING
        MAX-ACCESS     read-create
        STATUS         current
        DESCRIPTION    "OTU1 expected TTI."
        DEFVAL         { "" }
        ::= { tnDwdmCmnOtu1Odu1LinePortConfigEntry 4 }

    tnDwdmCmnLinePortOtu1TimConsequenceAction OBJECT-TYPE
        SYNTAX         AluWdmDisabledEnabled
        MAX-ACCESS     read-create
        STATUS         current
        DESCRIPTION    "OTU1 TIM consequence action."
        DEFVAL         { disabled }
        ::= { tnDwdmCmnOtu1Odu1LinePortConfigEntry 5 }

    tnDwdmCmnLinePortOtu1TimDetectionMode OBJECT-TYPE
        SYNTAX         AluWdmTimDetectionMode
        MAX-ACCESS     read-create
        STATUS         current
        DESCRIPTION    "OTU1 TIM detection mode."
        DEFVAL         { off }
        ::= { tnDwdmCmnOtu1Odu1LinePortConfigEntry 6 }

    tnDwdmCmnLinePortOdu1PayloadType OBJECT-TYPE
        SYNTAX         Unsigned32
        MAX-ACCESS     read-create
        STATUS         current
        DESCRIPTION    "ODU1 payload type.

                        Current configurable range: 0 to 255."
        DEFVAL         { 128 }
        ::= { tnDwdmCmnOtu1Odu1LinePortConfigEntry 7 }

    tnDwdmCmnLinePortOdu1OchSignalDefConsequenceAction OBJECT-TYPE
        SYNTAX         AluWdmOduOchSignalDefConsequenceAction
        MAX-ACCESS     read-create
        STATUS         current
        DESCRIPTION    "ODU1 OCH signal def consequence action."
        DEFVAL         { genericAis }
        ::= { tnDwdmCmnOtu1Odu1LinePortConfigEntry 8 }

    tnDwdmCmnLinePortOdu1PlmConsequenceAction OBJECT-TYPE
        SYNTAX         TruthValue
        MAX-ACCESS     read-create
        STATUS         current
        DESCRIPTION    "PLM consequence action."
        DEFVAL         { false }
        ::= { tnDwdmCmnOtu1Odu1LinePortConfigEntry 9 }

    tnDwdmCmnLinePortOdu1MappingMode OBJECT-TYPE
        SYNTAX         AluWdmMappingMode
        MAX-ACCESS     read-create
        STATUS         current
        DESCRIPTION    "ODU1 mapping mode."
        DEFVAL         { rsB }
        ::= { tnDwdmCmnOtu1Odu1LinePortConfigEntry 10 }

    tnDwdmCmnLinePortOdu1TpMode OBJECT-TYPE
        SYNTAX         TruthValue
        MAX-ACCESS     read-create
        STATUS         current
        DESCRIPTION    "ODU1 TP mode."
        DEFVAL         { true }
        ::= { tnDwdmCmnOtu1Odu1LinePortConfigEntry 11 }

    tnDwdmCmnLinePortOdu1TransmittedTti OBJECT-TYPE
        SYNTAX         OCTET STRING
        MAX-ACCESS     read-create
        STATUS         current
        DESCRIPTION    "ODU1 transmitted TTI."
        DEFVAL         { "" }
        ::= { tnDwdmCmnOtu1Odu1LinePortConfigEntry 12 }

    tnDwdmCmnLinePortOdu1ExpectedTti OBJECT-TYPE
        SYNTAX         OCTET STRING
        MAX-ACCESS     read-create
        STATUS         current
        DESCRIPTION    "ODU1 expected TTI."
        DEFVAL         { "" }
        ::= { tnDwdmCmnOtu1Odu1LinePortConfigEntry 13 }

    tnDwdmCmnLinePortOdu1TimConsequenceAction OBJECT-TYPE
        SYNTAX         AluWdmDisabledEnabled
        MAX-ACCESS     read-create
        STATUS         current
        DESCRIPTION    "ODU1 TIM consequence action."
        DEFVAL         { disabled }
        ::= { tnDwdmCmnOtu1Odu1LinePortConfigEntry 14 }

    tnDwdmCmnLinePortOdu1TimDetectionMode OBJECT-TYPE
        SYNTAX         AluWdmTimDetectionMode
        MAX-ACCESS     read-create
        STATUS         current
        DESCRIPTION    "ODU1 TIM detection mode."
        DEFVAL         { off }
        ::= { tnDwdmCmnOtu1Odu1LinePortConfigEntry 15 }

    tnDwdmCmnLinePortOdu1Interworking OBJECT-TYPE
        SYNTAX         TruthValue
        MAX-ACCESS     read-create
        STATUS         current
        DESCRIPTION    "ODU1 interworking."
        DEFVAL         { false }
        ::= { tnDwdmCmnOtu1Odu1LinePortConfigEntry 16 }

--------------------------------------------------------------------------------
-- DWDM Common OTU1/ODU1 Client Port Config Table
--------------------------------------------------------------------------------
    tnDwdmCmnOtu1Odu1ClientPortConfigTable OBJECT-TYPE
        SYNTAX         SEQUENCE OF TnDwdmCmnOtu1Odu1ClientPortConfigEntry
        MAX-ACCESS     not-accessible
        STATUS         current
        DESCRIPTION    "Common attributes against DWDM client ports."
        ::= { tnOpticalPortConfig 95 }

    tnDwdmCmnOtu1Odu1ClientPortConfigEntry OBJECT-TYPE
        SYNTAX         TnDwdmCmnOtu1Odu1ClientPortConfigEntry
        MAX-ACCESS     not-accessible
        STATUS         current
        DESCRIPTION    "."
        INDEX { ifIndex }
        ::= { tnDwdmCmnOtu1Odu1ClientPortConfigTable 1 }

    TnDwdmCmnOtu1Odu1ClientPortConfigEntry ::=
        SEQUENCE {
            tnDwdmCmnClientPortOchOtu1FecMode           AluWdmFecMode,
            tnDwdmCmnClientPortOchOtu1Rate              AluWdmPortOchOtuRate,
            tnDwdmCmnClientPortOtu1TransmittedTti       OCTET STRING,
            tnDwdmCmnClientPortOtu1ExpectedTti          OCTET STRING,
            tnDwdmCmnClientPortOtu1TimConsequenceAction AluWdmDisabledEnabled,
            tnDwdmCmnClientPortOtu1TimDetectionMode     AluWdmTimDetectionMode,
            tnDwdmCmnClientPortOdu1TransmittedTti       OCTET STRING,
            tnDwdmCmnClientPortOdu1ExpectedTti          OCTET STRING,
            tnDwdmCmnClientPortOdu1TimDetectionMode     AluWdmTimDetectionMode
        }

    tnDwdmCmnClientPortOchOtu1FecMode OBJECT-TYPE
        SYNTAX         AluWdmFecMode
        MAX-ACCESS     read-create
        STATUS         current
        DESCRIPTION    "OTU1 FEC mode."
        DEFVAL         { g709Fec }
        ::= { tnDwdmCmnOtu1Odu1ClientPortConfigEntry 1 }

    tnDwdmCmnClientPortOchOtu1Rate OBJECT-TYPE
        SYNTAX         AluWdmPortOchOtuRate
        MAX-ACCESS     read-create
        STATUS         current
        DESCRIPTION    "OTU1 rate."
        DEFVAL         { otm10G709 }
        ::= { tnDwdmCmnOtu1Odu1ClientPortConfigEntry 2 }

    tnDwdmCmnClientPortOtu1TransmittedTti OBJECT-TYPE
        SYNTAX         OCTET STRING
        MAX-ACCESS     read-create
        STATUS         current
        DESCRIPTION    "OTU1 transmitted TTI."
        DEFVAL         { "" }
        ::= { tnDwdmCmnOtu1Odu1ClientPortConfigEntry 3 }

    tnDwdmCmnClientPortOtu1ExpectedTti OBJECT-TYPE
        SYNTAX         OCTET STRING
        MAX-ACCESS     read-create
        STATUS         current
        DESCRIPTION    "OTU1 expected TTI."
        DEFVAL         { "" }
        ::= { tnDwdmCmnOtu1Odu1ClientPortConfigEntry 4 }

    tnDwdmCmnClientPortOtu1TimConsequenceAction OBJECT-TYPE
        SYNTAX         AluWdmDisabledEnabled
        MAX-ACCESS     read-create
        STATUS         current
        DESCRIPTION    "OTU1 TIM consequence action."
        DEFVAL         { disabled }
        ::= { tnDwdmCmnOtu1Odu1ClientPortConfigEntry 5 }

    tnDwdmCmnClientPortOtu1TimDetectionMode OBJECT-TYPE
        SYNTAX         AluWdmTimDetectionMode
        MAX-ACCESS     read-create
        STATUS         current
        DESCRIPTION    "OTU1 TIM detection mode."
        DEFVAL         { off }
        ::= { tnDwdmCmnOtu1Odu1ClientPortConfigEntry 6 }

    tnDwdmCmnClientPortOdu1TransmittedTti OBJECT-TYPE
        SYNTAX         OCTET STRING
        MAX-ACCESS     read-create
        STATUS         current
        DESCRIPTION    "ODU1 transmitted TTI."
        DEFVAL         { "" }
        ::= { tnDwdmCmnOtu1Odu1ClientPortConfigEntry 7 }

    tnDwdmCmnClientPortOdu1ExpectedTti OBJECT-TYPE
        SYNTAX         OCTET STRING
        MAX-ACCESS     read-create
        STATUS         current
        DESCRIPTION    "ODU1 expected TTI."
        DEFVAL         { "" }
        ::= { tnDwdmCmnOtu1Odu1ClientPortConfigEntry 8 }

    tnDwdmCmnClientPortOdu1TimDetectionMode OBJECT-TYPE
        SYNTAX         AluWdmTimDetectionMode
        MAX-ACCESS     read-create
        STATUS         current
        DESCRIPTION    "ODU1 TIM detection mode."
        DEFVAL         { off }
        ::= { tnDwdmCmnOtu1Odu1ClientPortConfigEntry 9 }

--------------------------------------------------------------------------------
-- 43STX4 Optical Port Config Scalar
--------------------------------------------------------------------------------
    tn43stx4PortConfigAttributeTotal OBJECT-TYPE
        SYNTAX         Integer32
        MAX-ACCESS     read-only
        STATUS         current
        DESCRIPTION    "."
        ::= { tnOpticalPortConfig 96 }

--------------------------------------------------------------------------------
-- 43STX4 Optical Port Config Table
--------------------------------------------------------------------------------
    tn43stx4PortConfigTable OBJECT-TYPE
        SYNTAX         SEQUENCE OF Tn43stx4PortConfigEntry
        MAX-ACCESS     not-accessible
        STATUS         current
        DESCRIPTION    "The ports on a 43STX4 optical card."
        ::= { tnOpticalPortConfig 97 }

    tn43stx4PortConfigEntry OBJECT-TYPE
        SYNTAX         Tn43stx4PortConfigEntry
        MAX-ACCESS     not-accessible
        STATUS         current
        DESCRIPTION    "."
        INDEX { ifIndex }
        ::= { tn43stx4PortConfigTable 1 }

    Tn43stx4PortConfigEntry ::=
        SEQUENCE {
            tn43stx4PortConfigFunction INTEGER
        }

    tn43stx4PortConfigFunction OBJECT-TYPE
        SYNTAX         INTEGER {
                         network(1),
                         client(2)
                       }
        MAX-ACCESS     read-only
        STATUS         current
        DESCRIPTION    "Indicates the functional type of this 43STX4 port."
        ::= { tn43stx4PortConfigEntry 1 }

--------------------------------------------------------------------------------
-- DWDM Common OTU3/ODU3 Line Port Config Table
--------------------------------------------------------------------------------
    tnDwdmCmnOtu3Odu3LinePortConfigTable OBJECT-TYPE
        SYNTAX         SEQUENCE OF TnDwdmCmnOtu3Odu3LinePortConfigEntry
        MAX-ACCESS     not-accessible
        STATUS         current
        DESCRIPTION    "Common attributes against DWDM line ports."
        ::= { tnOpticalPortConfig 98 }

    tnDwdmCmnOtu3Odu3LinePortConfigEntry OBJECT-TYPE
        SYNTAX         TnDwdmCmnOtu3Odu3LinePortConfigEntry
        MAX-ACCESS     not-accessible
        STATUS         current
        DESCRIPTION    "."
        INDEX { ifIndex }
        ::= { tnDwdmCmnOtu3Odu3LinePortConfigTable 1 }

    TnDwdmCmnOtu3Odu3LinePortConfigEntry ::=
        SEQUENCE {
            tnDwdmCmnLinePortOchOtu3FecMode            AluWdmFecMode,
            tnDwdmCmnLinePortOtu3TransmittedTti        OCTET STRING,
            tnDwdmCmnLinePortOtu3ExpectedTti           OCTET STRING,
            tnDwdmCmnLinePortOtu3TimConsequenceAction  AluWdmDisabledEnabled,
            tnDwdmCmnLinePortOtu3TimDetectionMode      AluWdmTimDetectionMode,
            tnDwdmCmnLinePortOdu3PayloadType           Unsigned32,
            tnDwdmCmnLinePortOdu3PlmConsequenceAction  TruthValue,
            tnDwdmCmnLinePortOdu3TransmittedTti        OCTET STRING,
            tnDwdmCmnLinePortOdu3ExpectedTti           OCTET STRING,
            tnDwdmCmnLinePortOdu3TimConsequenceAction  AluWdmDisabledEnabled,
            tnDwdmCmnLinePortOdu3TimDetectionMode      AluWdmTimDetectionMode,
            tnDwdmCmnLinePortOdu3MappingMode           AluWdmMappingMode,
            tnDwdmCmnLinePortOchOtu3Rate               AluWdmPortOchOtuRate,
            tnDwdmCmnLinePortOdu3Interworking          TruthValue
        }

    tnDwdmCmnLinePortOchOtu3FecMode OBJECT-TYPE
        SYNTAX         AluWdmFecMode
        MAX-ACCESS     read-create
        STATUS         current
        DESCRIPTION    "OTU3 FEC mode.  Default is uFec for 43STA1P and
                        aFec for other supported cards."
        ::= { tnDwdmCmnOtu3Odu3LinePortConfigEntry 1 }

    tnDwdmCmnLinePortOtu3TransmittedTti OBJECT-TYPE
        SYNTAX         OCTET STRING
        MAX-ACCESS     read-create
        STATUS         current
        DESCRIPTION    "OTU3 transmitted TTI."
        DEFVAL         { "" }
        ::= { tnDwdmCmnOtu3Odu3LinePortConfigEntry 2 }

    tnDwdmCmnLinePortOtu3ExpectedTti OBJECT-TYPE
        SYNTAX         OCTET STRING
        MAX-ACCESS     read-create
        STATUS         current
        DESCRIPTION    "OTU3 expected TTI."
        DEFVAL         { "" }
        ::= { tnDwdmCmnOtu3Odu3LinePortConfigEntry 3 }

    tnDwdmCmnLinePortOtu3TimConsequenceAction OBJECT-TYPE
        SYNTAX         AluWdmDisabledEnabled
        MAX-ACCESS     read-create
        STATUS         current
        DESCRIPTION    "OTU3 TIM consequence action."
        DEFVAL         { disabled }
        ::= { tnDwdmCmnOtu3Odu3LinePortConfigEntry 4 }

    tnDwdmCmnLinePortOtu3TimDetectionMode OBJECT-TYPE
        SYNTAX         AluWdmTimDetectionMode
        MAX-ACCESS     read-create
        STATUS         current
        DESCRIPTION    "OTU3 TIM detection mode."
        DEFVAL         { off }
        ::= { tnDwdmCmnOtu3Odu3LinePortConfigEntry 5 }

    tnDwdmCmnLinePortOdu3PayloadType OBJECT-TYPE
        SYNTAX         Unsigned32
        MAX-ACCESS     read-create
        STATUS         current
        DESCRIPTION    "ODU3 payload type.

                        Current configurable range: 0 to 255."
        DEFVAL         { 32 }
        ::= { tnDwdmCmnOtu3Odu3LinePortConfigEntry 6 }

    tnDwdmCmnLinePortOdu3PlmConsequenceAction OBJECT-TYPE
        SYNTAX         TruthValue
        MAX-ACCESS     read-create
        STATUS         current
        DESCRIPTION    "PLM consequence action."
        DEFVAL         { false }
        ::= { tnDwdmCmnOtu3Odu3LinePortConfigEntry 7 }

    tnDwdmCmnLinePortOdu3TransmittedTti OBJECT-TYPE
        SYNTAX         OCTET STRING
        MAX-ACCESS     read-create
        STATUS         current
        DESCRIPTION    "ODU3 transmitted TTI."
        DEFVAL         { "" }
        ::= { tnDwdmCmnOtu3Odu3LinePortConfigEntry 8 }

    tnDwdmCmnLinePortOdu3ExpectedTti OBJECT-TYPE
        SYNTAX         OCTET STRING
        MAX-ACCESS     read-create
        STATUS         current
        DESCRIPTION    "ODU3 expected TTI."
        DEFVAL         { "" }
        ::= { tnDwdmCmnOtu3Odu3LinePortConfigEntry 9 }

    tnDwdmCmnLinePortOdu3TimConsequenceAction OBJECT-TYPE
        SYNTAX         AluWdmDisabledEnabled
        MAX-ACCESS     read-create
        STATUS         current
        DESCRIPTION    "ODU3 TIM consequence action."
        DEFVAL         { disabled }
        ::= { tnDwdmCmnOtu3Odu3LinePortConfigEntry 10 }

    tnDwdmCmnLinePortOdu3TimDetectionMode OBJECT-TYPE
        SYNTAX         AluWdmTimDetectionMode
        MAX-ACCESS     read-create
        STATUS         current
        DESCRIPTION    "ODU3 TIM detection mode."
        DEFVAL         { off }
        ::= { tnDwdmCmnOtu3Odu3LinePortConfigEntry 11 }

    tnDwdmCmnLinePortOdu3MappingMode OBJECT-TYPE
        SYNTAX         AluWdmMappingMode
        MAX-ACCESS     read-create
        STATUS         current
        DESCRIPTION    "ODU3 mapping mode."
        DEFVAL         { rsB }
        ::= { tnDwdmCmnOtu3Odu3LinePortConfigEntry 12 }

    tnDwdmCmnLinePortOchOtu3Rate OBJECT-TYPE
        SYNTAX         AluWdmPortOchOtuRate
        MAX-ACCESS     read-create
        STATUS         current
        DESCRIPTION    "OTU3 rate."
        DEFVAL         { otm43G018 }
        ::= { tnDwdmCmnOtu3Odu3LinePortConfigEntry 13 }

    tnDwdmCmnLinePortOdu3Interworking OBJECT-TYPE
        SYNTAX         TruthValue
        MAX-ACCESS     read-create
        STATUS         current
        DESCRIPTION    "ODU3 interworking Mode."
        DEFVAL         { false }
        ::= { tnDwdmCmnOtu3Odu3LinePortConfigEntry 14 }

--------------------------------------------------------------------------------
-- ALPFGK Optical Port Config Scalar
--------------------------------------------------------------------------------
    tnAlpfgkPortConfigAttributeTotal OBJECT-TYPE
        SYNTAX         Integer32
        MAX-ACCESS     read-only
        STATUS         current
        DESCRIPTION    "."
        ::= { tnOpticalPortConfig 99 }

--------------------------------------------------------------------------------
-- ALPFGK Optical Port Config Table
--------------------------------------------------------------------------------
    tnAlpfgkPortConfigTable OBJECT-TYPE
        SYNTAX         SEQUENCE OF TnAlpfgkPortConfigEntry
        MAX-ACCESS     not-accessible
        STATUS         current
        DESCRIPTION    "The ports on an ALPFGK optical card."
        ::= { tnOpticalPortConfig 100 }

    tnAlpfgkPortConfigEntry OBJECT-TYPE
        SYNTAX         TnAlpfgkPortConfigEntry
        MAX-ACCESS     not-accessible
        STATUS         current
        DESCRIPTION    "."
        INDEX { ifIndex }
        ::= { tnAlpfgkPortConfigTable 1 }

    TnAlpfgkPortConfigEntry ::=
        SEQUENCE {
            tnAlpfgkPortConfigFunction  INTEGER
        }

    tnAlpfgkPortConfigFunction OBJECT-TYPE
        SYNTAX         INTEGER {
                         line(1),
                         signal(2),
                         inv(3),
                         osc(4),
                         oscSfp(5)
                       }
        MAX-ACCESS     read-only
        STATUS         current
        DESCRIPTION    "Indicates the functional type of this ALPFGK port."
        ::= { tnAlpfgkPortConfigEntry 1 }

--------------------------------------------------------------------------------
-- 4DPA2 Optical Port Config Scalar
--------------------------------------------------------------------------------
    tn4dpa2PortConfigAttributeTotal OBJECT-TYPE
        SYNTAX         Integer32
        MAX-ACCESS     read-only
        STATUS         current
        DESCRIPTION    "."
        ::= { tnOpticalPortConfig 101 }

--------------------------------------------------------------------------------
-- 4DPA2 Optical Port Config Table
--------------------------------------------------------------------------------
    tn4dpa2PortConfigTable OBJECT-TYPE
        SYNTAX         SEQUENCE OF Tn4dpa2PortConfigEntry
        MAX-ACCESS     not-accessible
        STATUS         current
        DESCRIPTION    "The ports on a 4DPA2 optical card."
        ::= { tnOpticalPortConfig 102 }

    tn4dpa2PortConfigEntry OBJECT-TYPE
        SYNTAX         Tn4dpa2PortConfigEntry
        MAX-ACCESS     not-accessible
        STATUS         current
        DESCRIPTION    "."
        INDEX { ifIndex }
        ::= { tn4dpa2PortConfigTable 1 }

    Tn4dpa2PortConfigEntry ::=
        SEQUENCE {
            tn4dpa2PortConfigFunction INTEGER
        }

    tn4dpa2PortConfigFunction OBJECT-TYPE
        SYNTAX         INTEGER {
                         network(1),
                         client(2)
                       }
        MAX-ACCESS     read-only
        STATUS         current
        DESCRIPTION    "Indicates the functional type of this 4DPA2 port."
        ::= { tn4dpa2PortConfigEntry 1 }

--------------------------------------------------------------------------------
-- 43STA1P Optical Port Config Scalar
--------------------------------------------------------------------------------
    tn43sta1pPortConfigAttributeTotal OBJECT-TYPE
        SYNTAX         Integer32
        MAX-ACCESS     read-only
        STATUS         current
        DESCRIPTION    "."
        ::= { tnOpticalPortConfig 103 }

--------------------------------------------------------------------------------
-- 43STA1P Optical Port Config Table
--------------------------------------------------------------------------------
    tn43sta1pPortConfigTable OBJECT-TYPE
        SYNTAX         SEQUENCE OF Tn43sta1pPortConfigEntry
        MAX-ACCESS     not-accessible
        STATUS         current
        DESCRIPTION    "The ports on a 43STA1P optical card."
        ::= { tnOpticalPortConfig 104 }

    tn43sta1pPortConfigEntry OBJECT-TYPE
        SYNTAX         Tn43sta1pPortConfigEntry
        MAX-ACCESS     not-accessible
        STATUS         current
        DESCRIPTION    "."
        INDEX { ifIndex }
        ::= { tn43sta1pPortConfigTable 1 }

    Tn43sta1pPortConfigEntry ::=
        SEQUENCE {
            tn43sta1pPortConfigFunction INTEGER
        }

    tn43sta1pPortConfigFunction OBJECT-TYPE
        SYNTAX         INTEGER {
                         network(1),
                         client(2)
                       }
        MAX-ACCESS     read-only
        STATUS         current
        DESCRIPTION    "Indicates the functional type of this 43STA1P port."
        ::= { tn43sta1pPortConfigEntry 1 }

--------------------------------------------------------------------------------
-- 43STX4P Optical Port Config Scalar
--------------------------------------------------------------------------------
    tn43stx4pPortConfigAttributeTotal OBJECT-TYPE
        SYNTAX         Integer32
        MAX-ACCESS     read-only
        STATUS         current
        DESCRIPTION    "."
        ::= { tnOpticalPortConfig 105 }

--------------------------------------------------------------------------------
-- 43STX4P Optical Port Config Table
--------------------------------------------------------------------------------
    tn43stx4pPortConfigTable OBJECT-TYPE
        SYNTAX         SEQUENCE OF Tn43stx4pPortConfigEntry
        MAX-ACCESS     not-accessible
        STATUS         current
        DESCRIPTION    "The ports on a 43STX4P optical card."
        ::= { tnOpticalPortConfig 106 }

    tn43stx4pPortConfigEntry OBJECT-TYPE
        SYNTAX         Tn43stx4pPortConfigEntry
        MAX-ACCESS     not-accessible
        STATUS         current
        DESCRIPTION    "."
        INDEX { ifIndex }
        ::= { tn43stx4pPortConfigTable 1 }

    Tn43stx4pPortConfigEntry ::=
        SEQUENCE {
            tn43stx4pPortConfigFunction INTEGER
        }

    tn43stx4pPortConfigFunction OBJECT-TYPE
        SYNTAX         INTEGER {
                         network(1),
                         client(2)
                       }
        MAX-ACCESS     read-only
        STATUS         current
        DESCRIPTION    "Indicates the functional type of this 43STX4P port."
        ::= { tn43stx4pPortConfigEntry 1 }

--------------------------------------------------------------------------------
-- A2325A Optical Port Config Scalar
--------------------------------------------------------------------------------
    tnA2325aPortConfigAttributeTotal OBJECT-TYPE
        SYNTAX         Integer32
        MAX-ACCESS     read-only
        STATUS         current
        DESCRIPTION    "."
        ::= { tnOpticalPortConfig 109 }

--------------------------------------------------------------------------------
-- A2325A Optical Port Config Table
--------------------------------------------------------------------------------
    tnA2325aPortConfigTable OBJECT-TYPE
        SYNTAX         SEQUENCE OF TnA2325aPortConfigEntry
        MAX-ACCESS     not-accessible
        STATUS         current
        DESCRIPTION    "The ports on an A2325A optical card."
        ::= { tnOpticalPortConfig 110 }

    tnA2325aPortConfigEntry OBJECT-TYPE
        SYNTAX         TnA2325aPortConfigEntry
        MAX-ACCESS     not-accessible
        STATUS         current
        DESCRIPTION    "."
        INDEX { ifIndex }
        ::= { tnA2325aPortConfigTable 1 }

    TnA2325aPortConfigEntry ::=
        SEQUENCE {
            tnA2325aPortConfigFunction INTEGER
        }

    tnA2325aPortConfigFunction OBJECT-TYPE
        SYNTAX         INTEGER {
                         line(1),
                         signal(2),
                         dcm(3),
                         inv(4),
                         osc(5),
                         custLan(6)
                       }
        MAX-ACCESS     read-only
        STATUS         current
        DESCRIPTION    "Indicates the functional type of this A2325A port."
        ::= { tnA2325aPortConfigEntry 1 }

--------------------------------------------------------------------------------
-- SFD40 Optical Port Config Scalar
--------------------------------------------------------------------------------
    tnSfd40PortConfigAttributeTotal OBJECT-TYPE
        SYNTAX         Integer32
        MAX-ACCESS     read-only
        STATUS         current
        DESCRIPTION    "."
        ::= { tnOpticalPortConfig 111 }

--------------------------------------------------------------------------------
-- SFD40 Optical Port Config Table
--------------------------------------------------------------------------------
    tnSfd40PortConfigTable OBJECT-TYPE
        SYNTAX         SEQUENCE OF TnSfd40PortConfigEntry
        MAX-ACCESS     not-accessible
        STATUS         current
        DESCRIPTION    "The ports on a SFD40 optical card."
        ::= { tnOpticalPortConfig 112 }

    tnSfd40PortConfigEntry OBJECT-TYPE
        SYNTAX         TnSfd40PortConfigEntry
        MAX-ACCESS     not-accessible
        STATUS         current
        DESCRIPTION    "."
        INDEX { ifIndex }
        ::= { tnSfd40PortConfigTable 1 }

    TnSfd40PortConfigEntry ::=
        SEQUENCE {
            tnSfd40PortConfigFunction INTEGER
        }

    tnSfd40PortConfigFunction OBJECT-TYPE
        SYNTAX         INTEGER {
                         channel(1),
                         mux(2)
                       }
        MAX-ACCESS     read-only
        STATUS         current
        DESCRIPTION    "."
        ::= { tnSfd40PortConfigEntry 1 }

--------------------------------------------------------------------------------
-- SFD40B Optical Port Config Scalar
--------------------------------------------------------------------------------
    tnSfd40bPortConfigAttributeTotal OBJECT-TYPE
        SYNTAX         Integer32
        MAX-ACCESS     read-only
        STATUS         current
        DESCRIPTION    "."
        ::= { tnOpticalPortConfig 113 }

--------------------------------------------------------------------------------
-- SFD40B Optical Port Config Table
--------------------------------------------------------------------------------
    tnSfd40bPortConfigTable OBJECT-TYPE
        SYNTAX         SEQUENCE OF TnSfd40bPortConfigEntry
        MAX-ACCESS     not-accessible
        STATUS         current
        DESCRIPTION    "The ports on a SFD40B optical card."
        ::= { tnOpticalPortConfig 114 }

    tnSfd40bPortConfigEntry OBJECT-TYPE
        SYNTAX         TnSfd40bPortConfigEntry
        MAX-ACCESS     not-accessible
        STATUS         current
        DESCRIPTION    "."
        INDEX { ifIndex }
        ::= { tnSfd40bPortConfigTable 1 }

    TnSfd40bPortConfigEntry ::=
        SEQUENCE {
            tnSfd40bPortConfigFunction INTEGER
        }

    tnSfd40bPortConfigFunction OBJECT-TYPE
        SYNTAX         INTEGER {
                         channel(1),
                         mux(2)
                       }
        MAX-ACCESS     read-only
        STATUS         current
        DESCRIPTION    "."
        ::= { tnSfd40bPortConfigEntry 1 }

--------------------------------------------------------------------------------
-- 11QPA4 Optical Port Config Scalar
--------------------------------------------------------------------------------
    tn11qpa4PortConfigAttributeTotal OBJECT-TYPE
        SYNTAX         Integer32
        MAX-ACCESS     read-only
        STATUS         current
        DESCRIPTION    "."
        ::= { tnOpticalPortConfig 115 }

--------------------------------------------------------------------------------
-- 11QPA4 Optical Port Config Table
--------------------------------------------------------------------------------
    tn11qpa4PortConfigTable OBJECT-TYPE
        SYNTAX         SEQUENCE OF Tn11qpa4PortConfigEntry
        MAX-ACCESS     not-accessible
        STATUS         current
        DESCRIPTION    "The ports on a 11QPA4 optical card."
        ::= { tnOpticalPortConfig 116 }

    tn11qpa4PortConfigEntry OBJECT-TYPE
        SYNTAX         Tn11qpa4PortConfigEntry
        MAX-ACCESS     not-accessible
        STATUS         current
        DESCRIPTION    "."
        INDEX { ifIndex }
        ::= { tn11qpa4PortConfigTable 1 }

    Tn11qpa4PortConfigEntry ::=
        SEQUENCE {
            tn11qpa4PortConfigFunction INTEGER
        }

    tn11qpa4PortConfigFunction OBJECT-TYPE
        SYNTAX         INTEGER {
                         network(1),
                         client(2),
                         evoa(3)
                       }
        MAX-ACCESS     read-only
        STATUS         current
        DESCRIPTION    "Indicates the functional type of this 11QPA4 port."
        ::= { tn11qpa4PortConfigEntry 1 }

--------------------------------------------------------------------------------
-- 112SCX10 Optical Port Config Scalar
--------------------------------------------------------------------------------
    tn112scx10PortConfigAttributeTotal OBJECT-TYPE
        SYNTAX         Integer32
        MAX-ACCESS     read-only
        STATUS         current
        DESCRIPTION    "."
        ::= { tnOpticalPortConfig 117 }

--------------------------------------------------------------------------------
-- 112SCX10 Optical Port Config Table
--------------------------------------------------------------------------------
    tn112scx10PortConfigTable OBJECT-TYPE
        SYNTAX         SEQUENCE OF Tn112scx10PortConfigEntry
        MAX-ACCESS     not-accessible
        STATUS         current
        DESCRIPTION    "The ports on a 112SCX10 optical card."
        ::= { tnOpticalPortConfig 118 }

    tn112scx10PortConfigEntry OBJECT-TYPE
        SYNTAX         Tn112scx10PortConfigEntry
        MAX-ACCESS     not-accessible
        STATUS         current
        DESCRIPTION    "."
        INDEX { ifIndex }
        ::= { tn112scx10PortConfigTable 1 }

    Tn112scx10PortConfigEntry ::=
        SEQUENCE {
            tn112scx10PortConfigFunction INTEGER
        }

    tn112scx10PortConfigFunction OBJECT-TYPE
        SYNTAX         INTEGER {
                         network(1),
                         client(2)
                       }
        MAX-ACCESS     read-only
        STATUS         current
        DESCRIPTION    "Indicates the functional type of this 112SCX10 port."
        ::= { tn112scx10PortConfigEntry 1 }

--------------------------------------------------------------------------------
-- 112SCA1 Optical Port Config Scalar
--------------------------------------------------------------------------------
    tn112sca1PortConfigAttributeTotal OBJECT-TYPE
        SYNTAX         Integer32
        MAX-ACCESS     read-only
        STATUS         current
        DESCRIPTION    "."
        ::= { tnOpticalPortConfig 119 }

--------------------------------------------------------------------------------
-- 112SCA1 Optical Port Config Table
--------------------------------------------------------------------------------
    tn112sca1PortConfigTable OBJECT-TYPE
        SYNTAX         SEQUENCE OF Tn112sca1PortConfigEntry
        MAX-ACCESS     not-accessible
        STATUS         current
        DESCRIPTION    "The ports on a 112SCA1 optical card."
        ::= { tnOpticalPortConfig 120 }

    tn112sca1PortConfigEntry OBJECT-TYPE
        SYNTAX         Tn112sca1PortConfigEntry
        MAX-ACCESS     not-accessible
        STATUS         current
        DESCRIPTION    "."
        INDEX { ifIndex }
        ::= { tn112sca1PortConfigTable 1 }

    Tn112sca1PortConfigEntry ::=
        SEQUENCE {
            tn112sca1PortConfigFunction INTEGER
        }

    tn112sca1PortConfigFunction OBJECT-TYPE
        SYNTAX         INTEGER {
                         network(1),
                         client(2)
                       }
        MAX-ACCESS     read-only
        STATUS         current
        DESCRIPTION    "Indicates the functional type of this 112SCA1 port."
        ::= { tn112sca1PortConfigEntry 1 }

--------------------------------------------------------------------------------
-- DWDM Common OTU4/ODU4 Line Port Config Table
--------------------------------------------------------------------------------
    tnDwdmCmnOtu4Odu4LinePortConfigTable OBJECT-TYPE
        SYNTAX         SEQUENCE OF TnDwdmCmnOtu4Odu4LinePortConfigEntry
        MAX-ACCESS     not-accessible
        STATUS         current
        DESCRIPTION    "Common attributes against DWDM line ports."
        ::= { tnOpticalPortConfig 121 }

    tnDwdmCmnOtu4Odu4LinePortConfigEntry OBJECT-TYPE
        SYNTAX         TnDwdmCmnOtu4Odu4LinePortConfigEntry
        MAX-ACCESS     not-accessible
        STATUS         current
        DESCRIPTION    "."
        INDEX { ifIndex }
        ::= { tnDwdmCmnOtu4Odu4LinePortConfigTable 1 }

    TnDwdmCmnOtu4Odu4LinePortConfigEntry ::=
        SEQUENCE {
            tnDwdmCmnLinePortOchOtu4FecMode            AluWdmFecMode,
            tnDwdmCmnLinePortOchOtu4Rate               AluWdmPortOchOtuRate,
            tnDwdmCmnLinePortOtu4TransmittedTti        OCTET STRING,
            tnDwdmCmnLinePortOtu4ExpectedTti           OCTET STRING,
            tnDwdmCmnLinePortOtu4TimConsequenceAction  AluWdmDisabledEnabled,
            tnDwdmCmnLinePortOtu4TimDetectionMode      AluWdmTimDetectionMode,
            tnDwdmCmnLinePortOdu4PayloadType           Unsigned32,
            tnDwdmCmnLinePortOdu4PlmConsequenceAction  TruthValue,
            tnDwdmCmnLinePortOdu4TransmittedTti        OCTET STRING,
            tnDwdmCmnLinePortOdu4ExpectedTti           OCTET STRING,
            tnDwdmCmnLinePortOdu4TimConsequenceAction  AluWdmDisabledEnabled,
            tnDwdmCmnLinePortOdu4TimDetectionMode      AluWdmTimDetectionMode,
            tnDwdmCmnLinePortOtu4RegenResponse         INTEGER,
            tnDwdmCmnLinePortOdu4Interworking          TruthValue,
            tnDwdmCmnLinePortOtu4holdofftimer          AluWdmDisabledEnabled,  -- deprecated
            tnDwdmCmnLinePortOdu4112GInterworking      TruthValue,
            tnDwdmCmnLinePortOdu4DMConfigCMEPMode      INTEGER,
            tnDwdmCmnLinePortOdu4DMConfigEnable        INTEGER,
            tnDwdmCmnLinePortOdu4CndRes                INTEGER,
            tnDwdmCmnLinePortOdu4Encoding              INTEGER
        }

    tnDwdmCmnLinePortOchOtu4FecMode OBJECT-TYPE
        SYNTAX         AluWdmFecMode
        MAX-ACCESS     read-create
        STATUS         current
        DESCRIPTION    "OTU4 FEC mode.  Default is sdFec for 130SCX10,
                        130SNX10, 130SCA1, 130SCUP, 130SCUPB, and 130SCUPC;
                        and aFec for other cards."
        ::= { tnDwdmCmnOtu4Odu4LinePortConfigEntry 1 }

    tnDwdmCmnLinePortOchOtu4Rate OBJECT-TYPE
        SYNTAX         AluWdmPortOchOtuRate
        MAX-ACCESS     read-create
        STATUS         current
        DESCRIPTION    "OTU4 rate."
        DEFVAL         { otm111G810 }
        ::= { tnDwdmCmnOtu4Odu4LinePortConfigEntry 2 }

    tnDwdmCmnLinePortOtu4TransmittedTti OBJECT-TYPE
        SYNTAX         OCTET STRING
        MAX-ACCESS     read-create
        STATUS         current
        DESCRIPTION    "OTU4 transmitted TTI."
        DEFVAL         { "" }
        ::= { tnDwdmCmnOtu4Odu4LinePortConfigEntry 3 }

    tnDwdmCmnLinePortOtu4ExpectedTti OBJECT-TYPE
        SYNTAX         OCTET STRING
        MAX-ACCESS     read-create
        STATUS         current
        DESCRIPTION    "OTU4 expected TTI."
        DEFVAL         { "" }
        ::= { tnDwdmCmnOtu4Odu4LinePortConfigEntry 4 }

    tnDwdmCmnLinePortOtu4TimConsequenceAction OBJECT-TYPE
        SYNTAX         AluWdmDisabledEnabled
        MAX-ACCESS     read-create
        STATUS         current
        DESCRIPTION    "OTU4 TIM consequence action."
        DEFVAL         { disabled }
        ::= { tnDwdmCmnOtu4Odu4LinePortConfigEntry 5 }

    tnDwdmCmnLinePortOtu4TimDetectionMode OBJECT-TYPE
        SYNTAX         AluWdmTimDetectionMode
        MAX-ACCESS     read-create
        STATUS         current
        DESCRIPTION    "OTU4 TIM detection mode."
        DEFVAL         { off }
        ::= { tnDwdmCmnOtu4Odu4LinePortConfigEntry 6 }

    tnDwdmCmnLinePortOdu4PayloadType OBJECT-TYPE
        SYNTAX         Unsigned32
        MAX-ACCESS     read-create
        STATUS         current
        DESCRIPTION    "ODU4 payload type.

                        Current configurable range: 0 to 255."
        ::= { tnDwdmCmnOtu4Odu4LinePortConfigEntry 7 }

    tnDwdmCmnLinePortOdu4PlmConsequenceAction OBJECT-TYPE
        SYNTAX         TruthValue
        MAX-ACCESS     read-create
        STATUS         current
        DESCRIPTION    "PLM consequence action."
        DEFVAL         { false }
        ::= { tnDwdmCmnOtu4Odu4LinePortConfigEntry 8 }

    tnDwdmCmnLinePortOdu4TransmittedTti OBJECT-TYPE
        SYNTAX         OCTET STRING
        MAX-ACCESS     read-create
        STATUS         current
        DESCRIPTION    "ODU4 transmitted TTI."
        DEFVAL         { "" }
        ::= { tnDwdmCmnOtu4Odu4LinePortConfigEntry 9 }

    tnDwdmCmnLinePortOdu4ExpectedTti OBJECT-TYPE
        SYNTAX         OCTET STRING
        MAX-ACCESS     read-create
        STATUS         current
        DESCRIPTION    "ODU4 expected TTI."
        DEFVAL         { "" }
        ::= { tnDwdmCmnOtu4Odu4LinePortConfigEntry 10 }

    tnDwdmCmnLinePortOdu4TimConsequenceAction OBJECT-TYPE
        SYNTAX         AluWdmDisabledEnabled
        MAX-ACCESS     read-create
        STATUS         current
        DESCRIPTION    "ODU4 TIM consequence action."
        DEFVAL         { disabled }
        ::= { tnDwdmCmnOtu4Odu4LinePortConfigEntry 11 }

    tnDwdmCmnLinePortOdu4TimDetectionMode OBJECT-TYPE
        SYNTAX         AluWdmTimDetectionMode
        MAX-ACCESS     read-create
        STATUS         current
        DESCRIPTION    "ODU4 TIM detection mode."
        DEFVAL         { off }
        ::= { tnDwdmCmnOtu4Odu4LinePortConfigEntry 12 }

    tnDwdmCmnLinePortOtu4RegenResponse OBJECT-TYPE
        SYNTAX         INTEGER {
                         laserOn(1),
                         laserOff(2)
                       }
        MAX-ACCESS     read-create
        STATUS         current
        DESCRIPTION    "The regen response mode."
        DEFVAL         { laserOn }
        ::= { tnDwdmCmnOtu4Odu4LinePortConfigEntry 13 }

    tnDwdmCmnLinePortOdu4Interworking OBJECT-TYPE
        SYNTAX         TruthValue
        MAX-ACCESS     read-create
        STATUS         current
        DESCRIPTION    "ODU4 interworking mode."
        DEFVAL         { false }
        ::= { tnDwdmCmnOtu4Odu4LinePortConfigEntry 14 }

    tnDwdmCmnLinePortOtu4holdofftimer OBJECT-TYPE
        SYNTAX         AluWdmDisabledEnabled
        MAX-ACCESS     read-create
        STATUS         deprecated
        DESCRIPTION    "Line port consequent action (whether it's AIS
                        insertion or laser off) must be delayed by a
                        hold-off timer."
        DEFVAL         { disabled }
        ::= { tnDwdmCmnOtu4Odu4LinePortConfigEntry 15 }

    tnDwdmCmnLinePortOdu4112GInterworking OBJECT-TYPE
        SYNTAX         TruthValue
        MAX-ACCESS     read-create
        STATUS         current
        DESCRIPTION    "ODU4 112G card interworking mode."
        DEFVAL         { false }
        ::= { tnDwdmCmnOtu4Odu4LinePortConfigEntry 16 }

    tnDwdmCmnLinePortOdu4DMConfigCMEPMode OBJECT-TYPE
        SYNTAX         INTEGER {
                         bypass(1),
                         source(2),
                         destination(3)
                       }
        MAX-ACCESS     read-create
        STATUS         current
        DESCRIPTION    "Connection Monitoring End Point Mode defined for
                        delay measurement on the specified entity."
        DEFVAL         { bypass }
        ::= { tnDwdmCmnOtu4Odu4LinePortConfigEntry 17 }

    tnDwdmCmnLinePortOdu4DMConfigEnable OBJECT-TYPE
        SYNTAX         INTEGER {
                         enable(1),
                         disable(2)
                       }
        MAX-ACCESS     read-create
        STATUS         current
        DESCRIPTION    "This attribute is used to enable or disable the
                        DM function."
        DEFVAL         { disable }
        ::= { tnDwdmCmnOtu4Odu4LinePortConfigEntry 18 }

    tnDwdmCmnLinePortOdu4CndRes OBJECT-TYPE
        SYNTAX         INTEGER {
                         c1d(1),
                         c8d(2)
                       }
        MAX-ACCESS     read-create
        STATUS         current
        DESCRIPTION    "."
        DEFVAL         { c1d }
        ::= { tnDwdmCmnOtu4Odu4LinePortConfigEntry 19 }

    tnDwdmCmnLinePortOdu4Encoding OBJECT-TYPE
        SYNTAX         INTEGER {
                        nrz(0),
                        pdpsk(1),
                        dpsk(2),
                        bpsk(3),
                        qpsk(4),
                        qpskEnhOsnr(5),
                        nrzCFP1(6),
                        icohpmqpsk(7),
                        duobinary(8),
                        qpskhperf2(9),
                        qam16(10),
                        qam8(11),
                        spqpsk(12),
                        qam64(13),
                        cohpm16qam250G(14),
                        unassigned(9997),
                        alien(9998),
                        unknown(9999)
             }
        MAX-ACCESS     read-create
        STATUS         current
        DESCRIPTION    "."
        ::= { tnDwdmCmnOtu4Odu4LinePortConfigEntry 20 }

--------------------------------------------------------------------------------
-- DWDM Common OTU4/ODU4 Client Port Config Table
--------------------------------------------------------------------------------
    tnDwdmCmnOtu4Odu4ClientPortConfigTable OBJECT-TYPE
        SYNTAX         SEQUENCE OF TnDwdmCmnOtu4Odu4ClientPortConfigEntry
        MAX-ACCESS     not-accessible
        STATUS         current
        DESCRIPTION    "Common attributes against DWDM client ports."
        ::= { tnOpticalPortConfig 122 }

    tnDwdmCmnOtu4Odu4ClientPortConfigEntry OBJECT-TYPE
        SYNTAX         TnDwdmCmnOtu4Odu4ClientPortConfigEntry
        MAX-ACCESS     not-accessible
        STATUS         current
        DESCRIPTION    "."
        INDEX { ifIndex }
        ::= { tnDwdmCmnOtu4Odu4ClientPortConfigTable 1 }

    TnDwdmCmnOtu4Odu4ClientPortConfigEntry ::=
        SEQUENCE {
            tnDwdmCmnClientPortOchOtu4FecMode            AluWdmFecMode,
            tnDwdmCmnClientPortOchOtu4Rate               AluWdmPortOchOtuRate,
            tnDwdmCmnClientPortOtu4TransmittedTti        OCTET STRING,
            tnDwdmCmnClientPortOtu4ExpectedTti           OCTET STRING,
            tnDwdmCmnClientPortOtu4TimConsequenceAction  AluWdmDisabledEnabled,
            tnDwdmCmnClientPortOtu4TimDetectionMode      AluWdmTimDetectionMode,
            tnDwdmCmnClientPortOdu4TransmittedTti        OCTET STRING,
            tnDwdmCmnClientPortOdu4ExpectedTti           OCTET STRING,
            tnDwdmCmnClientPortOdu4TimDetectionMode      AluWdmTimDetectionMode
--          obsolete
--            tnDwdmCmnClientPortOdu4IncomingTti           OCTET STRING,
--            tnDwdmCmnClientPortOdu4TtiStatus             AluWdmTtiStatus
    }

    tnDwdmCmnClientPortOchOtu4FecMode OBJECT-TYPE
        SYNTAX         AluWdmFecMode
        MAX-ACCESS     read-create
        STATUS         current
        DESCRIPTION    "OTU4 FEC mode."
        DEFVAL         { g709Fec }
        ::= { tnDwdmCmnOtu4Odu4ClientPortConfigEntry 1 }

    tnDwdmCmnClientPortOchOtu4Rate OBJECT-TYPE
        SYNTAX         AluWdmPortOchOtuRate
        MAX-ACCESS     read-create
        STATUS         current
        DESCRIPTION    "OTU4 rate."
        DEFVAL         { otm111G810 }
        ::= { tnDwdmCmnOtu4Odu4ClientPortConfigEntry 2 }

    tnDwdmCmnClientPortOtu4TransmittedTti OBJECT-TYPE
        SYNTAX         OCTET STRING
        MAX-ACCESS     read-create
        STATUS         current
        DESCRIPTION    "OTU4 transmitted TTI."
        DEFVAL         { "" }
        ::= { tnDwdmCmnOtu4Odu4ClientPortConfigEntry 3 }

    tnDwdmCmnClientPortOtu4ExpectedTti OBJECT-TYPE
        SYNTAX         OCTET STRING
        MAX-ACCESS     read-create
        STATUS         current
        DESCRIPTION    "OTU4 expected TTI."
        DEFVAL         { "" }
        ::= { tnDwdmCmnOtu4Odu4ClientPortConfigEntry 4 }

    tnDwdmCmnClientPortOtu4TimConsequenceAction OBJECT-TYPE
        SYNTAX         AluWdmDisabledEnabled
        MAX-ACCESS     read-create
        STATUS         current
        DESCRIPTION    "OTU4 TIM consequence action."
        DEFVAL         { disabled }
        ::= { tnDwdmCmnOtu4Odu4ClientPortConfigEntry 5 }

    tnDwdmCmnClientPortOtu4TimDetectionMode OBJECT-TYPE
        SYNTAX         AluWdmTimDetectionMode
        MAX-ACCESS     read-create
        STATUS         current
        DESCRIPTION    "OTU4 TIM detection mode."
        DEFVAL         { off }
        ::= { tnDwdmCmnOtu4Odu4ClientPortConfigEntry 6 }

    tnDwdmCmnClientPortOdu4TransmittedTti OBJECT-TYPE
        SYNTAX         OCTET STRING
        MAX-ACCESS     read-create
        STATUS         current
        DESCRIPTION    "ODU4 transmitted TTI."
        DEFVAL         { "" }
        ::= { tnDwdmCmnOtu4Odu4ClientPortConfigEntry 7 }

    tnDwdmCmnClientPortOdu4ExpectedTti OBJECT-TYPE
        SYNTAX         OCTET STRING
        MAX-ACCESS     read-create
        STATUS         current
        DESCRIPTION    "ODU4 expected TTI."
        DEFVAL         { "" }
        ::= { tnDwdmCmnOtu4Odu4ClientPortConfigEntry 8 }

    tnDwdmCmnClientPortOdu4TimDetectionMode OBJECT-TYPE
        SYNTAX         AluWdmTimDetectionMode
        MAX-ACCESS     read-create
        STATUS         current
        DESCRIPTION    "ODU4 TIM detection mode."
        DEFVAL         { off }
        ::= { tnDwdmCmnOtu4Odu4ClientPortConfigEntry 9 }

--    obsolete
--    tnDwdmCmnClientPortOdu4IncomingTti OBJECT-TYPE ::= { tnDwdmCmnOtu4Odu4ClientPortConfigEntry 10 }
--    tnDwdmCmnClientPortOdu4TtiStatus   OBJECT-TYPE ::= { tnDwdmCmnOtu4Odu4ClientPortConfigEntry 11 }

--------------------------------------------------------------------------------
-- RSMON Egress Port Config Table
--------------------------------------------------------------------------------
    tnRsmonEgrPortConfigTable OBJECT-TYPE
        SYNTAX         SEQUENCE OF TnRsmonEgrPortConfigEntry
        MAX-ACCESS     not-accessible
        STATUS         current
        DESCRIPTION    "Common attributes against RSMON Egress supported ports."
        ::= { tnOpticalPortConfig 123 }

    tnRsmonEgrPortConfigEntry OBJECT-TYPE
        SYNTAX         TnRsmonEgrPortConfigEntry
        MAX-ACCESS     not-accessible
        STATUS         current
        DESCRIPTION    "."
        INDEX { ifIndex }
        ::= { tnRsmonEgrPortConfigTable 1 }

    TnRsmonEgrPortConfigEntry ::=
        SEQUENCE {
            tnRsmonEgrPortTimod                 INTEGER,
            tnRsmonEgrPortSigMode               INTEGER,
            tnRsmonEgrPortTransmittedTti        OCTET STRING,
            tnRsmonEgrPortExpectedTti           OCTET STRING,
            tnRsmonEgrPortTimDetection          TruthValue,
            tnRsmonEgrPortTimConsequenceAction  AluWdmDisabledEnabled
        }

    tnRsmonEgrPortTimod OBJECT-TYPE
        SYNTAX         INTEGER {
                         notApplicable(1),
                         specific16Byte(2),
                         nonSpecificSingleByte(3),
                         specificSingleByte(4),
                         string64(5)
                       }
        MAX-ACCESS     read-create
        STATUS         current
        DESCRIPTION    "RSMON TIMOD."
        DEFVAL         { specific16Byte }
        ::= { tnRsmonEgrPortConfigEntry 1 }

    tnRsmonEgrPortSigMode OBJECT-TYPE
        SYNTAX         INTEGER {
                         transparent(1),
                         terminated(2)
                       }
        MAX-ACCESS     read-create
        STATUS         current
        DESCRIPTION    "RSMON signal mode."
        DEFVAL         { transparent }
        ::= { tnRsmonEgrPortConfigEntry 2 }

    tnRsmonEgrPortTransmittedTti OBJECT-TYPE
        SYNTAX         OCTET STRING
        MAX-ACCESS     read-create
        STATUS         current
        DESCRIPTION    "RSMON transmitted TTI."
        DEFVAL         { "" }
        ::= { tnRsmonEgrPortConfigEntry 3 }

    tnRsmonEgrPortExpectedTti OBJECT-TYPE
        SYNTAX         OCTET STRING
        MAX-ACCESS     read-create
        STATUS         current
        DESCRIPTION    "RSMON expected TTI."
        DEFVAL         { "" }
        ::= { tnRsmonEgrPortConfigEntry 4 }

    tnRsmonEgrPortTimDetection OBJECT-TYPE
        SYNTAX         TruthValue
        MAX-ACCESS     read-create
        STATUS         current
        DESCRIPTION    "RSMON TIM detection."
        DEFVAL         { false }
        ::= { tnRsmonEgrPortConfigEntry 5 }

    tnRsmonEgrPortTimConsequenceAction OBJECT-TYPE
        SYNTAX         AluWdmDisabledEnabled
        MAX-ACCESS     read-create
        STATUS         current
        DESCRIPTION    "RSMON TIM consequence action."
        DEFVAL         { disabled }
        ::= { tnRsmonEgrPortConfigEntry 6 }

--------------------------------------------------------------------------------
-- DWDM Common Rate Port Config Table
--------------------------------------------------------------------------------
    tnDwdmCbrArPortConfigTable OBJECT-TYPE
        SYNTAX         SEQUENCE OF TnDwdmCbrArPortConfigEntry
        MAX-ACCESS     not-accessible
        STATUS         current
        DESCRIPTION    "Common attributes for client port signal entities."
        ::= { tnOpticalPortConfig 124 }

    tnDwdmCbrArPortConfigEntry OBJECT-TYPE
        SYNTAX         TnDwdmCbrArPortConfigEntry
        MAX-ACCESS     not-accessible
        STATUS         current
        DESCRIPTION    "."
        INDEX { ifIndex }
        ::= { tnDwdmCbrArPortConfigTable 1 }

    TnDwdmCbrArPortConfigEntry ::=
        SEQUENCE {
            tnDwdmCbrArPortHdsdiRate  INTEGER
        }

    tnDwdmCbrArPortHdsdiRate OBJECT-TYPE
        SYNTAX         INTEGER {
                         hdSdi-1-485(1),
                         hdSdi-1-485-1-001(2)
                       }
        MAX-ACCESS     read-create
        STATUS         current
        DESCRIPTION    "HDSDI rate, which is compatible with existing NTSC
                        systems."
        DEFVAL         { hdSdi-1-485-1-001 }
        ::= { tnDwdmCbrArPortConfigEntry 1 }

--------------------------------------------------------------------------------
-- ALPFGT Optical Port Config Scalar
--------------------------------------------------------------------------------
    tnAlpfgtPortConfigAttributeTotal OBJECT-TYPE
        SYNTAX         Integer32
        MAX-ACCESS     read-only
        STATUS         current
        DESCRIPTION    "."
        ::= { tnOpticalPortConfig 125 }

--------------------------------------------------------------------------------
-- ALPFGT Optical Port Config Table
--------------------------------------------------------------------------------
    tnAlpfgtPortConfigTable OBJECT-TYPE
        SYNTAX         SEQUENCE OF TnAlpfgtPortConfigEntry
        MAX-ACCESS     not-accessible
        STATUS         current
        DESCRIPTION    "The ports on an ALPFGT optical card."
        ::= { tnOpticalPortConfig 126 }

    tnAlpfgtPortConfigEntry OBJECT-TYPE
        SYNTAX         TnAlpfgtPortConfigEntry
        MAX-ACCESS     not-accessible
        STATUS         current
        DESCRIPTION    "."
        INDEX { ifIndex }
        ::= { tnAlpfgtPortConfigTable 1 }

    TnAlpfgtPortConfigEntry ::=
        SEQUENCE {
            tnAlpfgtPortConfigFunction  INTEGER
        }

    tnAlpfgtPortConfigFunction OBJECT-TYPE
        SYNTAX         INTEGER {
                         line(1),
                         signal(2),
                         inv(3),
                         osc(4),
                         oscSfp(5)
                       }
        MAX-ACCESS     read-only
        STATUS         current
        DESCRIPTION    "Indicates the functional type of this ALPFGT port."
        ::= { tnAlpfgtPortConfigEntry 1 }

--------------------------------------------------------------------------------
-- OSCT Optical Port Config Scalar
--------------------------------------------------------------------------------
    tnOsctPortConfigAttributeTotal OBJECT-TYPE
        SYNTAX         Integer32
        MAX-ACCESS     read-only
        STATUS         current
        DESCRIPTION    "."
        ::= { tnOpticalPortConfig 127 }

--------------------------------------------------------------------------------
-- OSCT Optical Port Config Table
--------------------------------------------------------------------------------
    tnOsctPortConfigTable OBJECT-TYPE
        SYNTAX         SEQUENCE OF TnOsctPortConfigEntry
        MAX-ACCESS     not-accessible
        STATUS         current
        DESCRIPTION    "The ports on an OSCT optical card."
        ::= { tnOpticalPortConfig 128 }

    tnOsctPortConfigEntry OBJECT-TYPE
        SYNTAX         TnOsctPortConfigEntry
        MAX-ACCESS     not-accessible
        STATUS         current
        DESCRIPTION    "."
        INDEX { ifIndex }
        ::= { tnOsctPortConfigTable 1 }

    TnOsctPortConfigEntry ::=
        SEQUENCE {
            tnOsctPortConfigFunction  INTEGER
        }

    tnOsctPortConfigFunction OBJECT-TYPE
        SYNTAX         INTEGER {
                         signal(1),
                         line(2),
                         inv(3),
                         osc(4),
                         oscSfp(5)
                       }
        MAX-ACCESS     read-only
        STATUS         current
        DESCRIPTION    "Indicates the functional type of this OSCT port."
        ::= { tnOsctPortConfigEntry 1 }

--------------------------------------------------------------------------------
-- WTOCM Optical Port Config Scalar
--------------------------------------------------------------------------------
    tnWtocmPortConfigAttributeTotal OBJECT-TYPE
        SYNTAX         Integer32
        MAX-ACCESS     read-only
        STATUS         current
        DESCRIPTION    "."
        ::= { tnOpticalPortConfig 129 }

--------------------------------------------------------------------------------
-- WTOCM Optical Port Config Table
--------------------------------------------------------------------------------
    tnWtocmPortConfigTable OBJECT-TYPE
        SYNTAX         SEQUENCE OF TnWtocmPortConfigEntry
        MAX-ACCESS     not-accessible
        STATUS         current
        DESCRIPTION    "The ports on a WTOCM optical card."
        ::= { tnOpticalPortConfig 130 }

    tnWtocmPortConfigEntry OBJECT-TYPE
        SYNTAX         TnWtocmPortConfigEntry
        MAX-ACCESS     not-accessible
        STATUS         current
        DESCRIPTION    "."
        INDEX { ifIndex }
        ::= { tnWtocmPortConfigTable 1 }

    TnWtocmPortConfigEntry ::=
        SEQUENCE {
            tnWtocmPortConfigFunction  INTEGER
        }

    tnWtocmPortConfigFunction OBJECT-TYPE
        SYNTAX         INTEGER {
                         detect(1)
                       }
        MAX-ACCESS     read-only
        STATUS         current
        DESCRIPTION    "Indicates the functional type of this WTOCM port."
        ::= { tnWtocmPortConfigEntry 1 }

--------------------------------------------------------------------------------
-- WR2-88 Optical Port Config Scalar
--------------------------------------------------------------------------------
    tnWr2c88PortConfigAttributeTotal OBJECT-TYPE
        SYNTAX         Integer32
        MAX-ACCESS     read-only
        STATUS         current
        DESCRIPTION    "."
        ::= { tnOpticalPortConfig 131 }

--------------------------------------------------------------------------------
-- WR2-88 Optical Port Config Table
--------------------------------------------------------------------------------
    tnWr2c88PortConfigTable OBJECT-TYPE
        SYNTAX         SEQUENCE OF TnWr2c88PortConfigEntry
        MAX-ACCESS     not-accessible
        STATUS         current
        DESCRIPTION    "The ports on a WR2-88 optical card."
        ::= { tnOpticalPortConfig 132 }

    tnWr2c88PortConfigEntry OBJECT-TYPE
        SYNTAX         TnWr2c88PortConfigEntry
        MAX-ACCESS     not-accessible
        STATUS         current
        DESCRIPTION    "."
        INDEX { ifIndex }
        ::= { tnWr2c88PortConfigTable 1 }

    TnWr2c88PortConfigEntry ::=
        SEQUENCE {
            tnWr2c88PortConfigFunction  INTEGER
--            obsolete
--            tnWr2c88PortBlockerAging    Unsigned32
        }

    tnWr2c88PortConfigFunction OBJECT-TYPE
        SYNTAX         INTEGER {
                         signal(1),
                         thru(2),
                         dropOut(3),
                         addIn(4),
                         inv(5)
                       }
        MAX-ACCESS     read-only
        STATUS         current
        DESCRIPTION    "Indicates the functional type of this WR2-88 port."
        ::= { tnWr2c88PortConfigEntry 1 }

--    obsolete
--    tnWr2c88PortBlockerAging OBJECT-TYPE ::= { tnWr2c88PortConfigEntry 2 }

--------------------------------------------------------------------------------
-- AM2017B Optical Port Config Scalar
--------------------------------------------------------------------------------
    tnAm2017bPortConfigAttributeTotal OBJECT-TYPE
        SYNTAX         Integer32
        MAX-ACCESS     read-only
        STATUS         current
        DESCRIPTION    "."
        ::= { tnOpticalPortConfig 133 }

--------------------------------------------------------------------------------
-- AM2017B Optical Port Config Table
--------------------------------------------------------------------------------
    tnAm2017bPortConfigTable OBJECT-TYPE
        SYNTAX         SEQUENCE OF TnAm2017bPortConfigEntry
        MAX-ACCESS     not-accessible
        STATUS         current
        DESCRIPTION    "The ports on an AM2017B optical card."
        ::= { tnOpticalPortConfig 134 }

    tnAm2017bPortConfigEntry OBJECT-TYPE
        SYNTAX         TnAm2017bPortConfigEntry
        MAX-ACCESS     not-accessible
        STATUS         current
        DESCRIPTION    "."
        INDEX { ifIndex }
        ::= { tnAm2017bPortConfigTable 1 }

    TnAm2017bPortConfigEntry ::=
        SEQUENCE {
            tnAm2017bPortConfigFunction INTEGER
        }

    tnAm2017bPortConfigFunction OBJECT-TYPE
        SYNTAX         INTEGER {
                         line(1),
                         signal(2),
                         dcm(3),
                         inv(4),
                         osc(5)
--                         obsolete
--                         custLan(6)
                       }
        MAX-ACCESS     read-only
        STATUS         current
        DESCRIPTION    "Indicates the functional type of this AM2017B port."
        ::= { tnAm2017bPortConfigEntry 1 }

--------------------------------------------------------------------------------
-- AM2325B Optical Port Config Scalar
--------------------------------------------------------------------------------
    tnAm2325bPortConfigAttributeTotal OBJECT-TYPE
        SYNTAX         Integer32
        MAX-ACCESS     read-only
        STATUS         current
        DESCRIPTION    "."
        ::= { tnOpticalPortConfig 135 }

--------------------------------------------------------------------------------
-- AM2325B Optical Port Config Table
--------------------------------------------------------------------------------
    tnAm2325bPortConfigTable OBJECT-TYPE
        SYNTAX         SEQUENCE OF TnAm2325bPortConfigEntry
        MAX-ACCESS     not-accessible
        STATUS         current
        DESCRIPTION    "The ports on an AM2325B optical card."
        ::= { tnOpticalPortConfig 136 }

    tnAm2325bPortConfigEntry OBJECT-TYPE
        SYNTAX         TnAm2325bPortConfigEntry
        MAX-ACCESS     not-accessible
        STATUS         current
        DESCRIPTION    "."
        INDEX { ifIndex }
        ::= { tnAm2325bPortConfigTable 1 }

    TnAm2325bPortConfigEntry ::=
        SEQUENCE {
            tnAm2325bPortConfigFunction INTEGER
        }

    tnAm2325bPortConfigFunction OBJECT-TYPE
        SYNTAX         INTEGER {
                         line(1),
                         signal(2),
                         dcm(3),
                         inv(4),
                         osc(5)
--                         obsolete
--                         custLan(6)
                       }
        MAX-ACCESS     read-only
        STATUS         current
        DESCRIPTION    "Indicates the functional type of this AM2325B port."
        ::= { tnAm2325bPortConfigEntry 1 }

--------------------------------------------------------------------------------
-- 1DPP21 Optical Port Config Scalar
--------------------------------------------------------------------------------
    tn1dpp21PortConfigAttributeTotal OBJECT-TYPE
        SYNTAX         Integer32
        MAX-ACCESS     read-only
        STATUS         current
        DESCRIPTION    "."
        ::= { tnOpticalPortConfig 137 }

--------------------------------------------------------------------------------
-- 1DPP21 Optical Port Config Table
--------------------------------------------------------------------------------
    tn1dpp21PortConfigTable OBJECT-TYPE
        SYNTAX         SEQUENCE OF Tn1dpp21PortConfigEntry
        MAX-ACCESS     not-accessible
        STATUS         current
        DESCRIPTION    "The ports on a 1DPP21 optical card."
        ::= { tnOpticalPortConfig 138 }

    tn1dpp21PortConfigEntry OBJECT-TYPE
        SYNTAX         Tn1dpp21PortConfigEntry
        MAX-ACCESS     not-accessible
        STATUS         current
        DESCRIPTION    "."
        INDEX { ifIndex }
        ::= { tn1dpp21PortConfigTable 1 }

    Tn1dpp21PortConfigEntry ::=
        SEQUENCE {
            tn1dpp21PortConfigFunction INTEGER
        }

    tn1dpp21PortConfigFunction OBJECT-TYPE
        SYNTAX         INTEGER {
                         network(1),
                         client(2)
                       }
        MAX-ACCESS     read-only
        STATUS         current
        DESCRIPTION    "Indicates the functional type of this 1DPP21 port."
        ::= { tn1dpp21PortConfigEntry 1 }

--------------------------------------------------------------------------------
-- E1 T1 Port Config Table
--------------------------------------------------------------------------------
    tnE1T1PortConfigTable OBJECT-TYPE
        SYNTAX         SEQUENCE OF TnE1T1PortConfigEntry
        MAX-ACCESS     not-accessible
        STATUS         current
        DESCRIPTION    "Common attributes against E1 T1 supported ports."
        ::= { tnOpticalPortConfig 139 }

    tnE1T1PortConfigEntry OBJECT-TYPE
        SYNTAX         TnE1T1PortConfigEntry
        MAX-ACCESS     not-accessible
        STATUS         current
        DESCRIPTION    "."
        INDEX { ifIndex }
        ::= { tnE1T1PortConfigTable 1 }

    TnE1T1PortConfigEntry ::=
        SEQUENCE {
            tnE1T1MappingMode             INTEGER,
            tnE1T1Format                  INTEGER,
            tnE1T1ClientEgressTimingMode  INTEGER,
            tnE1T1PortConfigImpedance     INTEGER
        }

    tnE1T1MappingMode OBJECT-TYPE
        SYNTAX         INTEGER {
                         async(1)
                       }
        MAX-ACCESS     read-create
        STATUS         current
        DESCRIPTION    "E1 T1 MAP MODE."
        DEFVAL         { async }
        ::= { tnE1T1PortConfigEntry 1 }

    tnE1T1Format OBJECT-TYPE
        SYNTAX         INTEGER {
                         crc4mfrm(1),
                         dfrm(2)
                       }
        MAX-ACCESS     read-create
        STATUS         current
        DESCRIPTION    "E1 Frame Format."
        DEFVAL         { crc4mfrm }
        ::= { tnE1T1PortConfigEntry 2 }

    tnE1T1ClientEgressTimingMode OBJECT-TYPE
        SYNTAX         INTEGER {
                         system(1),
                         normal(2)
                       }
        MAX-ACCESS     read-create
        STATUS         current
        DESCRIPTION    "E1 T1 Client Egress Timing Mode."
        DEFVAL         { system }
        ::= { tnE1T1PortConfigEntry 3 }

    tnE1T1PortConfigImpedance OBJECT-TYPE
        SYNTAX         INTEGER {
                         imp75ohm(1),
                         imp120ohm(2)
                       }
        MAX-ACCESS     read-create
        STATUS         current
        DESCRIPTION    "E1 T1 port configurable impedance."
        DEFVAL         { imp75ohm }
        ::= { tnE1T1PortConfigEntry 4 }

--------------------------------------------------------------------------------
-- MVAC Optical Port Config Scalar
--------------------------------------------------------------------------------
    tnMvacPortConfigAttributeTotal OBJECT-TYPE
        SYNTAX         Integer32
        MAX-ACCESS     read-only
        STATUS         current
        DESCRIPTION    "."
        ::= { tnOpticalPortConfig 140 }

--------------------------------------------------------------------------------
-- MVAC Optical Port Config Table
--------------------------------------------------------------------------------
    tnMvacPortConfigTable OBJECT-TYPE
        SYNTAX         SEQUENCE OF TnMvacPortConfigEntry
        MAX-ACCESS     not-accessible
        STATUS         current
        DESCRIPTION    "The ports on a MVAC optical card."
        ::= { tnOpticalPortConfig 141 }

    tnMvacPortConfigEntry OBJECT-TYPE
        SYNTAX         TnMvacPortConfigEntry
        MAX-ACCESS     not-accessible
        STATUS         current
        DESCRIPTION    "."
        INDEX { ifIndex }
        ::= { tnMvacPortConfigTable 1 }

    TnMvacPortConfigEntry ::=
        SEQUENCE {
            tnMvacPortConfigFunction              INTEGER,
            tnMvacPortConfigVoaMode               INTEGER,
            tnMvacPortConfigAttenuationModeAtten  Integer32,
            tnMvacPortConfigConnToPort            InterfaceIndexOrZero
        }

    tnMvacPortConfigFunction OBJECT-TYPE
        SYNTAX         INTEGER {
                         general(1)
                       }
        MAX-ACCESS     read-only
        STATUS         current
        DESCRIPTION    "Indicates the functional type of this MVAC port."
        ::= { tnMvacPortConfigEntry 1 }

    tnMvacPortConfigVoaMode OBJECT-TYPE
        SYNTAX         INTEGER {
                         power(1),
                         attenuation(2)
                       }
        MAX-ACCESS     read-create
        STATUS         current
        DESCRIPTION    "Sets the port operating mode."
        DEFVAL         { power }
        ::= { tnMvacPortConfigEntry 2 }

    tnMvacPortConfigAttenuationModeAtten OBJECT-TYPE
        SYNTAX         Integer32
         UNITS         "mB"
        MAX-ACCESS     read-create
        STATUS         current
        DESCRIPTION    "Sets attenuation value in attenuation mode."
        DEFVAL         { 0 }
        ::= { tnMvacPortConfigEntry 3 }

    tnMvacPortConfigConnToPort OBJECT-TYPE
        SYNTAX         InterfaceIndexOrZero
        MAX-ACCESS     read-create
        STATUS         current
        DESCRIPTION    "Sets reference to degree input port when MVAC
                        port used external."
        DEFVAL         { 0 }
        ::= { tnMvacPortConfigEntry 4 }

--------------------------------------------------------------------------------
-- 43SCX4 Optical Port Config Scalar
--------------------------------------------------------------------------------
    tn43scx4PortConfigAttributeTotal OBJECT-TYPE
        SYNTAX         Integer32
        MAX-ACCESS     read-only
        STATUS         current
        DESCRIPTION    "."
        ::= { tnOpticalPortConfig 144 }

--------------------------------------------------------------------------------
-- 43SCX4 Optical Port Config Table
--------------------------------------------------------------------------------
    tn43scx4PortConfigTable OBJECT-TYPE
        SYNTAX         SEQUENCE OF Tn43scx4PortConfigEntry
        MAX-ACCESS     not-accessible
        STATUS         current
        DESCRIPTION    "The ports on a 43SCX4 optical card."
        ::= { tnOpticalPortConfig 145 }

    tn43scx4PortConfigEntry OBJECT-TYPE
        SYNTAX         Tn43scx4PortConfigEntry
        MAX-ACCESS     not-accessible
        STATUS         current
        DESCRIPTION    "."
        INDEX { ifIndex }
        ::= { tn43scx4PortConfigTable 1 }

    Tn43scx4PortConfigEntry ::=
        SEQUENCE {
            tn43scx4PortConfigFunction INTEGER
        }

    tn43scx4PortConfigFunction OBJECT-TYPE
        SYNTAX         INTEGER {
                         network(1),
                         client(2)
                       }
        MAX-ACCESS     read-only
        STATUS         current
        DESCRIPTION    "Indicates the functional type of this 43SCX4 port."
        ::= { tn43scx4PortConfigEntry 1 }

--------------------------------------------------------------------------------
-- RA2P Optical Port Config Scalar
--------------------------------------------------------------------------------
    tnRa2pPortConfigAttributeTotal OBJECT-TYPE
        SYNTAX         Integer32
        MAX-ACCESS     read-only
        STATUS         current
        DESCRIPTION    "."
        ::= { tnOpticalPortConfig 146 }

--------------------------------------------------------------------------------
-- RA2P Optical Port Config Table
--------------------------------------------------------------------------------
    tnRa2pPortConfigTable OBJECT-TYPE
        SYNTAX         SEQUENCE OF TnRa2pPortConfigEntry
        MAX-ACCESS     not-accessible
        STATUS         current
        DESCRIPTION    "The ports on a RA2P optical card."
        ::= { tnOpticalPortConfig 147 }

    tnRa2pPortConfigEntry OBJECT-TYPE
        SYNTAX         TnRa2pPortConfigEntry
        MAX-ACCESS     not-accessible
        STATUS         current
        DESCRIPTION    "."
        INDEX { ifIndex }
        ::= { tnRa2pPortConfigTable 1 }

    TnRa2pPortConfigEntry ::=
        SEQUENCE {
            tnRa2pPortConfigFunction INTEGER
        }

    tnRa2pPortConfigFunction OBJECT-TYPE
        SYNTAX         INTEGER {
                         lineIn(1),
                         lineOut(2)
                       }
        MAX-ACCESS     read-only
        STATUS         current
        DESCRIPTION    "Indicates the functional type of this RA2P port."
        ::= { tnRa2pPortConfigEntry 1 }

--------------------------------------------------------------------------------
-- AM2318A Optical Port Config Scalar
--------------------------------------------------------------------------------
    tnAm2318aPortConfigAttributeTotal OBJECT-TYPE
        SYNTAX         Integer32
        MAX-ACCESS     read-only
        STATUS         current
        DESCRIPTION    "."
        ::= { tnOpticalPortConfig 148 }

--------------------------------------------------------------------------------
-- AM2318A Optical Port Config Table
--------------------------------------------------------------------------------
    tnAm2318aPortConfigTable OBJECT-TYPE
        SYNTAX         SEQUENCE OF TnAm2318aPortConfigEntry
        MAX-ACCESS     not-accessible
        STATUS         current
        DESCRIPTION    "The ports on an AM2318A optical card."
        ::= { tnOpticalPortConfig 149 }

    tnAm2318aPortConfigEntry OBJECT-TYPE
        SYNTAX         TnAm2318aPortConfigEntry
        MAX-ACCESS     not-accessible
        STATUS         current
        DESCRIPTION    "."
        INDEX { ifIndex }
        ::= { tnAm2318aPortConfigTable 1 }

    TnAm2318aPortConfigEntry ::=
        SEQUENCE {
            tnAm2318aPortConfigFunction INTEGER
        }

    tnAm2318aPortConfigFunction OBJECT-TYPE
        SYNTAX         INTEGER {
                         lineIn(1),
                         inv(2),
                         osc(3),
                         lineOut(4),
                         oscSfp(5),
                         det(6),
                         custLan(7)
                       }
        MAX-ACCESS     read-only
        STATUS         current
        DESCRIPTION    "Indicates the functional type of this AM2318A port."
        ::= { tnAm2318aPortConfigEntry 1 }

--------------------------------------------------------------------------------
-- AM2125A Optical Port Config Scalar
--------------------------------------------------------------------------------
    tnAm2125aPortConfigAttributeTotal OBJECT-TYPE
        SYNTAX         Integer32
        MAX-ACCESS     read-only
        STATUS         current
        DESCRIPTION    "."
        ::= { tnOpticalPortConfig 150 }

--------------------------------------------------------------------------------
-- AM2125A Optical Port Config Table
--------------------------------------------------------------------------------
    tnAm2125aPortConfigTable OBJECT-TYPE
        SYNTAX         SEQUENCE OF TnAm2125aPortConfigEntry
        MAX-ACCESS     not-accessible
        STATUS         current
        DESCRIPTION    "The ports on an AM2125A optical card."
        ::= { tnOpticalPortConfig 151 }

    tnAm2125aPortConfigEntry OBJECT-TYPE
        SYNTAX         TnAm2125aPortConfigEntry
        MAX-ACCESS     not-accessible
        STATUS         current
        DESCRIPTION    "."
        INDEX { ifIndex }
        ::= { tnAm2125aPortConfigTable 1 }

    TnAm2125aPortConfigEntry ::=
        SEQUENCE {
            tnAm2125aPortConfigFunction INTEGER
        }

    tnAm2125aPortConfigFunction OBJECT-TYPE
        SYNTAX         INTEGER {
                         lineIn(1),
                         inv(2),
                         dcm(3),
                         lineOut(4),
                         oscSfp(5),
                         det(6),
                         osc(7),
                         custLan(8)
                       }
        MAX-ACCESS     read-only
        STATUS         current
        DESCRIPTION    "Indicates the functional type of this AM2125A port."
        ::= { tnAm2125aPortConfigEntry 1 }

--------------------------------------------------------------------------------
-- ITLU Optical Port Config Scalar
--------------------------------------------------------------------------------
    tnItluPortConfigAttributeTotal OBJECT-TYPE
        SYNTAX         Integer32
        MAX-ACCESS     read-only
        STATUS         current
        DESCRIPTION    "."
        ::= { tnOpticalPortConfig 152 }

--------------------------------------------------------------------------------
-- ITLU Optical Port Config Table
--------------------------------------------------------------------------------
    tnItluPortConfigTable OBJECT-TYPE
        SYNTAX         SEQUENCE OF TnItluPortConfigEntry
        MAX-ACCESS     not-accessible
        STATUS         current
        DESCRIPTION    "The ports on an ITLU optical card."
        ::= { tnOpticalPortConfig 153 }

    tnItluPortConfigEntry OBJECT-TYPE
        SYNTAX         TnItluPortConfigEntry
        MAX-ACCESS     not-accessible
        STATUS         current
        DESCRIPTION    "."
        INDEX { ifIndex }
        ::= { tnItluPortConfigTable 1 }

    TnItluPortConfigEntry ::=
        SEQUENCE {
            tnItluPortConfigFunction INTEGER
        }

    tnItluPortConfigFunction OBJECT-TYPE
        SYNTAX         INTEGER {
                         sigIn(1),
                         eOut(2),
                         oOut(3)
                       }
        MAX-ACCESS     read-only
        STATUS         current
        DESCRIPTION    "Indicates the functional type of this ITLU port:

                        port 1 - signal in
                        port 2 - even out
                        port 3 - odd out"
        ::= { tnItluPortConfigEntry 1 }

--------------------------------------------------------------------------------
-- WR8-88A Optical Port Config Scalar
--------------------------------------------------------------------------------
    tnWr8c88aPortConfigAttributeTotal OBJECT-TYPE
        SYNTAX         Integer32
        MAX-ACCESS     read-only
        STATUS         current
        DESCRIPTION    "."
        ::= { tnOpticalPortConfig 154 }

--------------------------------------------------------------------------------
-- WR8-88A Optical Port Config Table
--------------------------------------------------------------------------------
    tnWr8c88aPortConfigTable OBJECT-TYPE
        SYNTAX         SEQUENCE OF TnWr8c88aPortConfigEntry
        MAX-ACCESS     not-accessible
        STATUS         current
        DESCRIPTION    "The ports on a WR8-88A optical card."
        ::= { tnOpticalPortConfig 155 }

    tnWr8c88aPortConfigEntry OBJECT-TYPE
        SYNTAX         TnWr8c88aPortConfigEntry
        MAX-ACCESS     not-accessible
        STATUS         current
        DESCRIPTION    "."
        INDEX { ifIndex }
        ::= { tnWr8c88aPortConfigTable 1 }

    TnWr8c88aPortConfigEntry ::=
        SEQUENCE {
            tnWr8c88aPortConfigFunction  INTEGER
        }

    tnWr8c88aPortConfigFunction OBJECT-TYPE
        SYNTAX         INTEGER {
                         signal(1),
                         thru(2),
                         dropOut(3),
                         addIn(4),
--                       obsolete
--                         test(5),
                         meshOut(5),
                         inv(6)
                       }
        MAX-ACCESS     read-only
        STATUS         current
        DESCRIPTION    "Indicates the functional type of this WR8-88A port."
        ::= { tnWr8c88aPortConfigEntry 1 }

--------------------------------------------------------------------------------
-- 11DPE12E Optical Port Config Scalar
--------------------------------------------------------------------------------
    tn11dpe12ePortConfigAttributeTotal OBJECT-TYPE
        SYNTAX         Integer32
        MAX-ACCESS     read-only
        STATUS         current
        DESCRIPTION    "."
        ::= { tnOpticalPortConfig 156 }

--------------------------------------------------------------------------------
-- 11DPE12E Optical Port Config Table
--------------------------------------------------------------------------------
    tn11dpe12ePortConfigTable OBJECT-TYPE
        SYNTAX         SEQUENCE OF Tn11dpe12ePortConfigEntry
        MAX-ACCESS     not-accessible
        STATUS         current
        DESCRIPTION    "The ports on a 11DPE12E optical card."
        ::= { tnOpticalPortConfig 157 }

    tn11dpe12ePortConfigEntry OBJECT-TYPE
        SYNTAX         Tn11dpe12ePortConfigEntry
        MAX-ACCESS     not-accessible
        STATUS         current
        DESCRIPTION    "."
        INDEX { ifIndex }
        ::= { tn11dpe12ePortConfigTable 1 }

    Tn11dpe12ePortConfigEntry ::=
        SEQUENCE {
            tn11dpe12ePortConfigFunction INTEGER,
            tn11dpe12ePortQinQModeTPID   INTEGER,
            tn11dpe12ePortQinQModePVID   Unsigned32
        }

    tn11dpe12ePortConfigFunction OBJECT-TYPE
        SYNTAX         INTEGER {
                         network(1),
                         client(2),
                         evoa(3),
                         backplane(4)
                       }
        MAX-ACCESS     read-only
        STATUS         current
        DESCRIPTION    "Indicates the functional type of this 11DPGE12 port."
        ::= { tn11dpe12ePortConfigEntry 1 }

    tn11dpe12ePortQinQModeTPID OBJECT-TYPE
        SYNTAX         INTEGER {
                         qinqtpid1(1),
                         qinqtpid2(2),
                         qinqtpid3(3),
                         qinqtpid4(4)
                       }
        MAX-ACCESS     read-create
        STATUS         current
        DESCRIPTION    "The QinQ mode TPID for 11DPE12E port."
        DEFVAL         { qinqtpid1 }
        ::= { tn11dpe12ePortConfigEntry 2 }

    tn11dpe12ePortQinQModePVID OBJECT-TYPE
        SYNTAX         Unsigned32
        MAX-ACCESS     read-create
        STATUS         current
        DESCRIPTION    "The PVID for 11DPE12E port.

                        Current configurable range: 0 to 0x0FFE."
        DEFVAL         { 0 }
        ::= { tn11dpe12ePortConfigEntry 3 }

--------------------------------------------------------------------------------
-- 112SX10L Optical Port Config Scalar
--------------------------------------------------------------------------------
    tn112sx10lPortConfigAttributeTotal OBJECT-TYPE
        SYNTAX         Integer32
        MAX-ACCESS     read-only
        STATUS         current
        DESCRIPTION    "."
        ::= { tnOpticalPortConfig 158 }

--------------------------------------------------------------------------------
-- 112SX10L Optical Port Config Table
--------------------------------------------------------------------------------
    tn112sx10lPortConfigTable OBJECT-TYPE
        SYNTAX         SEQUENCE OF Tn112sx10lPortConfigEntry
        MAX-ACCESS     not-accessible
        STATUS         current
        DESCRIPTION    "The ports on a 112SX10L optical card."
        ::= { tnOpticalPortConfig 159 }

    tn112sx10lPortConfigEntry OBJECT-TYPE
        SYNTAX         Tn112sx10lPortConfigEntry
        MAX-ACCESS     not-accessible
        STATUS         current
        DESCRIPTION    "."
        INDEX { ifIndex }
        ::= { tn112sx10lPortConfigTable 1 }

    Tn112sx10lPortConfigEntry ::=
        SEQUENCE {
            tn112sx10lPortConfigFunction INTEGER
        }

    tn112sx10lPortConfigFunction OBJECT-TYPE
        SYNTAX         INTEGER {
                         network(1),
                         client(2)
                       }
        MAX-ACCESS     read-only
        STATUS         current
        DESCRIPTION    "Indicates the functional type of this 112SX10L port."
        ::= { tn112sx10lPortConfigEntry 1 }

--------------------------------------------------------------------------------
-- 112SA1L Optical Port Config Scalar
--------------------------------------------------------------------------------
    tn112sa1lPortConfigAttributeTotal OBJECT-TYPE
        SYNTAX         Integer32
        MAX-ACCESS     read-only
        STATUS         current
        DESCRIPTION    "."
        ::= { tnOpticalPortConfig 160 }

--------------------------------------------------------------------------------
-- 112SA1L Optical Port Config Table
--------------------------------------------------------------------------------
    tn112sa1lPortConfigTable OBJECT-TYPE
        SYNTAX         SEQUENCE OF Tn112sa1lPortConfigEntry
        MAX-ACCESS     not-accessible
        STATUS         current
        DESCRIPTION    "The ports on a 112SA1L optical card."
        ::= { tnOpticalPortConfig 161 }

    tn112sa1lPortConfigEntry OBJECT-TYPE
        SYNTAX         Tn112sa1lPortConfigEntry
        MAX-ACCESS     not-accessible
        STATUS         current
        DESCRIPTION    "."
        INDEX { ifIndex }
        ::= { tn112sa1lPortConfigTable 1 }

    Tn112sa1lPortConfigEntry ::=
        SEQUENCE {
            tn112sa1lPortConfigFunction INTEGER
        }

    tn112sa1lPortConfigFunction OBJECT-TYPE
        SYNTAX         INTEGER {
                         network(1),
                         client(2)
                       }
        MAX-ACCESS     read-only
        STATUS         current
        DESCRIPTION    "Indicates the functional type of this 112SA1L port."
        ::= { tn112sa1lPortConfigEntry 1 }

--------------------------------------------------------------------------------
-- 11DPM12 Optical Port Config Scalar
--------------------------------------------------------------------------------
    tn11dpm12PortConfigAttributeTotal OBJECT-TYPE
        SYNTAX         Integer32
        MAX-ACCESS     read-only
        STATUS         current
        DESCRIPTION    "."
        ::= { tnOpticalPortConfig 162 }

--------------------------------------------------------------------------------
-- 11DPM12 Optical Port Config Table
--------------------------------------------------------------------------------
    tn11dpm12PortConfigTable OBJECT-TYPE
        SYNTAX         SEQUENCE OF Tn11dpm12PortConfigEntry
        MAX-ACCESS     not-accessible
        STATUS         current
        DESCRIPTION    "The ports on a 11DPM12 optical card."
        ::= { tnOpticalPortConfig 163 }

    tn11dpm12PortConfigEntry OBJECT-TYPE
        SYNTAX         Tn11dpm12PortConfigEntry
        MAX-ACCESS     not-accessible
        STATUS         current
        DESCRIPTION    "."
        INDEX { ifIndex }
        ::= { tn11dpm12PortConfigTable 1 }

    Tn11dpm12PortConfigEntry ::=
        SEQUENCE {
            tn11dpm12PortConfigFunction INTEGER
        }

    tn11dpm12PortConfigFunction OBJECT-TYPE
        SYNTAX         INTEGER {
                         network(1),
                         client(2),
                         evoa(3)
                       }
        MAX-ACCESS     read-only
        STATUS         current
        DESCRIPTION    "Indicates the functional type of this 11DPM12 port."
        ::= { tn11dpm12PortConfigEntry 1 }

--    obsolete
--    tnWr8c88aAttenPortConfigTable OBJECT-TYPE ::= { tnOpticalPortConfig 164 }

--------------------------------------------------------------------------------
-- Raman Optical Port Config Table
--------------------------------------------------------------------------------
    tnRamanPortConfigTable OBJECT-TYPE
        SYNTAX         SEQUENCE OF TnRamanPortConfigEntry
        MAX-ACCESS     not-accessible
        STATUS         current
        DESCRIPTION    "The ports on a Raman optical card."
        ::= { tnOpticalPortConfig 165 }

    tnRamanPortConfigEntry OBJECT-TYPE
        SYNTAX         TnRamanPortConfigEntry
        MAX-ACCESS     not-accessible
        STATUS         current
        DESCRIPTION    "."
        INDEX { ifIndex }
        ::= { tnRamanPortConfigTable 1 }

    TnRamanPortConfigEntry ::=
        SEQUENCE {
            tnRamanPortFiberType                INTEGER,
            tnRamanPortGMinExpected             Integer32,
            tnRamanPortGMaxExpected             Integer32,
            tnRamanPortTiltTarget               Integer32,
            tnRamanPortOperatingMode            INTEGER,
            tnRamanPortAgcTargetGain            Integer32,
            tnRamanPortAprMode                  INTEGER,
            tnRamanPortInitialAgcTargetGain     Integer32,
            tnRamanPortAPRPulseAttempt          INTEGER,
            tnRamanPortConfigConnToPort         Integer32,
            tnRamanPortORLThreshold             Integer32,
            tnRamanPortSpanLossTh               Integer32
        }

    tnRamanPortFiberType OBJECT-TYPE
        SYNTAX         INTEGER {
                         ssmf(1),
                         twrs(2),
                         eleaf(3)
                      }
        MAX-ACCESS     read-create
        STATUS         current
        DESCRIPTION    "Indicates the fiber type."
        DEFVAL         { ssmf }
        ::= { tnRamanPortConfigEntry 1 }

    tnRamanPortGMinExpected OBJECT-TYPE
        SYNTAX         Integer32
        UNITS          "mB"
        MAX-ACCESS     read-create
        STATUS         current
        DESCRIPTION    "The minimum gain expected.

                        Current configurable range: 0 to 2500."
        DEFVAL         { 700 }
        ::= { tnRamanPortConfigEntry 2 }

    tnRamanPortGMaxExpected OBJECT-TYPE
        SYNTAX         Integer32
        UNITS          "mB"
        MAX-ACCESS     read-create
        STATUS         current
        DESCRIPTION    "The maximum gain expected.

                        Current configurable range: 0 to 2500."
        DEFVAL         { 2500 }
        ::= { tnRamanPortConfigEntry 3 }

    tnRamanPortTiltTarget OBJECT-TYPE
        SYNTAX         Integer32
        UNITS          "mB"
        MAX-ACCESS     read-create
        STATUS         current
        DESCRIPTION    "The tilt target.

                        Current configurable range: -300 to 300."
        DEFVAL         { 0 }
        ::= { tnRamanPortConfigEntry 4 }

    tnRamanPortOperatingMode OBJECT-TYPE
        SYNTAX         INTEGER {
                         power(1),
                         gain(2),
                         maxPower(3)
                       }
        MAX-ACCESS     read-create
        STATUS         current
        DESCRIPTION    "This attribute determines the operating mode."
        DEFVAL         { gain }
        ::= { tnRamanPortConfigEntry 5 }

    tnRamanPortAgcTargetGain OBJECT-TYPE
        SYNTAX         Integer32
        UNITS          "mB"
        MAX-ACCESS     read-create
        STATUS         current
        DESCRIPTION    "The AGC mode target gain.

                        Current configurable range: 200 to 2000."
        DEFVAL         { 1000 }
        ::= { tnRamanPortConfigEntry 6 }

    tnRamanPortAprMode OBJECT-TYPE
        SYNTAX         INTEGER {
                         auto(1),
                         force(2)
                      }
        MAX-ACCESS     read-create
        STATUS         current
        DESCRIPTION    "Indicates APR mode."
        DEFVAL         { auto }
        ::= { tnRamanPortConfigEntry 7 }

    tnRamanPortInitialAgcTargetGain OBJECT-TYPE
        SYNTAX         Integer32
        UNITS          "mB"
        MAX-ACCESS     read-create
        STATUS         current
        DESCRIPTION    "Initial AGC mode target gain.

                        Current configurable range: 200 to 2000."
        DEFVAL         { 1000 }
        ::= { tnRamanPortConfigEntry 8 }

    tnRamanPortAPRPulseAttempt OBJECT-TYPE
        SYNTAX         INTEGER {
                         off(1),
                         on(2)
                      }
        MAX-ACCESS     read-create
        STATUS         current
        DESCRIPTION    "APR pulse attempt."
        DEFVAL         { off }
        ::= { tnRamanPortConfigEntry 9 }

    tnRamanPortConfigConnToPort OBJECT-TYPE
        SYNTAX         Integer32 (0..2147483647)
        MAX-ACCESS     read-create
        STATUS         current
        DESCRIPTION    "Associated port."
        DEFVAL         { 0 }
        ::= { tnRamanPortConfigEntry 10 }

    tnRamanPortORLThreshold OBJECT-TYPE
        SYNTAX         Integer32 (0..5000)
        MAX-ACCESS     read-create
        STATUS         current
        DESCRIPTION    "."
        DEFVAL         { 2300 }
        ::= { tnRamanPortConfigEntry 11 }

    tnRamanPortSpanLossTh OBJECT-TYPE
        SYNTAX         Integer32
        UNITS          "mB"
        MAX-ACCESS     read-create
        STATUS         current
        DESCRIPTION    "Span loss threshold ."
        DEFVAL         { -9900 }
        ::= { tnRamanPortConfigEntry 12 }

--------------------------------------------------------------------------------
-- MESH4 Optical Port Config Scalar
--------------------------------------------------------------------------------
    tnMesh4PortConfigAttributeTotal OBJECT-TYPE
        SYNTAX         Integer32
        MAX-ACCESS     read-only
        STATUS         current
        DESCRIPTION    "."
        ::= { tnOpticalPortConfig 166 }

--------------------------------------------------------------------------------
-- MESH4 Optical Port Config Table
--------------------------------------------------------------------------------
    tnMesh4PortConfigTable OBJECT-TYPE
        SYNTAX         SEQUENCE OF TnMesh4PortConfigEntry
        MAX-ACCESS     not-accessible
        STATUS         current
        DESCRIPTION    "The ports on a MESH4 card."
        ::= { tnOpticalPortConfig 167 }

    tnMesh4PortConfigEntry OBJECT-TYPE
        SYNTAX         TnMesh4PortConfigEntry
        MAX-ACCESS     not-accessible
        STATUS         current
        DESCRIPTION    "."
        INDEX { ifIndex }
        ::= { tnMesh4PortConfigTable 1 }

    TnMesh4PortConfigEntry ::=
        SEQUENCE {
            tnMesh4PortConfigFunction  INTEGER
        }

    tnMesh4PortConfigFunction OBJECT-TYPE
        SYNTAX         INTEGER {
                         sigIn(1),
                         sigOut(2)
                       }
        MAX-ACCESS     read-only
        STATUS         current
        DESCRIPTION    "Indicates the functional type of this MESH4 port."
        ::= { tnMesh4PortConfigEntry 1 }

--    obsolete
--    tnTcmPortConfigAttributeTotal    OBJECT-TYPE ::= { tnOpticalPortConfig 168 }
--    tnTcmPortConfigTable OBJECT-TYPE OBJECT-TYPE ::= { tnOpticalPortConfig 169 }

--------------------------------------------------------------------------------
-- 43SCA1 Optical Port Config Scalar
--------------------------------------------------------------------------------
    tn43sca1PortConfigAttributeTotal OBJECT-TYPE
        SYNTAX         Integer32
        MAX-ACCESS     read-only
        STATUS         current
        DESCRIPTION    "."
        ::= { tnOpticalPortConfig 170 }

--------------------------------------------------------------------------------
-- 43SCA1 Optical Port Config Table
--------------------------------------------------------------------------------
    tn43sca1PortConfigTable OBJECT-TYPE
        SYNTAX         SEQUENCE OF Tn43sca1PortConfigEntry
        MAX-ACCESS     not-accessible
        STATUS         current
        DESCRIPTION    "The ports on a 43SCA1 optical card."
        ::= { tnOpticalPortConfig 171 }

    tn43sca1PortConfigEntry OBJECT-TYPE
        SYNTAX         Tn43sca1PortConfigEntry
        MAX-ACCESS     not-accessible
        STATUS         current
        DESCRIPTION    "."
        INDEX { ifIndex }
        ::= { tn43sca1PortConfigTable 1 }

    Tn43sca1PortConfigEntry ::=
        SEQUENCE {
            tn43sca1PortConfigFunction INTEGER
        }

    tn43sca1PortConfigFunction OBJECT-TYPE
        SYNTAX         INTEGER {
                         network(1),
                         client(2)
                       }
        MAX-ACCESS     read-only
        STATUS         current
        DESCRIPTION    "Indicates the functional type of this 43SCA1 port."
        ::= { tn43sca1PortConfigEntry 1 }

--------------------------------------------------------------------------------
-- 43SCX4L Optical Port Config Scalar
--------------------------------------------------------------------------------
    tn43scx4lPortConfigAttributeTotal OBJECT-TYPE
        SYNTAX         Integer32
        MAX-ACCESS     read-only
        STATUS         current
        DESCRIPTION    "."
        ::= { tnOpticalPortConfig 172 }

--------------------------------------------------------------------------------
-- 43SCX4L Optical Port Config Table
--------------------------------------------------------------------------------
    tn43scx4lPortConfigTable OBJECT-TYPE
        SYNTAX         SEQUENCE OF Tn43scx4lPortConfigEntry
        MAX-ACCESS     not-accessible
        STATUS         current
        DESCRIPTION    "The ports on a 43SCX4L optical card."
        ::= { tnOpticalPortConfig 173 }

    tn43scx4lPortConfigEntry OBJECT-TYPE
        SYNTAX         Tn43scx4lPortConfigEntry
        MAX-ACCESS     not-accessible
        STATUS         current
        DESCRIPTION    "."
        INDEX { ifIndex }
        ::= { tn43scx4lPortConfigTable 1 }

    Tn43scx4lPortConfigEntry ::=
        SEQUENCE {
            tn43scx4lPortConfigFunction INTEGER
        }

    tn43scx4lPortConfigFunction OBJECT-TYPE
        SYNTAX         INTEGER {
                         network(1),
                         client(2)
                       }
        MAX-ACCESS     read-only
        STATUS         current
        DESCRIPTION    "Indicates the functional type of this 43SCX4L port."
        ::= { tn43scx4lPortConfigEntry 1 }

--------------------------------------------------------------------------------
-- AM2125B Optical Port Config Scalar
--------------------------------------------------------------------------------
    tnAm2125bPortConfigAttributeTotal OBJECT-TYPE
        SYNTAX         Integer32
        MAX-ACCESS     read-only
        STATUS         current
        DESCRIPTION    "."
        ::= { tnOpticalPortConfig 174 }

--------------------------------------------------------------------------------
-- AM2125B Optical Port Config Table
--------------------------------------------------------------------------------
    tnAm2125bPortConfigTable OBJECT-TYPE
        SYNTAX         SEQUENCE OF TnAm2125bPortConfigEntry
        MAX-ACCESS     not-accessible
        STATUS         current
        DESCRIPTION    "The ports on an AM2125B optical card."
        ::= { tnOpticalPortConfig 175 }

    tnAm2125bPortConfigEntry OBJECT-TYPE
        SYNTAX         TnAm2125bPortConfigEntry
        MAX-ACCESS     not-accessible
        STATUS         current
        DESCRIPTION    "."
        INDEX { ifIndex }
        ::= { tnAm2125bPortConfigTable 1 }

    TnAm2125bPortConfigEntry ::=
        SEQUENCE {
            tnAm2125bPortConfigFunction INTEGER
        }

    tnAm2125bPortConfigFunction OBJECT-TYPE
        SYNTAX         INTEGER {
                         lineIn(1),
                         inv(2),
                         dcm(3),
                         lineOut(4),
                         oscSfp(5),
                         det(6),
                         osc(7),
                         custLan(8)
                       }
        MAX-ACCESS     read-only
        STATUS         current
        DESCRIPTION    "Indicates the functional type of this AM2125B port."
        ::= { tnAm2125bPortConfigEntry 1 }

--------------------------------------------------------------------------------
-- 112SNX10 Optical Port Config Scalar
--------------------------------------------------------------------------------
    tn112snx10PortConfigAttributeTotal OBJECT-TYPE
        SYNTAX         Integer32
        MAX-ACCESS     read-only
        STATUS         current
        DESCRIPTION    "."
        ::= { tnOpticalPortConfig 176 }

--------------------------------------------------------------------------------
-- 112SNX10 Optical Port Config Table
--------------------------------------------------------------------------------
    tn112snx10PortConfigTable OBJECT-TYPE
        SYNTAX         SEQUENCE OF Tn112snx10PortConfigEntry
        MAX-ACCESS     not-accessible
        STATUS         current
        DESCRIPTION    "The ports on a 112SNX10 optical card."
        ::= { tnOpticalPortConfig 177 }

    tn112snx10PortConfigEntry OBJECT-TYPE
        SYNTAX         Tn112snx10PortConfigEntry
        MAX-ACCESS     not-accessible
        STATUS         current
        DESCRIPTION    "."
        INDEX { ifIndex }
        ::= { tn112snx10PortConfigTable 1 }

    Tn112snx10PortConfigEntry ::=
        SEQUENCE {
            tn112snx10PortConfigFunction INTEGER
        }

    tn112snx10PortConfigFunction OBJECT-TYPE
        SYNTAX         INTEGER {
                         network(1),
                         client(2)
                       }
        MAX-ACCESS     read-only
        STATUS         current
        DESCRIPTION    "Indicates the functional type of this 112SNX10 port."
        ::= { tn112snx10PortConfigEntry 1 }

--------------------------------------------------------------------------------
-- 112SNA1 Optical Port Config Scalar
--------------------------------------------------------------------------------
    tn112sna1PortConfigAttributeTotal OBJECT-TYPE
        SYNTAX         Integer32
        MAX-ACCESS     read-only
        STATUS         current
        DESCRIPTION    "."
        ::= { tnOpticalPortConfig 178 }

--------------------------------------------------------------------------------
-- 112SNA1 Optical Port Config Table
--------------------------------------------------------------------------------
    tn112sna1PortConfigTable OBJECT-TYPE
        SYNTAX         SEQUENCE OF Tn112sna1PortConfigEntry
        MAX-ACCESS     not-accessible
        STATUS         current
        DESCRIPTION    "The ports on a 112SNA1 optical card."
        ::= { tnOpticalPortConfig 179 }

    tn112sna1PortConfigEntry OBJECT-TYPE
        SYNTAX         Tn112sna1PortConfigEntry
        MAX-ACCESS     not-accessible
        STATUS         current
        DESCRIPTION    "."
        INDEX { ifIndex }
        ::= { tn112sna1PortConfigTable 1 }

    Tn112sna1PortConfigEntry ::=
        SEQUENCE {
            tn112sna1PortConfigFunction INTEGER
        }

    tn112sna1PortConfigFunction OBJECT-TYPE
        SYNTAX         INTEGER {
                         network(1),
                         client(2)
                       }
        MAX-ACCESS     read-only
        STATUS         current
        DESCRIPTION    "Indicates the functional type of this 112SNA1 port."
        ::= { tn112sna1PortConfigEntry 1 }

--    obsolete
--    tn11qta4PortConfigAttributeTotal OBJECT-TYPE ::= { tnOpticalPortConfig 180 }
--    tn11qta4PortConfigTable          OBJECT-TYPE ::= { tnOpticalPortConfig 181 }

--------------------------------------------------------------------------------
-- 1DPP24M Optical Port Config Scalar
--------------------------------------------------------------------------------
    tn1dpp24mPortConfigAttributeTotal OBJECT-TYPE
        SYNTAX         Integer32
        MAX-ACCESS     read-only
        STATUS         current
        DESCRIPTION    "."
        ::= { tnOpticalPortConfig 182 }

--------------------------------------------------------------------------------
-- 1DPP24M Optical Port Config Table
--------------------------------------------------------------------------------
    tn1dpp24mPortConfigTable OBJECT-TYPE
        SYNTAX         SEQUENCE OF Tn1dpp24mPortConfigEntry
        MAX-ACCESS     not-accessible
        STATUS         current
        DESCRIPTION    "The ports on a 1DPP24M optical card."
        ::= { tnOpticalPortConfig 183 }

    tn1dpp24mPortConfigEntry OBJECT-TYPE
        SYNTAX         Tn1dpp24mPortConfigEntry
        MAX-ACCESS     not-accessible
        STATUS         current
        DESCRIPTION    "."
        INDEX { ifIndex }
        ::= { tn1dpp24mPortConfigTable 1 }

    Tn1dpp24mPortConfigEntry ::=
        SEQUENCE {
            tn1dpp24mPortConfigFunction INTEGER
        }

    tn1dpp24mPortConfigFunction OBJECT-TYPE
        SYNTAX         INTEGER {
                         network(1),
                         client(2)
                       }
        MAX-ACCESS     read-only
        STATUS         current
        DESCRIPTION    "Indicates the functional type of this 1DPP24M port."
        ::= { tn1dpp24mPortConfigEntry 1 }

--------------------------------------------------------------------------------
-- DWDM Common OTU3/ODU3 Client Port Config Table
--------------------------------------------------------------------------------
    tnDwdmCmnOtu3Odu3ClientPortConfigTable OBJECT-TYPE
        SYNTAX         SEQUENCE OF TnDwdmCmnOtu3Odu3ClientPortConfigEntry
        MAX-ACCESS     not-accessible
        STATUS         current
        DESCRIPTION    "Common attributes against DWDM client ports."
        ::= { tnOpticalPortConfig 184 }

    tnDwdmCmnOtu3Odu3ClientPortConfigEntry OBJECT-TYPE
        SYNTAX         TnDwdmCmnOtu3Odu3ClientPortConfigEntry
        MAX-ACCESS     not-accessible
        STATUS         current
        DESCRIPTION    "."
        INDEX { ifIndex }
        ::= { tnDwdmCmnOtu3Odu3ClientPortConfigTable 1 }

    TnDwdmCmnOtu3Odu3ClientPortConfigEntry ::=
        SEQUENCE {
            tnDwdmCmnClientPortOchOtu3FecMode            AluWdmFecMode,
            tnDwdmCmnClientPortOchOtu3Rate               AluWdmPortOchOtuRate,
            tnDwdmCmnClientPortOtu3TransmittedTti        OCTET STRING,
            tnDwdmCmnClientPortOtu3ExpectedTti           OCTET STRING,
            tnDwdmCmnClientPortOtu3TimConsequenceAction  AluWdmDisabledEnabled,
            tnDwdmCmnClientPortOtu3TimDetectionMode      AluWdmTimDetectionMode,
            tnDwdmCmnClientPortOdu3TransmittedTti        OCTET STRING,
            tnDwdmCmnClientPortOdu3ExpectedTti           OCTET STRING,
            tnDwdmCmnClientPortOdu3TimDetectionMode      AluWdmTimDetectionMode
    }

    tnDwdmCmnClientPortOchOtu3FecMode OBJECT-TYPE
        SYNTAX         AluWdmFecMode
        MAX-ACCESS     read-create
        STATUS         current
        DESCRIPTION    "OTU3 FEC mode."
        DEFVAL         { g709Fec }
        ::= { tnDwdmCmnOtu3Odu3ClientPortConfigEntry 1 }

    tnDwdmCmnClientPortOchOtu3Rate OBJECT-TYPE
        SYNTAX         AluWdmPortOchOtuRate
        MAX-ACCESS     read-create
        STATUS         current
        DESCRIPTION    "OTU3 rate."
        DEFVAL         { otm43G018 }
        ::= { tnDwdmCmnOtu3Odu3ClientPortConfigEntry 2 }

    tnDwdmCmnClientPortOtu3TransmittedTti OBJECT-TYPE
        SYNTAX         OCTET STRING
        MAX-ACCESS     read-create
        STATUS         current
        DESCRIPTION    "OTU3 transmitted TTI."
        DEFVAL         { "" }
        ::= { tnDwdmCmnOtu3Odu3ClientPortConfigEntry 3 }

    tnDwdmCmnClientPortOtu3ExpectedTti OBJECT-TYPE
        SYNTAX         OCTET STRING
        MAX-ACCESS     read-create
        STATUS         current
        DESCRIPTION    "OTU3 expected TTI."
        DEFVAL         { "" }
        ::= { tnDwdmCmnOtu3Odu3ClientPortConfigEntry 4 }

    tnDwdmCmnClientPortOtu3TimConsequenceAction OBJECT-TYPE
        SYNTAX         AluWdmDisabledEnabled
        MAX-ACCESS     read-create
        STATUS         current
        DESCRIPTION    "OTU3 TIM consequence action."
        DEFVAL         { disabled }
        ::= { tnDwdmCmnOtu3Odu3ClientPortConfigEntry 5 }

    tnDwdmCmnClientPortOtu3TimDetectionMode OBJECT-TYPE
        SYNTAX         AluWdmTimDetectionMode
        MAX-ACCESS     read-create
        STATUS         current
        DESCRIPTION    "OTU3 TIM detection mode."
        DEFVAL         { off }
        ::= { tnDwdmCmnOtu3Odu3ClientPortConfigEntry 6 }

    tnDwdmCmnClientPortOdu3TransmittedTti OBJECT-TYPE
        SYNTAX         OCTET STRING
        MAX-ACCESS     read-create
        STATUS         current
        DESCRIPTION    "ODU3 transmitted TTI."
        DEFVAL         { "" }
        ::= { tnDwdmCmnOtu3Odu3ClientPortConfigEntry 7 }

    tnDwdmCmnClientPortOdu3ExpectedTti OBJECT-TYPE
        SYNTAX         OCTET STRING
        MAX-ACCESS     read-create
        STATUS         current
        DESCRIPTION    "ODU3 expected TTI."
        DEFVAL         { "" }
        ::= { tnDwdmCmnOtu3Odu3ClientPortConfigEntry 8 }

    tnDwdmCmnClientPortOdu3TimDetectionMode OBJECT-TYPE
        SYNTAX         AluWdmTimDetectionMode
        MAX-ACCESS     read-create
        STATUS         current
        DESCRIPTION    "ODU3 TIM detection mode."
        DEFVAL         { off }
        ::= { tnDwdmCmnOtu3Odu3ClientPortConfigEntry 9 }

--------------------------------------------------------------------------------
-- UL43SCUP Optical Port Config Scalar
--------------------------------------------------------------------------------
    tnul43scupPortConfigAttributeTotal OBJECT-TYPE
        SYNTAX         Integer32
        MAX-ACCESS     read-only
        STATUS         current
        DESCRIPTION    "."
        ::= { tnOpticalPortConfig 185 }

--------------------------------------------------------------------------------
-- UL43SCUP Optical Port Config Table
--------------------------------------------------------------------------------
    tnul43scupPortConfigTable OBJECT-TYPE
        SYNTAX         SEQUENCE OF Tnul43scupPortConfigEntry
        MAX-ACCESS     not-accessible
        STATUS         current
        DESCRIPTION    "The ports on a UL43SCUP optical card."
        ::= { tnOpticalPortConfig 186 }

    tnul43scupPortConfigEntry OBJECT-TYPE
        SYNTAX         Tnul43scupPortConfigEntry
        MAX-ACCESS     not-accessible
        STATUS         current
        DESCRIPTION    "."
        INDEX { ifIndex }
        ::= { tnul43scupPortConfigTable 1 }

    Tnul43scupPortConfigEntry ::=
        SEQUENCE {
            tnul43scupPortConfigFunction  INTEGER
        }

    tnul43scupPortConfigFunction OBJECT-TYPE
        SYNTAX         INTEGER {
                         network(1)
                       }
        MAX-ACCESS     read-only
        STATUS         current
        DESCRIPTION    "Indicates the functional type of this UL43SCUP port."
        ::= { tnul43scupPortConfigEntry 1 }

--------------------------------------------------------------------------------
-- UL11QCUP Optical Port Config Scalar
--------------------------------------------------------------------------------
    tnul11qcupPortConfigAttributeTotal OBJECT-TYPE
        SYNTAX         Integer32
        MAX-ACCESS     read-only
        STATUS         current
        DESCRIPTION    "."
        ::= { tnOpticalPortConfig 187 }

--------------------------------------------------------------------------------
-- UL11QCUP Optical Port Config Table
--------------------------------------------------------------------------------
    tnul11qcupPortConfigTable OBJECT-TYPE
        SYNTAX         SEQUENCE OF Tnul11qcupPortConfigEntry
        MAX-ACCESS     not-accessible
        STATUS         current
        DESCRIPTION    "The ports on a UL11QCUP optical card."
        ::= { tnOpticalPortConfig 188 }

    tnul11qcupPortConfigEntry OBJECT-TYPE
        SYNTAX         Tnul11qcupPortConfigEntry
        MAX-ACCESS     not-accessible
        STATUS         current
        DESCRIPTION    "."
        INDEX { ifIndex }
        ::= { tnul11qcupPortConfigTable 1 }

    Tnul11qcupPortConfigEntry ::=
        SEQUENCE {
            tnul11qcupPortConfigFunction INTEGER
        }

    tnul11qcupPortConfigFunction OBJECT-TYPE
        SYNTAX         INTEGER {
                         network(1)
                       }
        MAX-ACCESS     read-only
        STATUS         current
        DESCRIPTION    "Indicates the functional type of this UL11QCUP port."
        ::= { tnul11qcupPortConfigEntry 1 }

--------------------------------------------------------------------------------
-- 11QPEN4 Optical Port Config Scalar
--------------------------------------------------------------------------------
    tn11qpen4PortConfigAttributeTotal OBJECT-TYPE
        SYNTAX         Integer32
        MAX-ACCESS     read-only
        STATUS         current
        DESCRIPTION    "."
        ::= { tnOpticalPortConfig 189 }

--------------------------------------------------------------------------------
-- 11QPEN4 Optical Port Config Table
--------------------------------------------------------------------------------
    tn11qpen4PortConfigTable OBJECT-TYPE
        SYNTAX         SEQUENCE OF Tn11qpen4PortConfigEntry
        MAX-ACCESS     not-accessible
        STATUS         current
        DESCRIPTION    "The ports on a 11QPEN4 optical card."
        ::= { tnOpticalPortConfig 190 }

    tn11qpen4PortConfigEntry OBJECT-TYPE
        SYNTAX         Tn11qpen4PortConfigEntry
        MAX-ACCESS     not-accessible
        STATUS         current
        DESCRIPTION    "."
        INDEX { ifIndex }
        ::= { tn11qpen4PortConfigTable 1 }

    Tn11qpen4PortConfigEntry ::=
        SEQUENCE {
            tn11qpen4PortConfigFunction                    INTEGER,
            tn11qpen4PortConfigEncryptionOperateKeySwitch  INTEGER,
            tn11qpen4PortConfigEncryptionState             TruthValue,
            tn11qpen4PortConfigEncryptionNextKey           SnmpAdminString,
            tn11qpen4PortConfigEncryptionWKAT              SnmpAdminString
        }

    tn11qpen4PortConfigFunction OBJECT-TYPE
        SYNTAX         INTEGER {
                         network(1),
                         client(2),
                         evoa(3)
                       }
        MAX-ACCESS     read-only
        STATUS         current
        DESCRIPTION    "Indicates the functional type of this 11QPEN4 port."
        ::= { tn11qpen4PortConfigEntry 1 }

    tn11qpen4PortConfigEncryptionOperateKeySwitch OBJECT-TYPE
        SYNTAX         INTEGER {
                         idle(1),
                         swapKeys(2)
                       }
        MAX-ACCESS     read-create
        STATUS         current
        DESCRIPTION    "Request the port to switch to the standby
                        encryption key."
        DEFVAL         { idle }
        ::= { tn11qpen4PortConfigEntry 2 }

    tn11qpen4PortConfigEncryptionState OBJECT-TYPE
        SYNTAX         TruthValue
        MAX-ACCESS     read-create
        STATUS         current
        DESCRIPTION    "Encryption State.
                        true  - on
                        false - off."
        DEFVAL         { false }
        ::= { tn11qpen4PortConfigEntry 3 }

    tn11qpen4PortConfigEncryptionNextKey OBJECT-TYPE
        SYNTAX         SnmpAdminString (SIZE(64))
        MAX-ACCESS     read-create
        STATUS         current
        DESCRIPTION    "The next encryption key to use."
        ::= { tn11qpen4PortConfigEntry 4 }

    tn11qpen4PortConfigEncryptionWKAT OBJECT-TYPE
        SYNTAX         SnmpAdminString (SIZE(0..256))
        MAX-ACCESS     read-create
        STATUS         current
        DESCRIPTION    "The WKAT string used to authenticate the far
                        end and validate the keys are correct."
        DEFVAL         { "" }
        ::= { tn11qpen4PortConfigEntry 5 }

--------------------------------------------------------------------------------
-- 43SCX4E Optical Port Config Scalar
--------------------------------------------------------------------------------
    tn43scx4ePortConfigAttributeTotal OBJECT-TYPE
        SYNTAX         Integer32
        MAX-ACCESS     read-only
        STATUS         current
        DESCRIPTION    "."
        ::= { tnOpticalPortConfig 191 }

--------------------------------------------------------------------------------
-- 43SCX4E Optical Port Config Table
--------------------------------------------------------------------------------
    tn43scx4ePortConfigTable OBJECT-TYPE
        SYNTAX         SEQUENCE OF Tn43scx4ePortConfigEntry
        MAX-ACCESS     not-accessible
        STATUS         current
        DESCRIPTION    "The ports on a 43SCX4E optical card."
        ::= { tnOpticalPortConfig 192 }

    tn43scx4ePortConfigEntry OBJECT-TYPE
        SYNTAX         Tn43scx4ePortConfigEntry
        MAX-ACCESS     not-accessible
        STATUS         current
        DESCRIPTION    "."
        INDEX { ifIndex }
        ::= { tn43scx4ePortConfigTable 1 }

    Tn43scx4ePortConfigEntry ::=
        SEQUENCE {
            tn43scx4ePortConfigFunction INTEGER
        }

    tn43scx4ePortConfigFunction OBJECT-TYPE
        SYNTAX         INTEGER {
                         network(1),
                         client(2)
                       }
        MAX-ACCESS     read-only
        STATUS         current
        DESCRIPTION    "Indicates the functional type of this 43SCX4E port."
        ::= { tn43scx4ePortConfigEntry 1 }

--------------------------------------------------------------------------------
-- 43SCGE1 Optical Port Config Scalar
--------------------------------------------------------------------------------
    tn43scge1PortConfigAttributeTotal OBJECT-TYPE
        SYNTAX         Integer32
        MAX-ACCESS     read-only
        STATUS         current
        DESCRIPTION    "."
        ::= { tnOpticalPortConfig 193 }

--------------------------------------------------------------------------------
-- 43SCGE1 Optical Port Config Table
--------------------------------------------------------------------------------
    tn43scge1PortConfigTable OBJECT-TYPE
        SYNTAX         SEQUENCE OF Tn43scge1PortConfigEntry
        MAX-ACCESS     not-accessible
        STATUS         current
        DESCRIPTION    "The ports on a 43SCGE1 optical card."
        ::= { tnOpticalPortConfig 194 }

    tn43scge1PortConfigEntry OBJECT-TYPE
        SYNTAX         Tn43scge1PortConfigEntry
        MAX-ACCESS     not-accessible
        STATUS         current
        DESCRIPTION    "."
        INDEX { ifIndex }
        ::= { tn43scge1PortConfigTable 1 }

    Tn43scge1PortConfigEntry ::=
        SEQUENCE {
            tn43scge1PortConfigFunction INTEGER
        }

    tn43scge1PortConfigFunction OBJECT-TYPE
        SYNTAX         INTEGER {
                         network(1),
                         client(2)
                       }
        MAX-ACCESS     read-only
        STATUS         current
        DESCRIPTION    "Indicates the functional type of this 43SCGE1 port."
        ::= { tn43scge1PortConfigEntry 1 }

--------------------------------------------------------------------------------
-- 11QPE24 Optical Port Config Scalar
--------------------------------------------------------------------------------
    tn11qpe24PortConfigAttributeTotal OBJECT-TYPE
        SYNTAX         Integer32
        MAX-ACCESS     read-only
        STATUS         current
        DESCRIPTION    "."
        ::= { tnOpticalPortConfig 195 }

--------------------------------------------------------------------------------
-- 11QPE24 Optical Port Config Table
--------------------------------------------------------------------------------
    tn11qpe24PortConfigTable OBJECT-TYPE
        SYNTAX         SEQUENCE OF Tn11qpe24PortConfigEntry
        MAX-ACCESS     not-accessible
        STATUS         current
        DESCRIPTION    "The ports on a 11QPE24 optical card."
        ::= { tnOpticalPortConfig 196 }

    tn11qpe24PortConfigEntry OBJECT-TYPE
        SYNTAX         Tn11qpe24PortConfigEntry
        MAX-ACCESS     not-accessible
        STATUS         current
        DESCRIPTION    "."
        INDEX { ifIndex }
        ::= { tn11qpe24PortConfigTable 1 }

    Tn11qpe24PortConfigEntry ::=
        SEQUENCE {
            tn11qpe24PortConfigFunction INTEGER
        }

    tn11qpe24PortConfigFunction OBJECT-TYPE
        SYNTAX         INTEGER {
                         network(1),
                         client(2),
                         evoa(3)
                       }
        MAX-ACCESS     read-only
        STATUS         current
        DESCRIPTION    "Indicates the functional type of this 11QPE24 port."
        ::= { tn11qpe24PortConfigEntry 1 }

--------------------------------------------------------------------------------
-- 11STAR1A Optical Port Config Scalar
--------------------------------------------------------------------------------
    tn11star1aPortConfigAttributeTotal OBJECT-TYPE
        SYNTAX         Integer32
        MAX-ACCESS     read-only
        STATUS         current
        DESCRIPTION    "."
        ::= { tnOpticalPortConfig 197 }

--------------------------------------------------------------------------------
-- 11STAR1A Optical Port Config Table
--------------------------------------------------------------------------------
    tn11star1aPortConfigTable OBJECT-TYPE
        SYNTAX         SEQUENCE OF Tn11star1aPortConfigEntry
        MAX-ACCESS     not-accessible
        STATUS         current
        DESCRIPTION    "The ports on a 11STAR1A optical card."
        ::= { tnOpticalPortConfig 198 }

    tn11star1aPortConfigEntry OBJECT-TYPE
        SYNTAX         Tn11star1aPortConfigEntry
        MAX-ACCESS     not-accessible
        STATUS         current
        DESCRIPTION    "."
        INDEX { ifIndex }
        ::= { tn11star1aPortConfigTable 1 }

    Tn11star1aPortConfigEntry ::=
        SEQUENCE {
            tn11star1aPortConfigFunction INTEGER
        }

    tn11star1aPortConfigFunction OBJECT-TYPE
        SYNTAX         INTEGER {
                         network(1),
                         client(2)
                       }
        MAX-ACCESS     read-only
        STATUS         current
        DESCRIPTION    "Indicates the functional type of this 11STAR1A port."
        ::= { tn11star1aPortConfigEntry 1 }

--------------------------------------------------------------------------------
-- MVAC8B Optical Port Config Scalar
--------------------------------------------------------------------------------
    tnMvac8bPortConfigAttributeTotal OBJECT-TYPE
        SYNTAX         Integer32
        MAX-ACCESS     read-only
        STATUS         current
        DESCRIPTION    "."
        ::= { tnOpticalPortConfig 199 }

--------------------------------------------------------------------------------
-- MVAC8B Optical Port Config Table
--------------------------------------------------------------------------------
    tnMvac8bPortConfigTable OBJECT-TYPE
        SYNTAX         SEQUENCE OF TnMvac8bPortConfigEntry
        MAX-ACCESS     not-accessible
        STATUS         current
        DESCRIPTION    "The ports on a MVAC8B optical card."
        ::= { tnOpticalPortConfig 200 }

    tnMvac8bPortConfigEntry OBJECT-TYPE
        SYNTAX         TnMvac8bPortConfigEntry
        MAX-ACCESS     not-accessible
        STATUS         current
        DESCRIPTION    "."
        INDEX { ifIndex }
        ::= { tnMvac8bPortConfigTable 1 }

    TnMvac8bPortConfigEntry ::=
        SEQUENCE {
            tnMvac8bPortConfigFunction INTEGER
        }

    tnMvac8bPortConfigFunction OBJECT-TYPE
        SYNTAX         INTEGER {
                         network(1),
                         client(2)
                       }
        MAX-ACCESS     read-only
        STATUS         current
        DESCRIPTION    "Indicates the functional type of this MVAC8B port."
        ::= { tnMvac8bPortConfigEntry 1 }

--------------------------------------------------------------------------------
-- WSS Channel Attenuation Config Scalars
--------------------------------------------------------------------------------
    tnWssAttenPortConfigAttributeTotal OBJECT-TYPE
        SYNTAX         Integer32
        MAX-ACCESS     read-only
        STATUS         current
        DESCRIPTION    "."
        ::= { tnOpticalPortConfig 201 }

--------------------------------------------------------------------------------
-- WSS Channel Attenuation Config Table
--------------------------------------------------------------------------------
    tnWssAttenPortConfigTable OBJECT-TYPE
        SYNTAX         SEQUENCE OF TnWssAttenPortConfigEntry
        MAX-ACCESS     not-accessible
        STATUS         current
        DESCRIPTION    "Through this table, a network operator may set
                        the WSS attenuation."
        ::= { tnOpticalPortConfig 202 }

    tnWssAttenPortConfigEntry OBJECT-TYPE
        SYNTAX         TnWssAttenPortConfigEntry
        MAX-ACCESS     not-accessible
        STATUS         current
        DESCRIPTION    "."
        INDEX { ifIndex,
                tnChannel }
        ::= { tnWssAttenPortConfigTable 1 }

    TnWssAttenPortConfigEntry ::=
        SEQUENCE {
            tnWssAttenPortConfigWssAtten   Unsigned32
        }

    tnWssAttenPortConfigWssAtten OBJECT-TYPE
        SYNTAX         Unsigned32
        UNITS          "mB"
        MAX-ACCESS     read-create
        STATUS         current
        DESCRIPTION    "The attenuation, expressed in units of mB, is
                        associated with the WSS channel attenuation.
                        This attributes pplies to the following ports:

                        CWR8:     THRU and CLS ports
                        CWR8-88:  THRU and CLS ports
                        WR8-88A:  SIG port
                        WR8-88AF: SIG port
                        WR2-88:   SIG port
                        WR20-TF:  SIG, ADT, and AD ports
                        WR20-TFM: SIG, ADT, and AD ports

                        Current configurable range: 0 to 1500."
        DEFVAL         { 1500 }
        ::= { tnWssAttenPortConfigEntry 1 }

--------------------------------------------------------------------------------
-- WR8-88AF Optical Port Config Scalar
--------------------------------------------------------------------------------
    tnWr8c88afPortConfigAttributeTotal OBJECT-TYPE
        SYNTAX         Integer32
        MAX-ACCESS     read-only
        STATUS         current
        DESCRIPTION    "."
        ::= { tnOpticalPortConfig 203 }

--------------------------------------------------------------------------------
-- WR8-88AF Optical Port Config Table
--------------------------------------------------------------------------------
    tnWr8c88afPortConfigTable OBJECT-TYPE
        SYNTAX         SEQUENCE OF TnWr8c88afPortConfigEntry
        MAX-ACCESS     not-accessible
        STATUS         current
        DESCRIPTION    "The ports on a WR8-88AF optical card."
        ::= { tnOpticalPortConfig 204 }

    tnWr8c88afPortConfigEntry OBJECT-TYPE
        SYNTAX         TnWr8c88afPortConfigEntry
        MAX-ACCESS     not-accessible
        STATUS         current
        DESCRIPTION    "."
        INDEX { ifIndex }
        ::= { tnWr8c88afPortConfigTable 1 }

    TnWr8c88afPortConfigEntry ::=
        SEQUENCE {
            tnWr8c88afPortConfigFunction  INTEGER
        }

    tnWr8c88afPortConfigFunction OBJECT-TYPE
        SYNTAX         INTEGER {
                         signal(1),
                         thru(2),
                         dropOut(3),
                         addIn(4),
                         meshOut(5),
                         inv(6)
                       }
        MAX-ACCESS     read-only
        STATUS         current
        DESCRIPTION    "Indicates the functional type of this WR8-88AF port."
        ::= { tnWr8c88afPortConfigEntry 1 }

--------------------------------------------------------------------------------
-- 10AN10G Optical Port Config Scalar
--------------------------------------------------------------------------------
    tncl10an10gPortConfigAttributeTotal OBJECT-TYPE
        SYNTAX         Integer32
        MAX-ACCESS     read-only
        STATUS         current
        DESCRIPTION    "."
        ::= { tnOpticalPortConfig 205 }

--------------------------------------------------------------------------------
-- 10AN10G Optical Port Config Table
--------------------------------------------------------------------------------
    tncl10an10gPortConfigTable OBJECT-TYPE
        SYNTAX         SEQUENCE OF Tncl10an10gPortConfigEntry
        MAX-ACCESS     not-accessible
        STATUS         current
        DESCRIPTION    "The ports on a 10AN10G optical card."
        ::= { tnOpticalPortConfig 206 }

    tncl10an10gPortConfigEntry OBJECT-TYPE
        SYNTAX         Tncl10an10gPortConfigEntry
        MAX-ACCESS     not-accessible
        STATUS         current
        DESCRIPTION    "."
        INDEX { ifIndex }
        ::= { tncl10an10gPortConfigTable 1 }

    Tncl10an10gPortConfigEntry ::=
        SEQUENCE {
            tncl10an10gPortConfigFunction INTEGER
        }

    tncl10an10gPortConfigFunction OBJECT-TYPE
        SYNTAX         INTEGER {
                         network(1),
                         client(2)
                       }
        MAX-ACCESS     read-only
        STATUS         current
        DESCRIPTION    "Indicates the functional type of this 10AN10G port."
        ::= { tncl10an10gPortConfigEntry 1 }

--------------------------------------------------------------------------------
-- 24ANM Optical Port Config Scalar
--------------------------------------------------------------------------------
    tncl24anmPortConfigAttributeTotal OBJECT-TYPE
        SYNTAX         Integer32
        MAX-ACCESS     read-only
        STATUS         current
        DESCRIPTION    "."
        ::= { tnOpticalPortConfig 207 }

--------------------------------------------------------------------------------
-- 24ANM Optical Port Config Table
--------------------------------------------------------------------------------
    tncl24anmPortConfigTable OBJECT-TYPE
        SYNTAX         SEQUENCE OF Tncl24anmPortConfigEntry
        MAX-ACCESS     not-accessible
        STATUS         current
        DESCRIPTION    "The ports on a 24ANM optical card."
        ::= { tnOpticalPortConfig 208 }

    tncl24anmPortConfigEntry OBJECT-TYPE
        SYNTAX         Tncl24anmPortConfigEntry
        MAX-ACCESS     not-accessible
        STATUS         current
        DESCRIPTION    "."
        INDEX { ifIndex }
        ::= { tncl24anmPortConfigTable 1 }

    Tncl24anmPortConfigEntry ::=
        SEQUENCE {
            tncl24anmPortConfigFunction INTEGER
        }

    tncl24anmPortConfigFunction OBJECT-TYPE
        SYNTAX         INTEGER {
                         network(1),
                         client(2)
                       }
        MAX-ACCESS     read-only
        STATUS         current
        DESCRIPTION    "Indicates the functional type of this 24ANM port."
        ::= { tncl24anmPortConfigEntry 1 }

--------------------------------------------------------------------------------
-- OPSB Optical Port Config Scalar
--------------------------------------------------------------------------------
    tnOpsbPortConfigAttributeTotal OBJECT-TYPE
        SYNTAX         Integer32
        MAX-ACCESS     read-only
        STATUS         current
        DESCRIPTION    "."
        ::= { tnOpticalPortConfig 209 }

--------------------------------------------------------------------------------
-- OPSB Optical Port Config Table
--------------------------------------------------------------------------------
    tnOpsbPortConfigTable OBJECT-TYPE
        SYNTAX         SEQUENCE OF TnOpsbPortConfigEntry
        MAX-ACCESS     not-accessible
        STATUS         current
        DESCRIPTION    "The ports on an OPSB optical card."
        ::= { tnOpticalPortConfig 210 }

    tnOpsbPortConfigEntry OBJECT-TYPE
        SYNTAX         TnOpsbPortConfigEntry
        MAX-ACCESS     not-accessible
        STATUS         current
        DESCRIPTION    "."
        INDEX { ifIndex }
        ::= { tnOpsbPortConfigTable 1 }

    TnOpsbPortConfigEntry ::=
        SEQUENCE {
            tnOpsbPortConfigFunction     INTEGER
        }

    tnOpsbPortConfigFunction OBJECT-TYPE
        SYNTAX         INTEGER {
                         signal(1),
                         workingProtected(2)
                       }
        MAX-ACCESS     read-only
        STATUS         current
        DESCRIPTION    "Indicates the functional type of this OPSB port."
        ::= { tnOpsbPortConfigEntry 1 }

--------------------------------------------------------------------------------
-- OPS Optical Port Config Scalar
--------------------------------------------------------------------------------
    tnOpsPortConfigAttributeTotal OBJECT-TYPE
        SYNTAX         Integer32
        MAX-ACCESS     read-only
        STATUS         current
        DESCRIPTION    "."
        ::= { tnOpticalPortConfig 211 }

--------------------------------------------------------------------------------
-- OPS Optical Port Config Table
--------------------------------------------------------------------------------
    tnOpsPortConfigTable OBJECT-TYPE
        SYNTAX         SEQUENCE OF TnOpsPortConfigEntry
        MAX-ACCESS     not-accessible
        STATUS         current
        DESCRIPTION    "The attributes for an OPS optical card."
        ::= { tnOpticalPortConfig 212 }

    tnOpsPortConfigEntry OBJECT-TYPE
        SYNTAX         TnOpsPortConfigEntry
        MAX-ACCESS     not-accessible
        STATUS         current
        DESCRIPTION    "."
        INDEX { ifIndex }
        ::= { tnOpsPortConfigTable 1 }

    TnOpsPortConfigEntry ::=
        SEQUENCE {
            tnOpsPortConfigSwitchingThreshold              Integer32,
            tnOpsPortConfigSwitchingThresholdTolerance     Unsigned32,
            tnOpsPortConfigTransmitAttenuation             Integer32,
            tnOpsPortConfigSwitchingThreshCalcControl      INTEGER,
            tnOpsPortTargetReceivedPower                   Integer32,
            tnOpsPortPaired                                TruthValue,
            tnOpsPortConfigChannelFreq                     Integer32,
            tnOpsPortConfigSwitchingThresholdPsd           Integer32,
            tnOpsPortConfigExpectedInputPower              Integer32
        }

    tnOpsPortConfigSwitchingThreshold OBJECT-TYPE
        SYNTAX         Integer32
        UNITS          "mBm"
        MAX-ACCESS     read-create
        STATUS         current
        DESCRIPTION    "If the power drops below this threshold, a
                        protection switch will be executed.  This is
                        accessible from ports 2 and 3 (working or
                        protected) exclusively.  This command applies
                        to ports A and B only.  Default is -3000 for
                        OCH protection, -2800 for OMS protection, and
                        -3000 for OLP protection.

                        Current configurable ranges and defaults:

                        OLP (OPSA)     :   (-3150..500), -2800
                        OCH/OMSP (OPSB):   (-3000..500), -1000
                        OMSP (OPSA)    :   (-3000..1700),-1000."
        ::= { tnOpsPortConfigEntry 1 }

    tnOpsPortConfigSwitchingThresholdTolerance OBJECT-TYPE
        SYNTAX         Unsigned32
        UNITS          "mB"
        MAX-ACCESS     read-create
        STATUS         current
        DESCRIPTION    "The tolerance applied to the port switching
                        threshold.  This is accessible from ports 2 and
                        3 (working or protected) exclusively.

                        Current configurable range: 0 to 500."
        DEFVAL         { 200 }
        ::= { tnOpsPortConfigEntry 2 }

    tnOpsPortConfigTransmitAttenuation OBJECT-TYPE
        SYNTAX         Integer32
        UNITS          "mB"
        MAX-ACCESS     read-create
        STATUS         current
        DESCRIPTION    "The attenuation of the attenuator - applies to
                        ports 2 and 3 (A and B) of the OPS optical card.

                        Current configurable range: -1 to 2000.
                        -1 means that max attenuation is applied."
        DEFVAL         { -1 }
        ::= { tnOpsPortConfigEntry 3 }

    tnOpsPortConfigSwitchingThreshCalcControl OBJECT-TYPE
        SYNTAX         INTEGER {
                         auto(1),
                         manual(2)
                       }
        MAX-ACCESS     read-create
        STATUS         current
        DESCRIPTION    "Indicates if the OPS switch threshold is
                        calculated by the NE (auto) or set by the user
                        (manual) - applies to ports 2 and 3 (A and B)
                        of the OPS card.  Default is auto for OPSA and
                        manual for OPSB."
        ::= { tnOpsPortConfigEntry 4 }

    tnOpsPortTargetReceivedPower OBJECT-TYPE
        SYNTAX         Integer32
        UNITS          "mBm"
        MAX-ACCESS     read-create
        STATUS         current
        DESCRIPTION    "Same value at A and B in ports; per channel.
                        The SW implementation is using the Sig port
                        to access this attribute.

                        Current configurable range: -3150 to 1700."
        DEFVAL         { -2600 }
        ::= { tnOpsPortConfigEntry 5 }

    tnOpsPortPaired OBJECT-TYPE
        SYNTAX         TruthValue
        MAX-ACCESS     read-create
        STATUS         current
        DESCRIPTION    "Required for SLA function. The flag is checked
                        when ingress adjust is triggered. set flag
                        against the sig port."
        DEFVAL         { false }
        ::= { tnOpsPortConfigEntry 6 }

    tnOpsPortConfigChannelFreq OBJECT-TYPE
        SYNTAX         Integer32
        MAX-ACCESS     read-create
        STATUS         current
        DESCRIPTION    "."
        ::= { tnOpsPortConfigEntry 7 }

    tnOpsPortConfigSwitchingThresholdPsd OBJECT-TYPE
        SYNTAX         Integer32
        MAX-ACCESS     read-create
        STATUS         current
        DESCRIPTION    "."
        ::= { tnOpsPortConfigEntry 8 }

    tnOpsPortConfigExpectedInputPower OBJECT-TYPE
        SYNTAX         Integer32
        MAX-ACCESS     read-create
        STATUS         current
        DESCRIPTION    "."
        ::= { tnOpsPortConfigEntry 9}

--------------------------------------------------------------------------------
-- 11DPE12A Optical Port Config Scalar
--------------------------------------------------------------------------------
    tn11dpe12aPortConfigAttributeTotal OBJECT-TYPE
        SYNTAX         Integer32
        MAX-ACCESS     read-only
        STATUS         current
        DESCRIPTION    "."
        ::= { tnOpticalPortConfig 213 }

--------------------------------------------------------------------------------
-- 11DPE12A Optical Port Config Table
--------------------------------------------------------------------------------
    tn11dpe12aPortConfigTable OBJECT-TYPE
        SYNTAX         SEQUENCE OF Tn11dpe12aPortConfigEntry
        MAX-ACCESS     not-accessible
        STATUS         current
        DESCRIPTION    "The ports on a 11DPE12A optical card."
        ::= { tnOpticalPortConfig 214 }

    tn11dpe12aPortConfigEntry OBJECT-TYPE
        SYNTAX         Tn11dpe12aPortConfigEntry
        MAX-ACCESS     not-accessible
        STATUS         current
        DESCRIPTION    "."
        INDEX { ifIndex }
        ::= { tn11dpe12aPortConfigTable 1 }

    Tn11dpe12aPortConfigEntry ::=
        SEQUENCE {
            tn11dpe12aPortConfigFunction              INTEGER,
            tn11dpe12aPortConfigQinQModeTPID          INTEGER,
            tn11dpe12aPortConfigQinQModePVID          Unsigned32,
            tn11dpe12aPortConfigLPTConsequenceAction  INTEGER,
            tn11dpe12aPortConfigMtu                   Integer32,
            tn11dpe12aPortConfigPortRole              INTEGER,
            tn11dpe12aPortConfigPtpTrans              INTEGER,
            tn11dpe12aPortConfigCompatibilityMode     INTEGER,
            tn11dpe12aPortConfigFlowControl           AluWdmEnabledDisabled
        }

    tn11dpe12aPortConfigFunction OBJECT-TYPE
        SYNTAX         INTEGER {
                         network(1),
                         client(2),
                         evoa(3),
                         backplane(4),
                         tod(5),
                         bits(6)
                       }
        MAX-ACCESS     read-only
        STATUS         current
        DESCRIPTION    "Indicates the functional type of this 11DPE12A port."
        ::= { tn11dpe12aPortConfigEntry 1 }

    tn11dpe12aPortConfigQinQModeTPID OBJECT-TYPE
        SYNTAX         INTEGER {
                         qinqtpid1(1),
                         qinqtpid2(2),
                         qinqtpid3(3),
                         qinqtpid4(4)
                       }
        MAX-ACCESS     read-create
        STATUS         current
        DESCRIPTION    "The QinQ mode TPID for 11dpe12a port."
        DEFVAL         { qinqtpid1 }
        ::= { tn11dpe12aPortConfigEntry 2 }

    tn11dpe12aPortConfigQinQModePVID OBJECT-TYPE
        SYNTAX         Unsigned32
        MAX-ACCESS     read-create
        STATUS         current
        DESCRIPTION    "The PVID for 11dpe12a port.

                        Current configurable range: 0 to 0x0FFE."
        DEFVAL         { 0 }
        ::= { tn11dpe12aPortConfigEntry 3 }

    tn11dpe12aPortConfigLPTConsequenceAction OBJECT-TYPE
        SYNTAX         INTEGER {
                         noAction(1),
                         oneShutDown(2),
                         allShutDown(3)
                       }
        MAX-ACCESS     read-create
        STATUS         current
        DESCRIPTION    "Indicates the 11dpe12a port LPT ConsequenceAction."
        DEFVAL         { noAction }
        ::= { tn11dpe12aPortConfigEntry 4 }

    tn11dpe12aPortConfigMtu OBJECT-TYPE
        SYNTAX         Integer32
        MAX-ACCESS     read-create
        STATUS         current
        DESCRIPTION    "The MTU size for 11dpe12a client interface.

                        Current configurable range: 1518 to 9600."
        DEFVAL         { 9600 }
        ::= { tn11dpe12aPortConfigEntry 5 }

    tn11dpe12aPortConfigPortRole OBJECT-TYPE
        SYNTAX         INTEGER {
                         uni(1),
                         nni(2)
                       }
        MAX-ACCESS     read-create
        STATUS         current
        DESCRIPTION    "The role for an 11dpe12a port:
                        uni - the port acts like a client port.
                        nni - the port acts like a line port."
        DEFVAL         { nni }
        ::= { tn11dpe12aPortConfigEntry 6 }

    tn11dpe12aPortConfigPtpTrans OBJECT-TYPE
        SYNTAX         INTEGER {
                         inPayload(1),
                         inOverhead(2)
                       }
        MAX-ACCESS     read-create
        STATUS         current
        DESCRIPTION    "Specifies how to transport the ptp packets.  This
                        attribute is valid for the OTU2 line ports only."
        DEFVAL         { inPayload }
        ::= { tn11dpe12aPortConfigEntry 7 }

    tn11dpe12aPortConfigCompatibilityMode OBJECT-TYPE
        SYNTAX         INTEGER {
                         default(1),
                         intMode11dpe12(2)
                       }
        MAX-ACCESS     read-create
        STATUS         current
        DESCRIPTION    "This parameter is used to set the compatible
                        mode of the OTU2 port.

                          default:        The port operates in the default
                                          mode which is supported by all
                                          12xGE cards except the 11DPE12.
                          intMode11dpe12: The port operates in the 11DPE12
                                          interworking mode."
        DEFVAL         { default }
        ::= { tn11dpe12aPortConfigEntry 8 }

    tn11dpe12aPortConfigFlowControl OBJECT-TYPE
        SYNTAX         AluWdmEnabledDisabled
        MAX-ACCESS     read-create
        STATUS         current
        DESCRIPTION    "The attribute is used to enable/disable flow
                        control (PAUSE frame processing) on the port."
        DEFVAL         { enabled }
        ::= { tn11dpe12aPortConfigEntry 9 }

--------------------------------------------------------------------------------
-- UL130SCUP Optical Port Config Scalar
--------------------------------------------------------------------------------
    tnul130scupPortConfigAttributeTotal OBJECT-TYPE
        SYNTAX         Integer32
        MAX-ACCESS     read-only
        STATUS         current
        DESCRIPTION    "."
        ::= { tnOpticalPortConfig 215 }

--------------------------------------------------------------------------------
-- UL130SCUP Optical Port Config Table
--------------------------------------------------------------------------------
    tnul130scupPortConfigTable OBJECT-TYPE
        SYNTAX         SEQUENCE OF Tnul130scupPortConfigEntry
        MAX-ACCESS     not-accessible
        STATUS         current
        DESCRIPTION    "The ports on a UL130SCUP optical card."
        ::= { tnOpticalPortConfig 216 }

    tnul130scupPortConfigEntry OBJECT-TYPE
        SYNTAX         Tnul130scupPortConfigEntry
        MAX-ACCESS     not-accessible
        STATUS         current
        DESCRIPTION    "."
        INDEX { ifIndex }
        ::= { tnul130scupPortConfigTable 1 }

    Tnul130scupPortConfigEntry ::=
        SEQUENCE {
            tnul130scupPortConfigFunction  INTEGER
        }

    tnul130scupPortConfigFunction OBJECT-TYPE
        SYNTAX         INTEGER {
                         network(1)
                       }
        MAX-ACCESS     read-only
        STATUS         current
        DESCRIPTION    "Indicates the functional type of this UL130SCUP port."
        ::= { tnul130scupPortConfigEntry 1 }

--------------------------------------------------------------------------------
-- 130SCX10 Optical Port Config Scalar
--------------------------------------------------------------------------------
    tn130scx10PortConfigAttributeTotal OBJECT-TYPE
        SYNTAX         Integer32
        MAX-ACCESS     read-only
        STATUS         current
        DESCRIPTION    "."
        ::= { tnOpticalPortConfig 217 }

--------------------------------------------------------------------------------
-- 130SCX10 Optical Port Config Table
--------------------------------------------------------------------------------
    tn130scx10PortConfigTable OBJECT-TYPE
        SYNTAX         SEQUENCE OF Tn130scx10PortConfigEntry
        MAX-ACCESS     not-accessible
        STATUS         current
        DESCRIPTION    "The ports on a 130SCX10 optical card."
        ::= { tnOpticalPortConfig 218 }

    tn130scx10PortConfigEntry OBJECT-TYPE
        SYNTAX         Tn130scx10PortConfigEntry
        MAX-ACCESS     not-accessible
        STATUS         current
        DESCRIPTION    "."
        INDEX { ifIndex }
        ::= { tn130scx10PortConfigTable 1 }

    Tn130scx10PortConfigEntry ::=
        SEQUENCE {
            tn130scx10PortConfigFunction  INTEGER
        }

    tn130scx10PortConfigFunction OBJECT-TYPE
        SYNTAX         INTEGER {
                         network(1),
                         client(2)
                       }
        MAX-ACCESS     read-only
        STATUS         current
        DESCRIPTION    "Indicates the functional type of this 130SCX10 port."
        ::= { tn130scx10PortConfigEntry 1 }

--------------------------------------------------------------------------------
-- A2P2125 Optical Port Config Scalar
--------------------------------------------------------------------------------
    tnA2p2125PortConfigAttributeTotal OBJECT-TYPE
        SYNTAX         Integer32
        MAX-ACCESS     read-only
        STATUS         current
        DESCRIPTION    "."
        ::= { tnOpticalPortConfig 219 }

--------------------------------------------------------------------------------
-- A2P2125 Optical Port Config Table
--------------------------------------------------------------------------------
    tnA2p2125PortConfigTable OBJECT-TYPE
        SYNTAX         SEQUENCE OF TnA2p2125PortConfigEntry
        MAX-ACCESS     not-accessible
        STATUS         current
        DESCRIPTION    "The ports on a A2P2125 optical card."
        ::= { tnOpticalPortConfig 220 }

    tnA2p2125PortConfigEntry OBJECT-TYPE
        SYNTAX         TnA2p2125PortConfigEntry
        MAX-ACCESS     not-accessible
        STATUS         current
        DESCRIPTION    "."
        INDEX { ifIndex }
        ::= { tnA2p2125PortConfigTable 1 }

    TnA2p2125PortConfigEntry ::=
        SEQUENCE {
            tnA2p2125PortConfigFunction  INTEGER
        }

    tnA2p2125PortConfigFunction OBJECT-TYPE
        SYNTAX         INTEGER {
                         lineIn(1),
                         inv(2),
                         dcm(3),
                         lineOut(4),
                         oscSfp(5),
                         osc(6),
                         custLan(7)
                       }
        MAX-ACCESS     read-only
        STATUS         current
        DESCRIPTION    "Indicates the functional type of this A2P2125 port."
        ::= { tnA2p2125PortConfigEntry 1 }

--------------------------------------------------------------------------------
-- 4QPA8 Optical Port Config Scalar
--------------------------------------------------------------------------------
    tn4qpa8PortConfigAttributeTotal OBJECT-TYPE
        SYNTAX         Integer32
        MAX-ACCESS     read-only
        STATUS         current
        DESCRIPTION    "."
        ::= { tnOpticalPortConfig 221 }

--------------------------------------------------------------------------------
-- 4QPA8 Optical Port Config Table
--------------------------------------------------------------------------------
    tn4qpa8PortConfigTable OBJECT-TYPE
        SYNTAX         SEQUENCE OF Tn4qpa8PortConfigEntry
        MAX-ACCESS     not-accessible
        STATUS         current
        DESCRIPTION    "The ports on a 4QPA8 optical card."
        ::= { tnOpticalPortConfig 222 }

    tn4qpa8PortConfigEntry OBJECT-TYPE
        SYNTAX         Tn4qpa8PortConfigEntry
        MAX-ACCESS     not-accessible
        STATUS         current
        DESCRIPTION    "."
        INDEX { ifIndex }
        ::= { tn4qpa8PortConfigTable 1 }

    Tn4qpa8PortConfigEntry ::=
        SEQUENCE {
            tn4qpa8PortConfigFunction    INTEGER,
            tn4qpa8PortConfigTtpPresent  TruthValue
        }

    tn4qpa8PortConfigFunction OBJECT-TYPE
        SYNTAX         INTEGER {
                         network(1),
                         client(2),
                         evoa(3)
                       }
        MAX-ACCESS     read-only
        STATUS         current
        DESCRIPTION    "Indicates the functional type of this 4QPA8 port."
        ::= { tn4qpa8PortConfigEntry 1 }

    tn4qpa8PortConfigTtpPresent OBJECT-TYPE
        SYNTAX         TruthValue
        MAX-ACCESS     read-create
        STATUS         current
        DESCRIPTION    "Ttp present:
                        true  - TP facility is present
                        false - NIM facility is present."
        DEFVAL         { false }
        ::= { tn4qpa8PortConfigEntry 2 }

--------------------------------------------------------------------------------
-- 112PDM11 Optical Port Config Scalar
--------------------------------------------------------------------------------
    tnOt112pdm11PortConfigAttributeTotal OBJECT-TYPE
        SYNTAX         Integer32
        MAX-ACCESS     read-only
        STATUS         current
        DESCRIPTION    "."
        ::= { tnOpticalPortConfig 223 }

--------------------------------------------------------------------------------
-- 112PDM11 Optical Port Config Table
--------------------------------------------------------------------------------
    tnOt112pdm11PortConfigTable OBJECT-TYPE
        SYNTAX         SEQUENCE OF TnOt112pdm11PortConfigEntry
        MAX-ACCESS     not-accessible
        STATUS         current
        DESCRIPTION    "The ports on a 112PDM11 optical card."
        ::= { tnOpticalPortConfig 224 }

    tnOt112pdm11PortConfigEntry OBJECT-TYPE
        SYNTAX         TnOt112pdm11PortConfigEntry
        MAX-ACCESS     not-accessible
        STATUS         current
        DESCRIPTION    "."
        INDEX { ifIndex }
        ::= { tnOt112pdm11PortConfigTable 1 }

    TnOt112pdm11PortConfigEntry ::=
        SEQUENCE {
            tnOt112pdm11PortConfigFunction  INTEGER
        }

    tnOt112pdm11PortConfigFunction OBJECT-TYPE
        SYNTAX         INTEGER {
                         network(1),
                         client(2)
                       }
        MAX-ACCESS     read-only
        STATUS         current
        DESCRIPTION    "Indicates the functional type of this 112PDM11 port."
        ::= { tnOt112pdm11PortConfigEntry 1 }

--------------------------------------------------------------------------------
-- WTOCMA Optical Port Config Scalar
--------------------------------------------------------------------------------
    tnWtocmaPortConfigAttributeTotal OBJECT-TYPE
        SYNTAX         Integer32
        MAX-ACCESS     read-only
        STATUS         current
        DESCRIPTION    "."
        ::= { tnOpticalPortConfig 225 }

--------------------------------------------------------------------------------
-- WTOCMA Optical Port Config Table
--------------------------------------------------------------------------------
    tnWtocmaPortConfigTable OBJECT-TYPE
        SYNTAX         SEQUENCE OF TnWtocmaPortConfigEntry
        MAX-ACCESS     not-accessible
        STATUS         current
        DESCRIPTION    "The ports on a WTOCMA optical card."
        ::= { tnOpticalPortConfig 226 }

    tnWtocmaPortConfigEntry OBJECT-TYPE
        SYNTAX         TnWtocmaPortConfigEntry
        MAX-ACCESS     not-accessible
        STATUS         current
        DESCRIPTION    "."
        INDEX { ifIndex }
        ::= { tnWtocmaPortConfigTable 1 }

    TnWtocmaPortConfigEntry ::=
        SEQUENCE {
            tnWtocmaPortConfigFunction     INTEGER,
            tnWtocmaPortConfigOsnrMeasure  TruthValue,
            tnWtocmaPortConfigOsnrClear    TnCommand
        }

    tnWtocmaPortConfigFunction OBJECT-TYPE
        SYNTAX         INTEGER {
                         detect(1)
                       }
        MAX-ACCESS     read-only
        STATUS         current
        DESCRIPTION    "Indicates the functional type of this WTOCMA port."
        ::= { tnWtocmaPortConfigEntry 1 }

    tnWtocmaPortConfigOsnrMeasure OBJECT-TYPE
        SYNTAX         TruthValue
        MAX-ACCESS     read-create
        STATUS         current
        DESCRIPTION    "Turn OFF/ON OSNR scan."
        DEFVAL         { false }
        ::= { tnWtocmaPortConfigEntry 2 }

    tnWtocmaPortConfigOsnrClear OBJECT-TYPE
        SYNTAX         TnCommand
        MAX-ACCESS     read-create
        STATUS         current
        DESCRIPTION    "This attribute is used to clear OSNR value for
                        all the channels on the specified port."
        DEFVAL         { noCmd }
        ::= { tnWtocmaPortConfigEntry 3 }

--------------------------------------------------------------------------------
-- PTPCTL Optical Port Config Scalar
--------------------------------------------------------------------------------
    tnPtpctlPortConfigAttributeTotal OBJECT-TYPE
        SYNTAX         Integer32
        MAX-ACCESS     read-only
        STATUS         current
        DESCRIPTION    "."
        ::= { tnOpticalPortConfig 227 }

--------------------------------------------------------------------------------
-- PTPCTL Optical Port Config Table
--------------------------------------------------------------------------------
    tnPtpctlPortConfigTable OBJECT-TYPE
        SYNTAX         SEQUENCE OF TnPtpctlPortConfigEntry
        MAX-ACCESS     not-accessible
        STATUS         current
        DESCRIPTION    "The ports on a PTPCTL optical card."
        ::= { tnOpticalPortConfig 228 }

    tnPtpctlPortConfigEntry OBJECT-TYPE
        SYNTAX         TnPtpctlPortConfigEntry
        MAX-ACCESS     not-accessible
        STATUS         current
        DESCRIPTION    "."
        INDEX { ifIndex }
        ::= { tnPtpctlPortConfigTable 1 }

    TnPtpctlPortConfigEntry ::=
        SEQUENCE {
            tnPtpctlPortConfigFunction           INTEGER,
            tnPtpctlPortConfigFiberConnectPort   InterfaceIndexOrZero
        }

    tnPtpctlPortConfigFunction OBJECT-TYPE
        SYNTAX         INTEGER {
                         tp(1),
                         bits(2),
                         tod(3)
                       }
        MAX-ACCESS     read-only
        STATUS         current
        DESCRIPTION    "Indicates the functional type of this PTPCTL port."
        ::= { tnPtpctlPortConfigEntry 1 }

    tnPtpctlPortConfigFiberConnectPort OBJECT-TYPE
        SYNTAX         InterfaceIndexOrZero
        MAX-ACCESS     read-create
        STATUS         current
        DESCRIPTION    "Fiber Connection Port Index(Shelf/Slot/Port) and
                        Direction. 32-bit value defined as below:

                        +--------+--------+--------+--------+----+----+
                        | 32  25 | 24  17 | 16   9 | 8    3 |  2 |  1 |
                        +--------+--------+--------+--------+----+----+
                        | SHELF  | SLOT   | PORT   | NOTUSE | RX | TX |
                        +--------+--------+--------+--------+----+----+

                        32-bit value: 0 for delete.

                        Bit 1 (TX) and bit 2 (RX) are used for direction:
                          Set both bit 1 (TX) and bit 2 (RX) to 1 for bidirection.

                        Bit 8 to 3, NOTUSE, fixed to 0."
        ::= { tnPtpctlPortConfigEntry 2 }

--------------------------------------------------------------------------------
-- PTPIO Optical Port Config Scalar
--------------------------------------------------------------------------------
    tnPtpioPortConfigAttributeTotal OBJECT-TYPE
        SYNTAX         Integer32
        MAX-ACCESS     read-only
        STATUS         current
        DESCRIPTION    "."
        ::= { tnOpticalPortConfig 229 }

--------------------------------------------------------------------------------
-- PTPIO Optical Port Config Table
--------------------------------------------------------------------------------
    tnPtpioPortConfigTable OBJECT-TYPE
        SYNTAX         SEQUENCE OF TnPtpioPortConfigEntry
        MAX-ACCESS     not-accessible
        STATUS         current
        DESCRIPTION    "The ports on a PTPIO optical card."
        ::= { tnOpticalPortConfig 230 }

    tnPtpioPortConfigEntry OBJECT-TYPE
        SYNTAX         TnPtpioPortConfigEntry
        MAX-ACCESS     not-accessible
        STATUS         current
        DESCRIPTION    "."
        INDEX { ifIndex }
        ::= { tnPtpioPortConfigTable 1 }

    TnPtpioPortConfigEntry ::=
        SEQUENCE {
            tnPtpioPortConfigFunction             INTEGER,
            tnPtpioPortConfigSigPortConnFromPort  InterfaceIndexOrZero,
            tnPtpioPortConfigSigPortConnToPort    InterfaceIndexOrZero
        }

    tnPtpioPortConfigFunction OBJECT-TYPE
        SYNTAX         INTEGER {
                         tp(1),
                         line(2),
                         sig(3),
                         itp(4)
                       }
        MAX-ACCESS     read-only
        STATUS         current
        DESCRIPTION    "Indicates the functional type of this PTPIO port."
        ::= { tnPtpioPortConfigEntry 1 }

    tnPtpioPortConfigSigPortConnFromPort OBJECT-TYPE
        SYNTAX         InterfaceIndexOrZero
        MAX-ACCESS     read-create
        STATUS         current
        DESCRIPTION    "The line port that is connected to the PTPIO SIG
                        port in the receive direction."
        DEFVAL         { 0 }
        ::= { tnPtpioPortConfigEntry 2 }

    tnPtpioPortConfigSigPortConnToPort OBJECT-TYPE
        SYNTAX         InterfaceIndexOrZero
        MAX-ACCESS     read-create
        STATUS         current
        DESCRIPTION    "The line port that is connected to the PTPIO SIG
                        port in the transmit direction."
        DEFVAL         { 0 }
        ::= { tnPtpioPortConfigEntry 3 }

--------------------------------------------------------------------------------
-- 24ET1GB Optical Port Config Scalar
--------------------------------------------------------------------------------
    tnIo24et1gbPortConfigAttributeTotal OBJECT-TYPE
        SYNTAX         Integer32
        MAX-ACCESS     read-only
        STATUS         current
        DESCRIPTION    "."
        ::= { tnOpticalPortConfig 231 }

--------------------------------------------------------------------------------
-- 24ET1GB Optical Port Config Table
--------------------------------------------------------------------------------
    tnIo24et1gbPortConfigTable OBJECT-TYPE
        SYNTAX         SEQUENCE OF TnIo24et1gbPortConfigEntry
        MAX-ACCESS     not-accessible
        STATUS         current
        DESCRIPTION    "The ports on a 24ET1GB optical card."
        ::= { tnOpticalPortConfig 232 }

    tnIo24et1gbPortConfigEntry OBJECT-TYPE
        SYNTAX         TnIo24et1gbPortConfigEntry
        MAX-ACCESS     not-accessible
        STATUS         current
        DESCRIPTION    "."
        INDEX { ifIndex }
        ::= { tnIo24et1gbPortConfigTable 1 }

    TnIo24et1gbPortConfigEntry ::=
        SEQUENCE {
            tnIo24et1gbPortConfigFunction  INTEGER
        }

    tnIo24et1gbPortConfigFunction OBJECT-TYPE
        SYNTAX         INTEGER {
                         network(1),
                         client(2)
                       }
        MAX-ACCESS     read-only
        STATUS         current
        DESCRIPTION    "Indicates the functional type of this 24ET1GB port."
        ::= { tnIo24et1gbPortConfigEntry 1 }

--------------------------------------------------------------------------------
-- DWDM IO Optical Port Config Scalar
--------------------------------------------------------------------------------
    tnDwdmIoPortConfigAttributeTotal OBJECT-TYPE
        SYNTAX         Integer32
        MAX-ACCESS     read-only
        STATUS         current
        DESCRIPTION    "."
        ::= { tnOpticalPortConfig 233 }

--------------------------------------------------------------------------------
-- DWDM IO Optical Port Config Table
--------------------------------------------------------------------------------
    tnDwdmIoPortConfigTable OBJECT-TYPE
        SYNTAX         SEQUENCE OF TnDwdmIoPortConfigEntry
        MAX-ACCESS     not-accessible
        STATUS         current
        DESCRIPTION    "The attributes for an optical port."
        ::= { tnOpticalPortConfig 234 }

    tnDwdmIoPortConfigEntry OBJECT-TYPE
        SYNTAX         TnDwdmIoPortConfigEntry
        MAX-ACCESS     not-accessible
        STATUS         current
        DESCRIPTION    "."
        INDEX { ifIndex }
        ::= { tnDwdmIoPortConfigTable 1 }

    TnDwdmIoPortConfigEntry ::=
        SEQUENCE {
            tnDwdmIoPortRole  INTEGER
        }

    tnDwdmIoPortRole OBJECT-TYPE
        SYNTAX         INTEGER {
                         line(1),
                         client(2)
                       }
        MAX-ACCESS     read-create
        STATUS         current
        DESCRIPTION    "Indicates if this port is line or client."
        DEFVAL         { client }
        ::= { tnDwdmIoPortConfigEntry 1 }

--------------------------------------------------------------------------------
-- 4AN10G Optical Port Config Scalar
--------------------------------------------------------------------------------
    tnIo4an10gPortConfigAttributeTotal OBJECT-TYPE
        SYNTAX         Integer32
        MAX-ACCESS     read-only
        STATUS         current
        DESCRIPTION    "."
        ::= { tnOpticalPortConfig 235 }

--------------------------------------------------------------------------------
-- 4AN10G Optical Port Config Table
--------------------------------------------------------------------------------
    tnIo4an10gPortConfigTable OBJECT-TYPE
        SYNTAX         SEQUENCE OF TnIo4an10gPortConfigEntry
        MAX-ACCESS     not-accessible
        STATUS         current
        DESCRIPTION    "The ports on a 4AN10G optical card."
        ::= { tnOpticalPortConfig 236 }

    tnIo4an10gPortConfigEntry OBJECT-TYPE
        SYNTAX         TnIo4an10gPortConfigEntry
        MAX-ACCESS     not-accessible
        STATUS         current
        DESCRIPTION    "."
        INDEX { ifIndex }
        ::= { tnIo4an10gPortConfigTable 1 }

    TnIo4an10gPortConfigEntry ::=
        SEQUENCE {
            tnIo4an10gPortConfigFunction  INTEGER
        }

    tnIo4an10gPortConfigFunction OBJECT-TYPE
        SYNTAX         INTEGER {
                         network(1),
                         client(2)
                       }
        MAX-ACCESS     read-only
        STATUS         current
        DESCRIPTION    "Indicates the functional type of this 4AN10G port."
        ::= { tnIo4an10gPortConfigEntry 1 }

--------------------------------------------------------------------------------
-- 8ET1GB Optical Port Config Scalar
--------------------------------------------------------------------------------
    tnIo8et1gbPortConfigAttributeTotal OBJECT-TYPE
        SYNTAX         Integer32
        MAX-ACCESS     read-only
        STATUS         current
        DESCRIPTION    "."
        ::= { tnOpticalPortConfig 237 }

--------------------------------------------------------------------------------
-- 8ET1GB Optical Port Config Table
--------------------------------------------------------------------------------
    tnIo8et1gbPortConfigTable OBJECT-TYPE
        SYNTAX         SEQUENCE OF TnIo8et1gbPortConfigEntry
        MAX-ACCESS     not-accessible
        STATUS         current
        DESCRIPTION    "The ports on a 8ET1GB optical card."
        ::= { tnOpticalPortConfig 238 }

    tnIo8et1gbPortConfigEntry OBJECT-TYPE
        SYNTAX         TnIo8et1gbPortConfigEntry
        MAX-ACCESS     not-accessible
        STATUS         current
        DESCRIPTION    "."
        INDEX { ifIndex }
        ::= { tnIo8et1gbPortConfigTable 1 }

    TnIo8et1gbPortConfigEntry ::=
        SEQUENCE {
            tnIo8et1gbPortConfigFunction  INTEGER
        }

    tnIo8et1gbPortConfigFunction OBJECT-TYPE
        SYNTAX         INTEGER {
                         network(1),
                         client(2)
                       }
        MAX-ACCESS     read-only
        STATUS         current
        DESCRIPTION    "Indicates the functional type of this 8ET1GB port."
        ::= { tnIo8et1gbPortConfigEntry 1 }

--------------------------------------------------------------------------------
-- 10ET10G Optical Port Config Scalar
--------------------------------------------------------------------------------
    tnIo10et10gPortConfigAttributeTotal OBJECT-TYPE
        SYNTAX         Integer32
        MAX-ACCESS     read-only
        STATUS         current
        DESCRIPTION    "."
        ::= { tnOpticalPortConfig 239 }

--------------------------------------------------------------------------------
-- 10ET10G Optical Port Config Table
--------------------------------------------------------------------------------
    tnIo10et10gPortConfigTable OBJECT-TYPE
        SYNTAX         SEQUENCE OF TnIo10et10gPortConfigEntry
        MAX-ACCESS     not-accessible
        STATUS         current
        DESCRIPTION    "The ports on a 10ET10G optical card."
        ::= { tnOpticalPortConfig 240 }

    tnIo10et10gPortConfigEntry OBJECT-TYPE
        SYNTAX         TnIo10et10gPortConfigEntry
        MAX-ACCESS     not-accessible
        STATUS         current
        DESCRIPTION    "."
        INDEX { ifIndex }
        ::= { tnIo10et10gPortConfigTable 1 }

    TnIo10et10gPortConfigEntry ::=
        SEQUENCE {
            tnIo10et10gPortConfigFunction  INTEGER
        }

    tnIo10et10gPortConfigFunction OBJECT-TYPE
        SYNTAX         INTEGER {
                         network(1),
                         client(2)
                       }
        MAX-ACCESS     read-only
        STATUS         current
        DESCRIPTION    "Indicates the functional type of this 10ET10G port."
        ::= { tnIo10et10gPortConfigEntry 1 }

--------------------------------------------------------------------------------
-- UL11QCUPC Optical Port Config Scalar
--------------------------------------------------------------------------------
    tnUl11qcupcPortConfigAttributeTotal OBJECT-TYPE
        SYNTAX         Integer32
        MAX-ACCESS     read-only
        STATUS         current
        DESCRIPTION    "."
        ::= { tnOpticalPortConfig 241 }

--------------------------------------------------------------------------------
-- UL11QCUPC Optical Port Config Table
--------------------------------------------------------------------------------
    tnUl11qcupcPortConfigTable OBJECT-TYPE
        SYNTAX         SEQUENCE OF TnUl11qcupcPortConfigEntry
        MAX-ACCESS     not-accessible
        STATUS         current
        DESCRIPTION    "The ports on a UL11QCUPC optical card."
        ::= { tnOpticalPortConfig 242 }

    tnUl11qcupcPortConfigEntry OBJECT-TYPE
        SYNTAX         TnUl11qcupcPortConfigEntry
        MAX-ACCESS     not-accessible
        STATUS         current
        DESCRIPTION    "."
        INDEX { ifIndex }
        ::= { tnUl11qcupcPortConfigTable 1 }

    TnUl11qcupcPortConfigEntry ::=
        SEQUENCE {
            tnUl11qcupcPortConfigFunction  INTEGER
        }

    tnUl11qcupcPortConfigFunction OBJECT-TYPE
        SYNTAX         INTEGER {
                         network(1),
                         evoa(2)
                       }
        MAX-ACCESS     read-only
        STATUS         current
        DESCRIPTION    "Indicates the functional type of this UL11QCUPC port."
        ::= { tnUl11qcupcPortConfigEntry 1 }

--------------------------------------------------------------------------------
-- 520SCX4 Optical Port Config Scalar
--------------------------------------------------------------------------------
    tnOt520scx4PortConfigAttributeTotal OBJECT-TYPE
        SYNTAX         Integer32
        MAX-ACCESS     read-only
        STATUS         current
        DESCRIPTION    "."
        ::= { tnOpticalPortConfig 243 }

--------------------------------------------------------------------------------
-- 520SCX4 Optical Port Config Table
--------------------------------------------------------------------------------
    tnOt520scx4PortConfigTable OBJECT-TYPE
        SYNTAX         SEQUENCE OF TnOt520scx4PortConfigEntry
        MAX-ACCESS     not-accessible
        STATUS         current
        DESCRIPTION    "The ports on a 520SCX4 optical card."
        ::= { tnOpticalPortConfig 244 }

    tnOt520scx4PortConfigEntry OBJECT-TYPE
        SYNTAX         TnOt520scx4PortConfigEntry
        MAX-ACCESS     not-accessible
        STATUS         current
        DESCRIPTION    "."
        INDEX { ifIndex }
        ::= { tnOt520scx4PortConfigTable 1 }

    TnOt520scx4PortConfigEntry ::=
        SEQUENCE {
            tnOt520scx4PortConfigFunction  INTEGER
        }

    tnOt520scx4PortConfigFunction OBJECT-TYPE
        SYNTAX         INTEGER {
                         network(1),
                         client(2)
                       }
        MAX-ACCESS     read-only
        STATUS         current
        DESCRIPTION    "Indicates the functional type of this 520SCX4 port."
        ::= { tnOt520scx4PortConfigEntry 1 }

--------------------------------------------------------------------------------
-- WSS APR Port Config Scalar
--------------------------------------------------------------------------------
    tnWssAprPortConfigAttributeTotal OBJECT-TYPE
        SYNTAX         Integer32
        MAX-ACCESS     read-only
        STATUS         current
        DESCRIPTION    "."
        ::= { tnOpticalPortConfig 245 }

--------------------------------------------------------------------------------
-- WSS APR Port Config Table
--------------------------------------------------------------------------------
    tnWssAprPortConfigTable OBJECT-TYPE
        SYNTAX         SEQUENCE OF TnWssAprPortConfigEntry
        MAX-ACCESS     not-accessible
        STATUS         current
        DESCRIPTION    "The APR attribute for a WSS port."
        ::= { tnOpticalPortConfig 246 }

    tnWssAprPortConfigEntry OBJECT-TYPE
        SYNTAX         TnWssAprPortConfigEntry
        MAX-ACCESS     not-accessible
        STATUS         current
        DESCRIPTION    "."
        INDEX { ifIndex }
        ::= { tnWssAprPortConfigTable 1 }

    TnWssAprPortConfigEntry ::=
        SEQUENCE {
            tnWssAprPortConfigAprHoldOffTime     INTEGER
        }

    tnWssAprPortConfigAprHoldOffTime OBJECT-TYPE
        SYNTAX         INTEGER {
                         time0ms(1),
                         time250ms(4)
                       }
        MAX-ACCESS     read-create
        STATUS         current
        DESCRIPTION    "The auto power recovery hold off time."
        DEFVAL         { time0ms }
        ::= { tnWssAprPortConfigEntry 1 }

--------------------------------------------------------------------------------
-- Power Filter Port Config Scalar
--------------------------------------------------------------------------------
    tnPowerFilterPortConfigAttributeTotal OBJECT-TYPE
        SYNTAX         Integer32
        MAX-ACCESS     read-only
        STATUS         current
        DESCRIPTION    "."
        ::= { tnOpticalPortConfig 247 }

--------------------------------------------------------------------------------
-- Power Filter Port Config Table
--------------------------------------------------------------------------------
    tnPowerFilterPortConfigTable OBJECT-TYPE
        SYNTAX         SEQUENCE OF TnPowerFilterPortConfigEntry
        MAX-ACCESS     not-accessible
        STATUS         current
        DESCRIPTION    "The ports on a PowerFilter optical card."
        ::= { tnOpticalPortConfig 248 }

    tnPowerFilterPortConfigEntry OBJECT-TYPE
        SYNTAX         TnPowerFilterPortConfigEntry
        MAX-ACCESS     not-accessible
        STATUS         current
        DESCRIPTION    "."
        INDEX { ifIndex }
        ::= { tnPowerFilterPortConfigTable 1 }

    TnPowerFilterPortConfigEntry ::=
        SEQUENCE {
            tnPowerFilterPortConfigFunction  INTEGER
        }

    tnPowerFilterPortConfigFunction OBJECT-TYPE
        SYNTAX         INTEGER {
                         oneTru(1)
                       }
        MAX-ACCESS     read-only
        STATUS         current
        DESCRIPTION    "Indicates the functional type of this PowerFilter port."
        ::= { tnPowerFilterPortConfigEntry 1 }

--------------------------------------------------------------------------------
-- 11OPE8 Optical Port Config Scalar
--------------------------------------------------------------------------------
    tn11ope8PortConfigAttributeTotal OBJECT-TYPE
        SYNTAX         Integer32
        MAX-ACCESS     read-only
        STATUS         current
        DESCRIPTION    "."
        ::= { tnOpticalPortConfig 249 }

--------------------------------------------------------------------------------
-- 11OPE8 Optical Port Config Table
--------------------------------------------------------------------------------
    tn11ope8PortConfigTable OBJECT-TYPE
        SYNTAX         SEQUENCE OF Tn11ope8PortConfigEntry
        MAX-ACCESS     not-accessible
        STATUS         current
        DESCRIPTION    "The ports on a 11OPE8 optical card."
        ::= { tnOpticalPortConfig 250 }

    tn11ope8PortConfigEntry OBJECT-TYPE
        SYNTAX         Tn11ope8PortConfigEntry
        MAX-ACCESS     not-accessible
        STATUS         current
        DESCRIPTION    "."
        INDEX { ifIndex }
        ::= { tn11ope8PortConfigTable 1 }

    Tn11ope8PortConfigEntry ::=
        SEQUENCE {
            tn11ope8PortConfigFunction  INTEGER
        }

    tn11ope8PortConfigFunction OBJECT-TYPE
        SYNTAX         INTEGER {
                         network(1),
                         client(2),
                         evoa(3),
                         backplane(4),
                         tod(5),
                         ethman(6)
                       }
        MAX-ACCESS     read-only
        STATUS         current
        DESCRIPTION    "Indicates the functional type of this 11OPE8 port."
        ::= { tn11ope8PortConfigEntry 1 }

--------------------------------------------------------------------------------
-- 11QCE12X Optical Port Config Scalar
--------------------------------------------------------------------------------
    tn11qce12xPortConfigAttributeTotal OBJECT-TYPE
        SYNTAX         Integer32
        MAX-ACCESS     read-only
        STATUS         current
        DESCRIPTION    "."
        ::= { tnOpticalPortConfig 251 }

--------------------------------------------------------------------------------
-- 11QCE12X Optical Port Config Table
--------------------------------------------------------------------------------
    tn11qce12xPortConfigTable OBJECT-TYPE
        SYNTAX         SEQUENCE OF Tn11qce12xPortConfigEntry
        MAX-ACCESS     not-accessible
        STATUS         current
        DESCRIPTION    "The ports on a 11QCE12X optical card."
        ::= { tnOpticalPortConfig 252 }

    tn11qce12xPortConfigEntry OBJECT-TYPE
        SYNTAX         Tn11qce12xPortConfigEntry
        MAX-ACCESS     not-accessible
        STATUS         current
        DESCRIPTION    "."
        INDEX { ifIndex }
        ::= { tn11qce12xPortConfigTable 1 }

    Tn11qce12xPortConfigEntry ::=
        SEQUENCE {
            tn11qce12xPortConfigFunction  INTEGER
        }

    tn11qce12xPortConfigFunction OBJECT-TYPE
        SYNTAX         INTEGER {
                         network(1),
                         client(2),
                         evoa(3),
                         backplane(4),
                         tod(5),
                         bits(6),
                         ethman(7)
                       }
        MAX-ACCESS     read-only
        STATUS         current
        DESCRIPTION    "Indicates the functional type of this 11QCE12X port."
        ::= { tn11qce12xPortConfigEntry 1 }

--------------------------------------------------------------------------------
-- AM2625A Optical Port Config Scalar
--------------------------------------------------------------------------------
    tnAm2625aPortConfigAttributeTotal OBJECT-TYPE
        SYNTAX         Integer32
        MAX-ACCESS     read-only
        STATUS         current
        DESCRIPTION    "."
        ::= { tnOpticalPortConfig 253 }

--------------------------------------------------------------------------------
-- AM2625A Optical Port Config Table
--------------------------------------------------------------------------------
    tnAm2625aPortConfigTable OBJECT-TYPE
        SYNTAX         SEQUENCE OF TnAm2625aPortConfigEntry
        MAX-ACCESS     not-accessible
        STATUS         current
        DESCRIPTION    "The ports on an AM2625A optical card."
        ::= { tnOpticalPortConfig 254 }

    tnAm2625aPortConfigEntry OBJECT-TYPE
        SYNTAX         TnAm2625aPortConfigEntry
        MAX-ACCESS     not-accessible
        STATUS         current
        DESCRIPTION    "."
        INDEX { ifIndex }
        ::= { tnAm2625aPortConfigTable 1 }

    TnAm2625aPortConfigEntry ::=
        SEQUENCE {
            tnAm2625aPortConfigFunction INTEGER
        }

    tnAm2625aPortConfigFunction OBJECT-TYPE
        SYNTAX         INTEGER {
                         lineIn(1),
                         inv(2),
                         dcm(3),
                         lineOut(4),
                         oscSfp(5),
                         det(6),
                         osc(7),
                         custLan(8)
                       }
        MAX-ACCESS     read-only
        STATUS         current
        DESCRIPTION    "Indicates the functional type of this AM2625A port."
        ::= { tnAm2625aPortConfigEntry 1 }

--------------------------------------------------------------------------------
-- AM2032A Optical Port Config Scalar
--------------------------------------------------------------------------------
    tnAm2032aPortConfigAttributeTotal OBJECT-TYPE
        SYNTAX         Integer32
        MAX-ACCESS     read-only
        STATUS         current
        DESCRIPTION    "."
        ::= { tnOpticalPortConfig 255 }

--------------------------------------------------------------------------------
-- AM2032A Optical Port Config Table
--------------------------------------------------------------------------------
    tnAm2032aPortConfigTable OBJECT-TYPE
        SYNTAX         SEQUENCE OF TnAm2032aPortConfigEntry
        MAX-ACCESS     not-accessible
        STATUS         current
        DESCRIPTION    "The ports on an AM2032A optical card."
        ::= { tnOpticalPortConfig 256 }

    tnAm2032aPortConfigEntry OBJECT-TYPE
        SYNTAX         TnAm2032aPortConfigEntry
        MAX-ACCESS     not-accessible
        STATUS         current
        DESCRIPTION    "."
        INDEX { ifIndex }
        ::= { tnAm2032aPortConfigTable 1 }

    TnAm2032aPortConfigEntry ::=
        SEQUENCE {
            tnAm2032aPortConfigFunction INTEGER
        }

    tnAm2032aPortConfigFunction OBJECT-TYPE
        SYNTAX         INTEGER {
                         lineIn(1),
                         inv(2),
                         dcm(3),
                         lineOut(4),
                         oscSfp(5),
                         det(6),
                         osc(7),
                         custLan(8)
                       }
        MAX-ACCESS     read-only
        STATUS         current
        DESCRIPTION    "Indicates the functional type of this AM2032A port."
        ::= { tnAm2032aPortConfigEntry 1 }

--------------------------------------------------------------------------------
-- OT260SCX2 Optical Port Config Scalar
--------------------------------------------------------------------------------
    tnOt260scx2PortConfigAttributeTotal OBJECT-TYPE
        SYNTAX         Integer32
        MAX-ACCESS     read-only
        STATUS         current
        DESCRIPTION    "."
        ::= { tnOpticalPortConfig 257 }

--------------------------------------------------------------------------------
-- OT260SCX2 Optical Port Config Table
--------------------------------------------------------------------------------
    tnOt260scx2PortConfigTable OBJECT-TYPE
        SYNTAX         SEQUENCE OF TnOt260scx2PortConfigEntry
        MAX-ACCESS     not-accessible
        STATUS         current
        DESCRIPTION    "The ports on a OT260SCX2 optical card."
        ::= { tnOpticalPortConfig 258 }

    tnOt260scx2PortConfigEntry OBJECT-TYPE
        SYNTAX         TnOt260scx2PortConfigEntry
        MAX-ACCESS     not-accessible
        STATUS         current
        DESCRIPTION    "."
        INDEX { ifIndex }
        ::= { tnOt260scx2PortConfigTable 1 }

    TnOt260scx2PortConfigEntry ::=
        SEQUENCE {
            tnOt260scx2PortConfigFunction  INTEGER
        }

    tnOt260scx2PortConfigFunction OBJECT-TYPE
        SYNTAX         INTEGER {
                         network(1),
                         client(2)
                       }
        MAX-ACCESS     read-only
        STATUS         current
        DESCRIPTION    "Indicates the functional type of this OT260SCX2 port."
        ::= { tnOt260scx2PortConfigEntry 1 }

--------------------------------------------------------------------------------
-- OT130SNX10 Optical Port Config Scalar
--------------------------------------------------------------------------------
    tnOt130snx10PortConfigAttributeTotal OBJECT-TYPE
        SYNTAX         Integer32
        MAX-ACCESS     read-only
        STATUS         current
        DESCRIPTION    "."
        ::= { tnOpticalPortConfig 259 }

--------------------------------------------------------------------------------
-- OT130SNX10 Optical Port Config Table
--------------------------------------------------------------------------------
    tnOt130snx10PortConfigTable OBJECT-TYPE
        SYNTAX         SEQUENCE OF TnOt130snx10PortConfigEntry
        MAX-ACCESS     not-accessible
        STATUS         current
        DESCRIPTION    "The ports on a OT130SNX10 optical card."
        ::= { tnOpticalPortConfig 260 }

    tnOt130snx10PortConfigEntry OBJECT-TYPE
        SYNTAX         TnOt130snx10PortConfigEntry
        MAX-ACCESS     not-accessible
        STATUS         current
        DESCRIPTION    "."
        INDEX { ifIndex }
        ::= { tnOt130snx10PortConfigTable 1 }

    TnOt130snx10PortConfigEntry ::=
        SEQUENCE {
            tnOt130snx10PortConfigFunction  INTEGER
        }

    tnOt130snx10PortConfigFunction OBJECT-TYPE
        SYNTAX         INTEGER {
                         network(1),
                         client(2)
                       }
        MAX-ACCESS     read-only
        STATUS         current
        DESCRIPTION    "Indicates the functional type of this OT130SNX10 port."
        ::= { tnOt130snx10PortConfigEntry 1 }

--------------------------------------------------------------------------------
-- IO24ANMB Optical Port Config Scalar
--------------------------------------------------------------------------------
    tnIo24anmbPortConfigAttributeTotal OBJECT-TYPE
        SYNTAX         Integer32
        MAX-ACCESS     read-only
        STATUS         current
        DESCRIPTION    "."
        ::= { tnOpticalPortConfig 261 }

--------------------------------------------------------------------------------
-- IO24ANMB Optical Port Config Table
--------------------------------------------------------------------------------
    tnIo24anmbPortConfigTable OBJECT-TYPE
        SYNTAX         SEQUENCE OF TnIo24anmbPortConfigEntry
        MAX-ACCESS     not-accessible
        STATUS         current
        DESCRIPTION    "The ports on a IO24ANMB optical card."
        ::= { tnOpticalPortConfig 262 }

    tnIo24anmbPortConfigEntry OBJECT-TYPE
        SYNTAX         TnIo24anmbPortConfigEntry
        MAX-ACCESS     not-accessible
        STATUS         current
        DESCRIPTION    "."
        INDEX { ifIndex }
        ::= { tnIo24anmbPortConfigTable 1 }

    TnIo24anmbPortConfigEntry ::=
        SEQUENCE {
            tnIo24anmbPortConfigFunction INTEGER
        }

    tnIo24anmbPortConfigFunction OBJECT-TYPE
        SYNTAX         INTEGER {
                         client(1)
                       }
        MAX-ACCESS     read-only
        STATUS         current
        DESCRIPTION    "Indicates the functional type of this IO24ANMB port."
        ::= { tnIo24anmbPortConfigEntry 1 }

--------------------------------------------------------------------------------
-- OT11DPM8 Optical Port Config Scalar
--------------------------------------------------------------------------------
    tnOt11dpm8PortConfigAttributeTotal OBJECT-TYPE
        SYNTAX         Integer32
        MAX-ACCESS     read-only
        STATUS         current
        DESCRIPTION    "."
        ::= { tnOpticalPortConfig 263 }

--------------------------------------------------------------------------------
-- OT11DPM8 Optical Port Config Table
--------------------------------------------------------------------------------
    tnOt11dpm8PortConfigTable OBJECT-TYPE
        SYNTAX         SEQUENCE OF TnOt11dpm8PortConfigEntry
        MAX-ACCESS     not-accessible
        STATUS         current
        DESCRIPTION    "The ports on a OT11DPM8 optical card."
        ::= { tnOpticalPortConfig 264 }

    tnOt11dpm8PortConfigEntry OBJECT-TYPE
        SYNTAX         TnOt11dpm8PortConfigEntry
        MAX-ACCESS     not-accessible
        STATUS         current
        DESCRIPTION    "."
        INDEX { ifIndex }
        ::= { tnOt11dpm8PortConfigTable 1 }

    TnOt11dpm8PortConfigEntry ::=
        SEQUENCE {
            tnOt11dpm8PortConfigFunction    INTEGER,
            tnOt11dpm8PortConfigTtpPresent  TruthValue
        }

    tnOt11dpm8PortConfigFunction OBJECT-TYPE
        SYNTAX         INTEGER {
                         network(1),
                         client(2),
                         evoa(3)
                       }
        MAX-ACCESS     read-only
        STATUS         current
        DESCRIPTION    "Indicates the functional type of this OT11DPM8 port."
        ::= { tnOt11dpm8PortConfigEntry 1 }

    tnOt11dpm8PortConfigTtpPresent OBJECT-TYPE
        SYNTAX         TruthValue
        MAX-ACCESS     read-create
        STATUS         current
        DESCRIPTION    "Ttp present:
                        true  - TP facility is present
                        false - NIM facility is present."
        DEFVAL         { false }
        ::= { tnOt11dpm8PortConfigEntry 2 }


--------------------------------------------------------------------------------
-- OT11DPM4M Optical Port Config Scalar
--------------------------------------------------------------------------------
    tnOt11dpm4mPortConfigAttributeTotal OBJECT-TYPE
        SYNTAX         Integer32
        MAX-ACCESS     read-only
        STATUS         current
        DESCRIPTION    "."
        ::= { tnOpticalPortConfig 265 }

--------------------------------------------------------------------------------
-- OT11DPM4M Optical Port Config Table
--------------------------------------------------------------------------------
    tnOt11dpm4mPortConfigTable OBJECT-TYPE
        SYNTAX         SEQUENCE OF TnOt11dpm4mPortConfigEntry
        MAX-ACCESS     not-accessible
        STATUS         current
        DESCRIPTION    "The ports on a OT11DPM4M optical card."
        ::= { tnOpticalPortConfig 266 }

    tnOt11dpm4mPortConfigEntry OBJECT-TYPE
        SYNTAX         TnOt11dpm4mPortConfigEntry
        MAX-ACCESS     not-accessible
        STATUS         current
        DESCRIPTION    "."
        INDEX { ifIndex }
        ::= { tnOt11dpm4mPortConfigTable 1 }

    TnOt11dpm4mPortConfigEntry ::=
        SEQUENCE {
            tnOt11dpm4mPortConfigFunction INTEGER
        }

    tnOt11dpm4mPortConfigFunction OBJECT-TYPE
        SYNTAX         INTEGER {
                         network(1),
                         client(2)
                       }
        MAX-ACCESS     read-only
        STATUS         current
        DESCRIPTION    "Indicates the functional type of this OT11DPM4M port."
        ::= { tnOt11dpm4mPortConfigEntry 1 }

--------------------------------------------------------------------------------
-- UL130SCUPB Optical Port Config Scalar
--------------------------------------------------------------------------------
    tnUl130scupbPortConfigAttributeTotal OBJECT-TYPE
        SYNTAX         Integer32
        MAX-ACCESS     read-only
        STATUS         current
        DESCRIPTION    "."
        ::= { tnOpticalPortConfig 267 }

--------------------------------------------------------------------------------
-- UL130SCUPB Optical Port Config Table
--------------------------------------------------------------------------------
    tnUl130scupbPortConfigTable OBJECT-TYPE
        SYNTAX         SEQUENCE OF TnUl130scupbPortConfigEntry
        MAX-ACCESS     not-accessible
        STATUS         current
        DESCRIPTION    "The ports on a UL130SCUPB optical card."
        ::= { tnOpticalPortConfig 268 }

    tnUl130scupbPortConfigEntry OBJECT-TYPE
        SYNTAX         TnUl130scupbPortConfigEntry
        MAX-ACCESS     not-accessible
        STATUS         current
        DESCRIPTION    "."
        INDEX { ifIndex }
        ::= { tnUl130scupbPortConfigTable 1 }

    TnUl130scupbPortConfigEntry ::=
        SEQUENCE {
            tnUl130scupbPortConfigFunction  INTEGER
        }

    tnUl130scupbPortConfigFunction OBJECT-TYPE
        SYNTAX         INTEGER {
                         network(1)
                       }
        MAX-ACCESS     read-only
        STATUS         current
        DESCRIPTION    "Indicates the functional type of this UL130SCUPB port."
        ::= { tnUl130scupbPortConfigEntry 1 }

--------------------------------------------------------------------------------
-- OT112SDX11 Optical Port Config Scalar
--------------------------------------------------------------------------------
    tnOt112sdx11PortConfigAttributeTotal OBJECT-TYPE
        SYNTAX         Integer32
        MAX-ACCESS     read-only
        STATUS         current
        DESCRIPTION    "."
        ::= { tnOpticalPortConfig 269 }

--------------------------------------------------------------------------------
-- OT112SDX11 Optical Port Config Table
--------------------------------------------------------------------------------
    tnOt112sdx11PortConfigTable OBJECT-TYPE
        SYNTAX         SEQUENCE OF TnOt112sdx11PortConfigEntry
        MAX-ACCESS     not-accessible
        STATUS         current
        DESCRIPTION    "The ports on a OT112SDX11 optical card."
        ::= { tnOpticalPortConfig 270 }

    tnOt112sdx11PortConfigEntry OBJECT-TYPE
        SYNTAX         TnOt112sdx11PortConfigEntry
        MAX-ACCESS     not-accessible
        STATUS         current
        DESCRIPTION    "."
        INDEX { ifIndex }
        ::= { tnOt112sdx11PortConfigTable 1 }

    TnOt112sdx11PortConfigEntry ::=
        SEQUENCE {
            tnOt112sdx11PortConfigFunction  INTEGER,
            tnOt112sdx11PortConfigLinkGroupId INTEGER,
            tnOt112sdx11ProgrammedNwOutputPower Integer32
        }

    tnOt112sdx11PortConfigFunction OBJECT-TYPE
        SYNTAX         INTEGER {
                         network(1),
                         client(2)
                       }
        MAX-ACCESS     read-only
        STATUS         current
        DESCRIPTION    "Indicates the functional type of this OT112SDX11 port."
        ::= { tnOt112sdx11PortConfigEntry 1 }

    tnOt112sdx11PortConfigLinkGroupId OBJECT-TYPE
        SYNTAX         INTEGER {
                         notApplicable(1),
                         islGroupId1(2),
                         islGroupId2(3),
                         islGroupId3(4),
                         islGroupId4(5),
                         islGroupId5(6)
                       }
        MAX-ACCESS     read-create
        STATUS         current
        DESCRIPTION    "port ISL group Id."
        DEFVAL         { notApplicable }
        ::= { tnOt112sdx11PortConfigEntry 2 }

    tnOt112sdx11ProgrammedNwOutputPower OBJECT-TYPE
        SYNTAX         Integer32
        UNITS          "mBm"
        MAX-ACCESS     read-create
        STATUS         current
        DESCRIPTION    "The programmed DC output power of
                         the port with Coherent CFP, measured in mBm.
                         It is the power of the full optical signal.
                        Current configurable range:
                         -1500 to 300 (C120G1TC coherent cfp on 112SDX11)"
        ::= { tnOt112sdx11PortConfigEntry 3 }

--------------------------------------------------------------------------------
-- AA2DONW Port Config Scalar
--------------------------------------------------------------------------------
    tnAa2donwPortConfigAttributeTotal OBJECT-TYPE
        SYNTAX         Integer32
        MAX-ACCESS     read-only
        STATUS         current
        DESCRIPTION    "."
        ::= { tnOpticalPortConfig 271 }

--------------------------------------------------------------------------------
-- AA2DONW Port Config Table
--------------------------------------------------------------------------------
    tnAa2donwPortConfigTable OBJECT-TYPE
        SYNTAX         SEQUENCE OF TnAa2donwPortConfigEntry
        MAX-ACCESS     not-accessible
        STATUS         current
        DESCRIPTION    "The ports on an AA2DONW optical card."
        ::= { tnOpticalPortConfig 272 }

    tnAa2donwPortConfigEntry OBJECT-TYPE
        SYNTAX         TnAa2donwPortConfigEntry
        MAX-ACCESS     not-accessible
        STATUS         current
        DESCRIPTION    "."
        INDEX { ifIndex }
        ::= { tnAa2donwPortConfigTable 1 }

    TnAa2donwPortConfigEntry ::=
        SEQUENCE {
            tnAa2donwPortConfigFunction  INTEGER
        }

    tnAa2donwPortConfigFunction OBJECT-TYPE
        SYNTAX         INTEGER {
                         line(1),
                         signal(2),
                         inv(3),
                         osc(4),
                         oscSfp(5)
                       }
        MAX-ACCESS     read-only
        STATUS         current
        DESCRIPTION    "Indicates the functional type of this AA2DONW port."
        ::= { tnAa2donwPortConfigEntry 1 }

--------------------------------------------------------------------------------
-- 130SCA1 Optical Port Config Scalar
--------------------------------------------------------------------------------
    tnOt130sca1PortConfigAttributeTotal OBJECT-TYPE
        SYNTAX         Integer32
        MAX-ACCESS     read-only
        STATUS         current
        DESCRIPTION    "."
        ::= { tnOpticalPortConfig 273 }

--------------------------------------------------------------------------------
-- 130SCA1 Optical Port Config Table
--------------------------------------------------------------------------------
    tnOt130sca1PortConfigTable OBJECT-TYPE
        SYNTAX         SEQUENCE OF TnOt130sca1PortConfigEntry
        MAX-ACCESS     not-accessible
        STATUS         current
        DESCRIPTION    "The ports on a 130SCA1 optical card."
        ::= { tnOpticalPortConfig 274 }

    tnOt130sca1PortConfigEntry OBJECT-TYPE
        SYNTAX         TnOt130sca1PortConfigEntry
        MAX-ACCESS     not-accessible
        STATUS         current
        DESCRIPTION    "."
        INDEX { ifIndex }
        ::= { tnOt130sca1PortConfigTable 1 }

    TnOt130sca1PortConfigEntry ::=
        SEQUENCE {
            tnOt130sca1PortConfigFunction INTEGER
        }

    tnOt130sca1PortConfigFunction OBJECT-TYPE
        SYNTAX         INTEGER {
                         network(1),
                         client(2)
                       }
        MAX-ACCESS     read-only
        STATUS         current
        DESCRIPTION    "Indicates the functional type of this 130SCA1 port."
        ::= { tnOt130sca1PortConfigEntry 1 }

--------------------------------------------------------------------------------
-- 10AN10GB Optical Port Config Scalar
--------------------------------------------------------------------------------
    tnIo10an10gbPortConfigAttributeTotal OBJECT-TYPE
        SYNTAX         Integer32
        MAX-ACCESS     read-only
        STATUS         current
        DESCRIPTION    "."
        ::= { tnOpticalPortConfig 275 }

--------------------------------------------------------------------------------
-- 10AN10GB Optical Port Config Table
--------------------------------------------------------------------------------
    tnIo10an10gbPortConfigTable OBJECT-TYPE
        SYNTAX         SEQUENCE OF TnIo10an10gbPortConfigEntry
        MAX-ACCESS     not-accessible
        STATUS         current
        DESCRIPTION    "The ports on a 10AN10GB optical card."
        ::= { tnOpticalPortConfig 276 }

    tnIo10an10gbPortConfigEntry OBJECT-TYPE
        SYNTAX         TnIo10an10gbPortConfigEntry
        MAX-ACCESS     not-accessible
        STATUS         current
        DESCRIPTION    "."
        INDEX { ifIndex }
        ::= { tnIo10an10gbPortConfigTable 1 }

    TnIo10an10gbPortConfigEntry ::=
        SEQUENCE {
            tnIo10an10gbPortConfigFunction INTEGER
        }

    tnIo10an10gbPortConfigFunction OBJECT-TYPE
        SYNTAX         INTEGER {
                         network(1),
                         client(2)
                       }
        MAX-ACCESS     read-only
        STATUS         current
        DESCRIPTION    "Indicates the functional type of this 10AN10GB port."
        ::= { tnIo10an10gbPortConfigEntry 1 }

--------------------------------------------------------------------------------
-- 10ET10GB Optical Port Config Scalar
--------------------------------------------------------------------------------
    tnIo10et10gbPortConfigAttributeTotal OBJECT-TYPE
        SYNTAX         Integer32
        MAX-ACCESS     read-only
        STATUS         current
        DESCRIPTION    "."
        ::= { tnOpticalPortConfig 277 }

--------------------------------------------------------------------------------
-- 10ET10GB Optical Port Config Table
--------------------------------------------------------------------------------
    tnIo10et10gbPortConfigTable OBJECT-TYPE
        SYNTAX         SEQUENCE OF TnIo10et10gbPortConfigEntry
        MAX-ACCESS     not-accessible
        STATUS         current
        DESCRIPTION    "The ports on a 10ET10GB optical card."
        ::= { tnOpticalPortConfig 278 }

    tnIo10et10gbPortConfigEntry OBJECT-TYPE
        SYNTAX         TnIo10et10gbPortConfigEntry
        MAX-ACCESS     not-accessible
        STATUS         current
        DESCRIPTION    "."
        INDEX { ifIndex }
        ::= { tnIo10et10gbPortConfigTable 1 }

    TnIo10et10gbPortConfigEntry ::=
        SEQUENCE {
            tnIo10et10gbPortConfigFunction  INTEGER
        }

    tnIo10et10gbPortConfigFunction OBJECT-TYPE
        SYNTAX         INTEGER {
                         network(1),
                         client(2)
                       }
        MAX-ACCESS     read-only
        STATUS         current
        DESCRIPTION    "Indicates the functional type of this 10ET10GB port."
        ::= { tnIo10et10gbPortConfigEntry 1 }

--------------------------------------------------------------------------------
-- PSC1-6 Optical Port Config Scalar
--------------------------------------------------------------------------------
    tnPsc1x6PortConfigAttributeTotal OBJECT-TYPE
        SYNTAX         Integer32
        MAX-ACCESS     read-only
        STATUS         current
        DESCRIPTION    "."
        ::= { tnOpticalPortConfig 279 }

--------------------------------------------------------------------------------
-- PSC1-6 Optical Port Config Table
--------------------------------------------------------------------------------
    tnPsc1x6PortConfigTable OBJECT-TYPE
        SYNTAX         SEQUENCE OF TnPsc1x6PortConfigEntry
        MAX-ACCESS     not-accessible
        STATUS         current
        DESCRIPTION    "The ports on a PSC1-6 optical card."
        ::= { tnOpticalPortConfig 280 }

    tnPsc1x6PortConfigEntry OBJECT-TYPE
        SYNTAX         TnPsc1x6PortConfigEntry
        MAX-ACCESS     not-accessible
        STATUS         current
        DESCRIPTION    "."
        INDEX { ifIndex }
        ::= { tnPsc1x6PortConfigTable 1 }

    TnPsc1x6PortConfigEntry ::=
        SEQUENCE {
            tnPsc1x6PortConfigFunction  INTEGER
        }

    tnPsc1x6PortConfigFunction OBJECT-TYPE
        SYNTAX         INTEGER {
                         signal(1),
                         channel(2)
                       }
        MAX-ACCESS     read-only
        STATUS         current
        DESCRIPTION    "Indicates the functional type of this PSC1-6 port."
        ::= { tnPsc1x6PortConfigEntry 1 }

--------------------------------------------------------------------------------
-- WR20-TF Optical Port Config Scalar
--------------------------------------------------------------------------------
    tnWr20tfPortConfigAttributeTotal OBJECT-TYPE
        SYNTAX         Integer32
        MAX-ACCESS     read-only
        STATUS         current
        DESCRIPTION    "."
        ::= { tnOpticalPortConfig 281 }

--------------------------------------------------------------------------------
-- WR20-TF Optical Port Config Table
--------------------------------------------------------------------------------
    tnWr20tfPortConfigTable OBJECT-TYPE
        SYNTAX         SEQUENCE OF TnWr20tfPortConfigEntry
        MAX-ACCESS     not-accessible
        STATUS         current
        DESCRIPTION    "The ports on a WR20-TF optical card."
        ::= { tnOpticalPortConfig 282 }

    tnWr20tfPortConfigEntry OBJECT-TYPE
        SYNTAX         TnWr20tfPortConfigEntry
        MAX-ACCESS     not-accessible
        STATUS         current
        DESCRIPTION    "."
        INDEX { ifIndex }
        ::= { tnWr20tfPortConfigTable 1 }

    TnWr20tfPortConfigEntry ::=
        SEQUENCE {
            tnWr20tfPortConfigFunction             INTEGER,
            tnWr20tfPortConfigDropInitTargetPower  Integer32,
            tnWr20tfPortConfigExpressTargetPower   Integer32,
            tnWr20tfPortConfigDropMaxTargetPower   Integer32,
            tnWr20tfPortConfigDropMinTargetPower   Integer32
        }

    tnWr20tfPortConfigFunction OBJECT-TYPE
        SYNTAX         INTEGER {
                         signal(1),
                         adt(2),
                         ad(3),
                         inv(4)
                       }
        MAX-ACCESS     read-only
        STATUS         current
        DESCRIPTION    "Indicates the functional type of this WR20-TF port."
        ::= { tnWr20tfPortConfigEntry 1 }

    tnWr20tfPortConfigDropInitTargetPower OBJECT-TYPE
        SYNTAX         Integer32 (-2000..0)
        UNITS          "mBm"
        MAX-ACCESS     read-create
        STATUS         current
        DESCRIPTION    "The initial target power used for dropped channels.

                        Current configurable range: -2000 to 0."
        DEFVAL         { -800 }
        ::= { tnWr20tfPortConfigEntry 2 }

    tnWr20tfPortConfigExpressTargetPower OBJECT-TYPE
        SYNTAX         Integer32 (-2000..300)
        UNITS          "mBm"
        MAX-ACCESS     read-create
        STATUS         current
        DESCRIPTION    "The target power used to set drop side WSS
                        attenuation value for expressed channels.

                        Current configurable range: -2000 to 300."
        DEFVAL         { -800 }
        ::= { tnWr20tfPortConfigEntry 3 }

    tnWr20tfPortConfigDropMaxTargetPower OBJECT-TYPE
        SYNTAX         Integer32 (-2000..0)
        UNITS          "mBm"
        MAX-ACCESS     read-create
        STATUS         current
        DESCRIPTION    "Upper limit for SCOT drop target adjustment loop.
                        For advanced users only.

                        Current configurable range: -2000 to 0."
        DEFVAL         { -600 }
        ::= { tnWr20tfPortConfigEntry 4 }

    tnWr20tfPortConfigDropMinTargetPower OBJECT-TYPE
        SYNTAX         Integer32 (-2000..0)
        UNITS          "mBm"
        MAX-ACCESS     read-create
        STATUS         current
        DESCRIPTION    "Lower limit for SCOT drop target adjustment loop.
                        For advanced users only.

                        Current configurable range: -2000 to 0."
        DEFVAL         { -1200 }
        ::= { tnWr20tfPortConfigEntry 5 }

--------------------------------------------------------------------------------
-- WTOCMF Optical Port Config Scalar
--------------------------------------------------------------------------------
    tnWtocmfPortConfigAttributeTotal OBJECT-TYPE
        SYNTAX         Integer32
        MAX-ACCESS     read-only
        STATUS         current
        DESCRIPTION    "."
        ::= { tnOpticalPortConfig 283 }

--------------------------------------------------------------------------------
-- WTOCMF Optical Port Config Table
--------------------------------------------------------------------------------
    tnWtocmfPortConfigTable OBJECT-TYPE
        SYNTAX         SEQUENCE OF TnWtocmfPortConfigEntry
        MAX-ACCESS     not-accessible
        STATUS         current
        DESCRIPTION    "The ports on a WTOCMF optical card."
        ::= { tnOpticalPortConfig 284 }

    tnWtocmfPortConfigEntry OBJECT-TYPE
        SYNTAX         TnWtocmfPortConfigEntry
        MAX-ACCESS     not-accessible
        STATUS         current
        DESCRIPTION    "."
        INDEX { ifIndex }
        ::= { tnWtocmfPortConfigTable 1 }

    TnWtocmfPortConfigEntry ::=
        SEQUENCE {
            tnWtocmfPortConfigFunction  INTEGER
        }

    tnWtocmfPortConfigFunction OBJECT-TYPE
        SYNTAX         INTEGER {
                         detect(1)
                       }
        MAX-ACCESS     read-only
        STATUS         current
        DESCRIPTION    "Indicates the functional type of this WTOCMF port."
        ::= { tnWtocmfPortConfigEntry 1 }

--------------------------------------------------------------------------------
-- ASWG Optical Port Config Scalar
--------------------------------------------------------------------------------
    tnAswgPortConfigAttributeTotal OBJECT-TYPE
        SYNTAX         Integer32
        MAX-ACCESS     read-only
        STATUS         current
        DESCRIPTION    "."
        ::= { tnOpticalPortConfig 285 }

--------------------------------------------------------------------------------
-- ASWG Optical Port Config Table
--------------------------------------------------------------------------------
    tnAswgPortConfigTable OBJECT-TYPE
        SYNTAX         SEQUENCE OF TnAswgPortConfigEntry
        MAX-ACCESS     not-accessible
        STATUS         current
        DESCRIPTION    "The ports on an ASWG optical card."
        ::= { tnOpticalPortConfig 286 }

    tnAswgPortConfigEntry OBJECT-TYPE
        SYNTAX         TnAswgPortConfigEntry
        MAX-ACCESS     not-accessible
        STATUS         current
        DESCRIPTION    "."
        INDEX { ifIndex }
        ::= { tnAswgPortConfigTable 1 }

    TnAswgPortConfigEntry ::=
        SEQUENCE {
            tnAswgPortConfigFunction INTEGER
        }

    tnAswgPortConfigFunction OBJECT-TYPE
        SYNTAX         INTEGER {
                         lineIn(1),
                         otdrRx(2),
                         otdrTx(3),
                         lineOut(4),
                         oscSfp(5),
                         osc(6),
                         custLan(7),
                         inv(8)
                       }
        MAX-ACCESS     read-only
        STATUS         current
        DESCRIPTION    "Indicates the functional type of this ASWG port."
        ::= { tnAswgPortConfigEntry 1 }

--------------------------------------------------------------------------------
-- A4PSWG Optical Port Config Scalar
--------------------------------------------------------------------------------
    tnA4pswgPortConfigAttributeTotal OBJECT-TYPE
        SYNTAX         Integer32
        MAX-ACCESS     read-only
        STATUS         current
        DESCRIPTION    "."
        ::= { tnOpticalPortConfig 287 }

--------------------------------------------------------------------------------
-- A4PSWG Optical Port Config Table
--------------------------------------------------------------------------------
    tnA4pswgPortConfigTable OBJECT-TYPE
        SYNTAX         SEQUENCE OF TnA4pswgPortConfigEntry
        MAX-ACCESS     not-accessible
        STATUS         current
        DESCRIPTION    "The ports on an A4PSWG optical card."
        ::= { tnOpticalPortConfig 288 }

    tnA4pswgPortConfigEntry OBJECT-TYPE
        SYNTAX         TnA4pswgPortConfigEntry
        MAX-ACCESS     not-accessible
        STATUS         current
        DESCRIPTION    "."
        INDEX { ifIndex }
        ::= { tnA4pswgPortConfigTable 1 }

    TnA4pswgPortConfigEntry ::=
        SEQUENCE {
            tnA4pswgPortConfigFunction INTEGER
        }

    tnA4pswgPortConfigFunction OBJECT-TYPE
        SYNTAX         INTEGER {
                         lineIn(1),
                         otdrRx(2),
                         otdrTx(3),
                         lineOut(4),
                         oscSfp(5),
                         osc(6),
                         custLan(7)
                       }
        MAX-ACCESS     read-only
        STATUS         current
        DESCRIPTION    "Indicates the functional type of this A4PSWG port."
        ::= { tnA4pswgPortConfigEntry 1 }

--------------------------------------------------------------------------------
-- OTDR (Optical Time Domain Reflectometer) Optical Port Config Scalar
--------------------------------------------------------------------------------
    tnOtdrPortConfigAttributeTotal OBJECT-TYPE
        SYNTAX         Integer32
        MAX-ACCESS     read-only
        STATUS         current
        DESCRIPTION    "."
        ::= { tnOpticalPortConfig 289 }

--------------------------------------------------------------------------------
-- OTDR (Optical Time Domain Reflectometer) Optical Port Config Table
--------------------------------------------------------------------------------
    tnOtdrPortConfigTable OBJECT-TYPE
        SYNTAX         SEQUENCE OF TnOtdrPortConfigEntry
        MAX-ACCESS     not-accessible
        STATUS         current
        DESCRIPTION    "The ports on an OTDR optical card."
        ::= { tnOpticalPortConfig 290 }

    tnOtdrPortConfigEntry OBJECT-TYPE
        SYNTAX         TnOtdrPortConfigEntry
        MAX-ACCESS     not-accessible
        STATUS         current
        DESCRIPTION    "."
        INDEX { ifIndex }
        ::= { tnOtdrPortConfigTable 1 }

    TnOtdrPortConfigEntry ::=
        SEQUENCE {
            tnOtdrPortConfigFunction INTEGER,
            tnOtdrPortConfigConnAddress  Integer32
        }

    tnOtdrPortConfigFunction OBJECT-TYPE
        SYNTAX         INTEGER {
                         px(1)
                       }
        MAX-ACCESS     read-only
        STATUS         current
        DESCRIPTION    "Indicates the functional type of this OTDR port."
        ::= { tnOtdrPortConfigEntry 1 }

    tnOtdrPortConfigConnAddress OBJECT-TYPE
        SYNTAX         Integer32 (-1..2147483647)
        MAX-ACCESS     read-create
        STATUS         current
        DESCRIPTION    "Specifies the assigned LD port that
                        is connected to the OTDR port."
        ::= { tnOtdrPortConfigEntry 2 }

--------------------------------------------------------------------------------
-- WR20-TFM Optical Port Config Scalar
--------------------------------------------------------------------------------
    tnWr20tfmPortConfigAttributeTotal OBJECT-TYPE
        SYNTAX         Integer32
        MAX-ACCESS     read-only
        STATUS         current
        DESCRIPTION    "."
        ::= { tnOpticalPortConfig 291 }

--------------------------------------------------------------------------------
-- WR20-TFM Optical Port Config Table
--------------------------------------------------------------------------------
    tnWr20tfmPortConfigTable OBJECT-TYPE
        SYNTAX         SEQUENCE OF TnWr20tfmPortConfigEntry
        MAX-ACCESS     not-accessible
        STATUS         current
        DESCRIPTION    "The ports on a WR20-TFM optical card."
        ::= { tnOpticalPortConfig 292 }

    tnWr20tfmPortConfigEntry OBJECT-TYPE
        SYNTAX         TnWr20tfmPortConfigEntry
        MAX-ACCESS     not-accessible
        STATUS         current
        DESCRIPTION    "."
        INDEX { ifIndex }
        ::= { tnWr20tfmPortConfigTable 1 }

    TnWr20tfmPortConfigEntry ::=
        SEQUENCE {
            tnWr20tfmPortConfigFunction                        INTEGER,
            tnWr20tfmPortConfigDropInitTargetPower             Integer32,
            tnWr20tfmPortConfigExpressTargetPower              Integer32,
            tnWr20tfmPortConfigDropMaxTargetPower              Integer32,
            tnWr20tfmPortConfigDropMinTargetPower              Integer32,
--          obsolete
--          tnWr20tfmPortConfigExecuteForcedDropDisposition    TnCommand,
            tnWr20tfmPortConfigEndForcedDropDisposition        TnCommand,
--          obsolete
--          tnWr20tfmPortConfigExecuteForcedAddDisposition     TnCommand,
            tnWr20tfmPortConfigEndForcedAddDisposition         TnCommand,
            tnWr20tfmPortConfigForceAllchannelsDropDisposition AluWdmWRConfigAddDropDisposition,
            tnWr20tfmPortConfigForceAllchannelsAddDisposition  AluWdmWRConfigAddDropDisposition
        }

    tnWr20tfmPortConfigFunction OBJECT-TYPE
        SYNTAX         INTEGER {
                         signal(1),
                         adt(2),
                         ad(3),
                         inv(4),
                         mpoDropOut(5),
                         mpoAddIn(6)
                       }
        MAX-ACCESS     read-only
        STATUS         current
        DESCRIPTION    "Indicates the functional type of this WR20-TFM port."
        ::= { tnWr20tfmPortConfigEntry 1 }

    tnWr20tfmPortConfigDropInitTargetPower OBJECT-TYPE
        SYNTAX         Integer32 (-2000..0)
        UNITS          "mB"
        MAX-ACCESS     read-create
        STATUS         current
        DESCRIPTION    "The initial target power used for
                        dropped channels.

                        Current Configurable Range: -2000 to 0
                        and default is -1200."
        DEFVAL         { -1200 }
        ::= { tnWr20tfmPortConfigEntry 2 }

    tnWr20tfmPortConfigExpressTargetPower OBJECT-TYPE
        SYNTAX         Integer32 (-2000..300)
        UNITS          "mB"
        MAX-ACCESS     read-create
        STATUS         current
        DESCRIPTION    "The target power used to set drop
                        side WSS attenuation value for
                        expressed channels.

                        Current Configurable Range: -2000 to 300
                        and default is -700."
        DEFVAL         { -700 }
        ::= { tnWr20tfmPortConfigEntry 3 }

    tnWr20tfmPortConfigDropMaxTargetPower OBJECT-TYPE
        SYNTAX         Integer32 (-2000..0)
        UNITS          "mB"
        MAX-ACCESS     read-create
        STATUS         current
        DESCRIPTION    "Upper limit for SCOT drop target
                        adjustment loop.  For advanced
                        users only.

                        Current Configurable Range: -2000 to 0
                        and default is -1200."
        DEFVAL         { -1200 }
        ::= { tnWr20tfmPortConfigEntry 4 }

    tnWr20tfmPortConfigDropMinTargetPower OBJECT-TYPE
        SYNTAX         Integer32 (-2000..0)
        UNITS          "mB"
        MAX-ACCESS     read-create
        STATUS         current
        DESCRIPTION    "Lower limit for SCOT drop target
                        adjustment loop.  For advanced
                        users only.

                        Current Configurable Range: -2000 to 0
                        and default is -1400."
        DEFVAL         { -1400 }
        ::= { tnWr20tfmPortConfigEntry 5 }

--    obsolete
--    tnWr20tfmPortConfigExecuteForcedDropDisposition OBJECT-TYPE ::= { tnWr20tfmPortConfigEntry 6 }

    tnWr20tfmPortConfigEndForcedDropDisposition OBJECT-TYPE
        SYNTAX         TnCommand
        MAX-ACCESS     read-create
        STATUS         current
        DESCRIPTION    "Ends forced disposition in drop direction
                        of test channels.  All non-cross connected
                        channels are blocked.  For advanced users
                        only."
        DEFVAL         { noCmd }
        ::= { tnWr20tfmPortConfigEntry 7 }
--    obsolete
--    tnWr20tfmPortConfigExecuteForcedAddDisposition OBJECT-TYPE ::= { tnWr20tfmPortConfigEntry 8 }

    tnWr20tfmPortConfigEndForcedAddDisposition OBJECT-TYPE
        SYNTAX         TnCommand
        MAX-ACCESS     read-create
        STATUS         current
        DESCRIPTION    "Ends forced disposition in add direction of
                        test channels.  All non-cross connected
                        channels are blocked.  For advanced users
                        only."
        DEFVAL         { noCmd }
        ::= { tnWr20tfmPortConfigEntry 9 }

    tnWr20tfmPortConfigForceAllchannelsDropDisposition OBJECT-TYPE
        SYNTAX         AluWdmWRConfigAddDropDisposition
        MAX-ACCESS     read-create
        STATUS         current
        DESCRIPTION    "Set disposition of ALL channels to a given
                        AD/ADT port in drop direction. Use
                        tnWr20tfmPortConfigEndForcedDropDisposition
                        to cancel and revert to blocked.
                        This attribute returns to notForced when
                        force is ended."
        DEFVAL         { notForced }
        ::= { tnWr20tfmPortConfigEntry 10 }

    tnWr20tfmPortConfigForceAllchannelsAddDisposition OBJECT-TYPE
        SYNTAX         AluWdmWRConfigAddDropDisposition
        MAX-ACCESS     read-create
        STATUS         current
        DESCRIPTION    "Set disposition of ALL channels from a given
                        AD/ADT port in add direction.  Use
                        tnWr20tfmPortConfigEndForcedAddDisposition
                        to cancel and revert to blocked.
                        This attribute returns to notForced when
                        force is ended"
        DEFVAL         { notForced }
        ::= { tnWr20tfmPortConfigEntry 11 }

--------------------------------------------------------------------------------
-- AAR-8A Optical Port Config Scalar
--------------------------------------------------------------------------------
    tnAar8aPortConfigAttributeTotal OBJECT-TYPE
        SYNTAX         Integer32
        MAX-ACCESS     read-only
        STATUS         current
        DESCRIPTION    "."
        ::= { tnOpticalPortConfig 293 }

--------------------------------------------------------------------------------
-- AAR-8A Optical Port Config Table
--------------------------------------------------------------------------------
    tnAar8aPortConfigTable OBJECT-TYPE
        SYNTAX         SEQUENCE OF TnAar8aPortConfigEntry
        MAX-ACCESS     not-accessible
        STATUS         current
        DESCRIPTION    "The ports on an AAR-8A optical card."
        ::= { tnOpticalPortConfig 294 }

    tnAar8aPortConfigEntry OBJECT-TYPE
        SYNTAX         TnAar8aPortConfigEntry
        MAX-ACCESS     not-accessible
        STATUS         current
        DESCRIPTION    "."
        INDEX { ifIndex }
        ::= { tnAar8aPortConfigTable 1 }

    TnAar8aPortConfigEntry ::=
        SEQUENCE {
            tnAar8aPortConfigFunction   INTEGER
        }

    tnAar8aPortConfigFunction OBJECT-TYPE
        SYNTAX         INTEGER {
                         ampIn(1),
                         ampOut(2),
                         mpoFsm(3),
                         mpoMcs(4)
                       }
        MAX-ACCESS     read-only
        STATUS         current
        DESCRIPTION    "Indicates the functional type of this AAR-8A port."
        ::= { tnAar8aPortConfigEntry 1 }

--------------------------------------------------------------------------------
-- MCS8-16 Optical Port Config Scalar
--------------------------------------------------------------------------------
    tnMcs8x16PortConfigAttributeTotal OBJECT-TYPE
        SYNTAX         Integer32
        MAX-ACCESS     read-only
        STATUS         current
        DESCRIPTION    "."
        ::= { tnOpticalPortConfig 295 }

--------------------------------------------------------------------------------
-- MCS8-16 Optical Port Config Table
--------------------------------------------------------------------------------
    tnMcs8x16PortConfigTable OBJECT-TYPE
        SYNTAX         SEQUENCE OF TnMcs8x16PortConfigEntry
        MAX-ACCESS     not-accessible
        STATUS         current
        DESCRIPTION    "The ports on a MCS8-16 optical card."
        ::= { tnOpticalPortConfig 296 }

    tnMcs8x16PortConfigEntry OBJECT-TYPE
        SYNTAX         TnMcs8x16PortConfigEntry
        MAX-ACCESS     not-accessible
        STATUS         current
        DESCRIPTION    "."
        INDEX { ifIndex }
        ::= { tnMcs8x16PortConfigTable 1 }

    TnMcs8x16PortConfigEntry ::=
        SEQUENCE {
            tnMcs8x16PortConfigFunction   INTEGER
        }

    tnMcs8x16PortConfigFunction OBJECT-TYPE
        SYNTAX         INTEGER {
                         signal(1),
                         ad(2),
                         mpoAar(3)
                       }
        MAX-ACCESS     read-only
        STATUS         current
        DESCRIPTION    "Indicates the functional type of this MCS8-16 port."
        ::= { tnMcs8x16PortConfigEntry 1 }

--------------------------------------------------------------------------------
-- MSH8-FSM Optical Port Config Scalar
--------------------------------------------------------------------------------
    tnMsh8fsmPortConfigAttributeTotal OBJECT-TYPE
        SYNTAX         Integer32
        MAX-ACCESS     read-only
        STATUS         current
        DESCRIPTION    "."
        ::= { tnOpticalPortConfig 297 }

--------------------------------------------------------------------------------
-- MSH8-FSM Optical Port Config Table
--------------------------------------------------------------------------------
    tnMsh8fsmPortConfigTable OBJECT-TYPE
        SYNTAX         SEQUENCE OF TnMsh8fsmPortConfigEntry
        MAX-ACCESS     not-accessible
        STATUS         current
        DESCRIPTION    "The ports on a MSH8-FSM optical card."
        ::= { tnOpticalPortConfig 298 }

    tnMsh8fsmPortConfigEntry OBJECT-TYPE
        SYNTAX         TnMsh8fsmPortConfigEntry
        MAX-ACCESS     not-accessible
        STATUS         current
        DESCRIPTION    "."
        INDEX { ifIndex }
        ::= { tnMsh8fsmPortConfigTable 1 }

    TnMsh8fsmPortConfigEntry ::=
        SEQUENCE {
            tnMsh8fsmPortConfigFunction   INTEGER
        }

    tnMsh8fsmPortConfigFunction OBJECT-TYPE
        SYNTAX         INTEGER {
                         mpoWssDropIn(1),
                         mpoWssAddOut(2),
                         mpoWssAd(3),
                         expIn(4),
                         expOut(5)
                       }
        MAX-ACCESS     read-only
        STATUS         current
        DESCRIPTION    "Indicates the functional type of this MSH8-FSM port."
        ::= { tnMsh8fsmPortConfigEntry 1 }

--------------------------------------------------------------------------------
-- Multi Cast Switch(MCS) Port Config Scalar
--------------------------------------------------------------------------------
    tnMcsPortConfigAttributeTotal OBJECT-TYPE
        SYNTAX         Integer32
        MAX-ACCESS     read-only
        STATUS         current
        DESCRIPTION    "."
        ::= { tnOpticalPortConfig 299 }

--------------------------------------------------------------------------------
-- Multi Cast Switch(MCS) Port Config Table
--------------------------------------------------------------------------------
    tnMcsPortConfigTable OBJECT-TYPE
        SYNTAX         SEQUENCE OF TnMcsPortConfigEntry
        MAX-ACCESS     not-accessible
        STATUS         current
        DESCRIPTION    "MCS configurable force disposition
                        attributes."
        ::= { tnOpticalPortConfig 300 }

    tnMcsPortConfigEntry OBJECT-TYPE
        SYNTAX         TnMcsPortConfigEntry
        MAX-ACCESS     not-accessible
        STATUS         current
        DESCRIPTION    "."
        INDEX { ifIndex }
        ::= { tnMcsPortConfigTable 1 }

    TnMcsPortConfigEntry ::=
        SEQUENCE {
            tnMcsPortConfigTargetForDispositionForce       INTEGER,
            tnMcsPortConfigExecuteForceDispositionToTarget INTEGER
        }

    tnMcsPortConfigTargetForDispositionForce OBJECT-TYPE
        SYNTAX         INTEGER {
                         blocked(1),
                         sig1(2),
                         sig2(3),
                         sig3(4),
                         sig4(5),
                         sig5(6),
                         sig6(7),
                         sig7(8),
                         sig8(9),
                         sig9(10),
                         sig10(11),
                         sig11(12),
                         sig12(13),
                         sig13(14),
                         sig14(15),
                         sig15(16),
                         sig16(17)
                       }
        MAX-ACCESS     read-create
        STATUS         current
        DESCRIPTION    "Set desired target routing for forcing disposition
                        of add and drop directions to given port.  Use
                        tnMcsPortConfigExecuteForceDispositionToTarget
                        to execute switch to this targeted routing."
        DEFVAL         { blocked }
        ::= { tnMcsPortConfigEntry 1 }

    tnMcsPortConfigExecuteForceDispositionToTarget OBJECT-TYPE
        SYNTAX         INTEGER {
                         noCmd(1),
                         execute(2)
                       }
        MAX-ACCESS     read-create
        STATUS         current
        DESCRIPTION    "Use Execute to force add and drop
                        disposition to the value given in
                        tnMcsPortConfigTargetForDispositionForce.
                        Only allowed if no cross-connects
                        are using target disposition."
        DEFVAL         { noCmd }
        ::= { tnMcsPortConfigEntry 2 }

--------------------------------------------------------------------------------
-- Amplifier ARray (AAR) Port Config Scalar
--------------------------------------------------------------------------------
    tnAarPortConfigAttributeTotal OBJECT-TYPE
        SYNTAX         Integer32
        MAX-ACCESS     read-only
        STATUS         current
        DESCRIPTION    "."
        ::= { tnOpticalPortConfig 301 }

--------------------------------------------------------------------------------
-- Amplifier ARray (AAR) Port Config Table
--------------------------------------------------------------------------------
    tnAarPortConfigTable OBJECT-TYPE
        SYNTAX         SEQUENCE OF TnAarPortConfigEntry
        MAX-ACCESS     not-accessible
        STATUS         current
        DESCRIPTION    "The optical amplifier array card configurable
                        attributes."
        ::= { tnOpticalPortConfig 302 }

    tnAarPortConfigEntry OBJECT-TYPE
        SYNTAX         TnAarPortConfigEntry
        MAX-ACCESS     not-accessible
        STATUS         current
        DESCRIPTION    "."
        INDEX { ifIndex }
        ::= { tnAarPortConfigTable 1 }

    TnAarPortConfigEntry ::=
        SEQUENCE {
            tnAarPortConfigOperatingMode                          INTEGER,
            tnAarPortConfigPowerGainTarget                        Unsigned32,
            tnAarPortConfigSignalPowerTarget                      Integer32,
            tnAarPortConfigOaInputChannelPowerTargetSpecified     Integer32,
            tnAarPortConfigOaInputChannelPowerTargetActive        Integer32
        }

    tnAarPortConfigOperatingMode OBJECT-TYPE
        SYNTAX         INTEGER {
                         power(1),
                         gain(2),
                         disabled(3)
                       }
        MAX-ACCESS     read-create
        STATUS         current
        DESCRIPTION    "Configures the amplifier operating mode:

                        power:    constant signal output power.
                        gain:     constant signal gain.
                        disabled: pumps are powered down.

                        Only users operating the amplifier for test purposes
                        should set this attribute."
        DEFVAL         { disabled }
        ::= { tnAarPortConfigEntry 1 }

    tnAarPortConfigPowerGainTarget OBJECT-TYPE
        SYNTAX         Unsigned32 (1000..2000)
        UNITS          "mB"
        MAX-ACCESS     read-create
        STATUS         current
        DESCRIPTION    "Configures the gain setting for signal gain.  The
                        operating mode tnAarPortConfigOperatingMode must be
                        configured to Gain prior to setting the gain.  Only
                        use for test purposes.

                        Current configurable range: 1000 to 2000."
        DEFVAL         { 1500 }
        ::= { tnAarPortConfigEntry 2 }

    tnAarPortConfigSignalPowerTarget OBJECT-TYPE
        SYNTAX         Integer32 (-500..1000)
        UNITS          "mB"
        MAX-ACCESS     read-create
        STATUS         current
        DESCRIPTION    "Configures the power setting for signal output power
                        in power mode.  The operating mode
                        tnAarPortConfigOperatingMode must be configured to
                        Power prior to setting the power.  Only use for test
                        purposes.

                        Current configurable range: -500 to 1000."
        DEFVAL         { 300 }
        ::= { tnAarPortConfigEntry 3 }

    tnAarPortConfigOaInputChannelPowerTargetSpecified OBJECT-TYPE
        SYNTAX         Integer32 (-9900..-1600)
        UNITS          "mBm"
        MAX-ACCESS     read-create
        STATUS         current
        DESCRIPTION    "Defined per channel target input power for add amplifier.
                        When configured, system will use this target power.

                        Current configurable range: -9900 to -1600."
        DEFVAL         { -9900 }
        ::= { tnAarPortConfigEntry 4 }

    tnAarPortConfigOaInputChannelPowerTargetActive OBJECT-TYPE
        SYNTAX         Integer32 (-2450..-1400)
        UNITS          "mBm"
        MAX-ACCESS     read-create
        STATUS         current
        DESCRIPTION    "Target input power per channel for add amplifier
                        currently used by the system software.The value may
                        vary as the system software makes adjustments.

                        Current configurable range: -2450 to -1400."
        DEFVAL         { -1900 }
        ::= { tnAarPortConfigEntry 5 }

--------------------------------------------------------------------------------
-- WR20-TFM Port Channel Config Scalars
--------------------------------------------------------------------------------
    tnWr20tfmPortChannelConfigAttributeTotal OBJECT-TYPE
        SYNTAX         Integer32
        MAX-ACCESS     read-only
        STATUS         current
        DESCRIPTION    "."
        ::= { tnOpticalPortConfig 303 }

--------------------------------------------------------------------------------
-- WR20-TFM Port Channel Config Table
--------------------------------------------------------------------------------
    tnWr20tfmPortChannelConfigTable OBJECT-TYPE
        SYNTAX         SEQUENCE OF TnWr20tfmPortChannelConfigEntry
        MAX-ACCESS     not-accessible
        STATUS         current
        DESCRIPTION    "Set target port for add/drop disposition force for test
                        channel(s) on a WR20-TFM card."
        ::= { tnOpticalPortConfig 304 }

    tnWr20tfmPortChannelConfigEntry OBJECT-TYPE
        SYNTAX         TnWr20tfmPortChannelConfigEntry
        MAX-ACCESS     not-accessible
        STATUS         current
        DESCRIPTION    "."
        INDEX { ifIndex,
                tnChannel }
        ::= { tnWr20tfmPortChannelConfigTable 1 }

    TnWr20tfmPortChannelConfigEntry ::=
        SEQUENCE {
            tnWr20tfmPortChannelConfigTargetForcedDropDisposition     AluWdmWRConfigAddDropDisposition,
            tnWr20tfmPortChannelConfigTargetForcedAddDisposition      AluWdmWRConfigAddDropDisposition
        }

    tnWr20tfmPortChannelConfigTargetForcedDropDisposition OBJECT-TYPE
        SYNTAX         AluWdmWRConfigAddDropDisposition
        MAX-ACCESS     read-create
        STATUS         current
        DESCRIPTION    "Target port to drop test channel(s) to.
                        Use tnWr20tfmPortConfigExecuteForcedDropDisposition
                        attribute to execute.  Note only one port
                        can be used at a time in this mode.
                        For advanced users only.

                        Not supported in current(7.0.2) release."
        DEFVAL         { notForced }
        ::= { tnWr20tfmPortChannelConfigEntry 1 }

    tnWr20tfmPortChannelConfigTargetForcedAddDisposition OBJECT-TYPE
        SYNTAX         AluWdmWRConfigAddDropDisposition
        MAX-ACCESS     read-create
        STATUS         current
        DESCRIPTION    "Target port to add test channel(s) from.
                        Use tnWr20tfmPortConfigExecuteForcedAddDisposition
                        attribute to execute.  Note only one port
                        can be used at a time in this mode.
                        For advanced users only.

                        Not supported in current(7.0.2) release."
        DEFVAL         { notForced }
        ::= { tnWr20tfmPortChannelConfigEntry 2 }

--------------------------------------------------------------------------------
-- MPO Port Config Scalar
--------------------------------------------------------------------------------
    tnMpoPortConfigAttributeTotal OBJECT-TYPE
        SYNTAX         Integer32
        MAX-ACCESS     read-only
        STATUS         current
        DESCRIPTION    "."
        ::= { tnOpticalPortConfig 305 }

--------------------------------------------------------------------------------
-- MPO Optical Port Config Table
--------------------------------------------------------------------------------
    tnMpoPortConfigTable OBJECT-TYPE
        SYNTAX         SEQUENCE OF TnMpoPortConfigEntry
        MAX-ACCESS     not-accessible
        STATUS         current
        DESCRIPTION    "MPO port details"
        ::= { tnOpticalPortConfig 306 }

    tnMpoPortConfigEntry OBJECT-TYPE
        SYNTAX         TnMpoPortConfigEntry
        MAX-ACCESS     not-accessible
        STATUS         current
        DESCRIPTION    "."
        INDEX { ifIndex }
        ::= { tnMpoPortConfigTable 1 }

    TnMpoPortConfigEntry ::=
        SEQUENCE {
            tnMpoPortConfigFarEndIfIndex InterfaceIndexOrZero,
            tnMpoPortConfigFarEndType    INTEGER,
            tnMpoPortConfigDescription   SnmpAdminString
        }

    tnMpoPortConfigFarEndIfIndex OBJECT-TYPE
        SYNTAX         InterfaceIndexOrZero
        MAX-ACCESS     read-create
        STATUS         current
        DESCRIPTION    "Connects the multi-fiber port to a far end
                        multi-fiber port if not connected.  View
                        the current far end multi-fiber port if
                        connected and 0 if not connected."
        DEFVAL         { 0 }
        ::= { tnMpoPortConfigEntry 1 }

    tnMpoPortConfigFarEndType OBJECT-TYPE
        SYNTAX         INTEGER {
                         notConnected(1),
                         internal(2)
                       }
        MAX-ACCESS     read-create
        STATUS         current
        DESCRIPTION    "The type of multi-fiber port connection.
                        notConnected(1): The port is not
                        connected.
                        internal(2): The port is internally
                        connected."
        DEFVAL         { notConnected }
        ::= { tnMpoPortConfigEntry 2 }

    tnMpoPortConfigDescription OBJECT-TYPE
        SYNTAX         SnmpAdminString
        MAX-ACCESS     read-create
        STATUS         current
        DESCRIPTION    "Configures the description of the
                        multi-fiber port.  Default is the
                        port name."
        DEFVAL         { "" }
        ::= { tnMpoPortConfigEntry 3 }

--------------------------------------------------------------------------------
-- 4AN100G Optical Port Config Scalar
--------------------------------------------------------------------------------
    tnIo4an100gPortConfigAttributeTotal OBJECT-TYPE
        SYNTAX         Integer32
        MAX-ACCESS     read-only
        STATUS         current
        DESCRIPTION    "."
        ::= { tnOpticalPortConfig 307 }

--------------------------------------------------------------------------------
-- 4AN100G Optical Port Config Table
--------------------------------------------------------------------------------
    tnIo4an100gPortConfigTable OBJECT-TYPE
        SYNTAX         SEQUENCE OF TnIo4an100gPortConfigEntry
        MAX-ACCESS     not-accessible
        STATUS         current
        DESCRIPTION    "The ports on a 4AN100G optical card."
        ::= { tnOpticalPortConfig 308 }

    tnIo4an100gPortConfigEntry OBJECT-TYPE
        SYNTAX         TnIo4an100gPortConfigEntry
        MAX-ACCESS     not-accessible
        STATUS         current
        DESCRIPTION    "."
        INDEX { ifIndex }
        ::= { tnIo4an100gPortConfigTable 1 }

    TnIo4an100gPortConfigEntry ::=
        SEQUENCE {
            tnIo4an100gPortConfigFunction  INTEGER
        }

    tnIo4an100gPortConfigFunction OBJECT-TYPE
        SYNTAX         INTEGER {
                         client(1)
                       }
        MAX-ACCESS     read-only
        STATUS         current
        DESCRIPTION    "Indicates the functional type of this 4AN100G port."
        ::= { tnIo4an100gPortConfigEntry 1 }

--------------------------------------------------------------------------------
-- 30AN10G Optical Port Config Scalar
--------------------------------------------------------------------------------
    tnIo30an10gPortConfigAttributeTotal OBJECT-TYPE
        SYNTAX         Integer32
        MAX-ACCESS     read-only
        STATUS         current
        DESCRIPTION    "."
        ::= { tnOpticalPortConfig 309 }

--------------------------------------------------------------------------------
-- 30AN10G Optical Port Config Table
--------------------------------------------------------------------------------
    tnIo30an10gPortConfigTable OBJECT-TYPE
        SYNTAX         SEQUENCE OF TnIo30an10gPortConfigEntry
        MAX-ACCESS     not-accessible
        STATUS         current
        DESCRIPTION    "The ports on a 30AN10G optical card."
        ::= { tnOpticalPortConfig 310 }

    tnIo30an10gPortConfigEntry OBJECT-TYPE
        SYNTAX         TnIo30an10gPortConfigEntry
        MAX-ACCESS     not-accessible
        STATUS         current
        DESCRIPTION    "."
        INDEX { ifIndex }
        ::= { tnIo30an10gPortConfigTable 1 }

    TnIo30an10gPortConfigEntry ::=
        SEQUENCE {
            tnIo30an10gPortConfigFunction  INTEGER
        }

    tnIo30an10gPortConfigFunction OBJECT-TYPE
        SYNTAX         INTEGER {
                         client(1)
                       }
        MAX-ACCESS     read-only
        STATUS         current
        DESCRIPTION    "Indicates the functional type of this 30AN10G port."
        ::= { tnIo30an10gPortConfigEntry 1 }

--------------------------------------------------------------------------------
-- 30AN300 Optical Port Config Scalar
--------------------------------------------------------------------------------
    tnIo30an300PortConfigAttributeTotal OBJECT-TYPE
        SYNTAX         Integer32
        MAX-ACCESS     read-only
        STATUS         current
        DESCRIPTION    "."
        ::= { tnOpticalPortConfig 311 }

--------------------------------------------------------------------------------
-- 30AN300 Optical Port Config Table
--------------------------------------------------------------------------------
    tnIo30an300PortConfigTable OBJECT-TYPE
        SYNTAX         SEQUENCE OF TnIo30an300PortConfigEntry
        MAX-ACCESS     not-accessible
        STATUS         current
        DESCRIPTION    "The ports on a 30AN300 optical card."
        ::= { tnOpticalPortConfig 312 }

    tnIo30an300PortConfigEntry OBJECT-TYPE
        SYNTAX         TnIo30an300PortConfigEntry
        MAX-ACCESS     not-accessible
        STATUS         current
        DESCRIPTION    "."
        INDEX { ifIndex }
        ::= { tnIo30an300PortConfigTable 1 }

    TnIo30an300PortConfigEntry ::=
        SEQUENCE {
            tnIo30an300PortConfigFunction  INTEGER
        }

    tnIo30an300PortConfigFunction OBJECT-TYPE
        SYNTAX         INTEGER {
                         client(1)
                       }
        MAX-ACCESS     read-only
        STATUS         current
        DESCRIPTION    "Indicates the functional type of this 30AN300 port."
        ::= { tnIo30an300PortConfigEntry 1 }

--------------------------------------------------------------------------------
-- 4AN400 Optical Port Config Scalar
--------------------------------------------------------------------------------
    tnIo4an400PortConfigAttributeTotal OBJECT-TYPE
        SYNTAX         Integer32
        MAX-ACCESS     read-only
        STATUS         current
        DESCRIPTION    "."
        ::= { tnOpticalPortConfig 313 }

--------------------------------------------------------------------------------
-- 4AN400 Optical Port Config Table
--------------------------------------------------------------------------------
    tnIo4an400PortConfigTable OBJECT-TYPE
        SYNTAX         SEQUENCE OF TnIo4an400PortConfigEntry
        MAX-ACCESS     not-accessible
        STATUS         current
        DESCRIPTION    "The ports on a 4AN400 optical card."
        ::= { tnOpticalPortConfig 314 }

    tnIo4an400PortConfigEntry OBJECT-TYPE
        SYNTAX         TnIo4an400PortConfigEntry
        MAX-ACCESS     not-accessible
        STATUS         current
        DESCRIPTION    "."
        INDEX { ifIndex }
        ::= { tnIo4an400PortConfigTable 1 }

    TnIo4an400PortConfigEntry ::=
        SEQUENCE {
            tnIo4an400PortConfigFunction  INTEGER
        }

    tnIo4an400PortConfigFunction OBJECT-TYPE
        SYNTAX         INTEGER {
                         client(1)
                       }
        MAX-ACCESS     read-only
        STATUS         current
        DESCRIPTION    "Indicates the functional type of this 4AN400 port."
        ::= { tnIo4an400PortConfigEntry 1 }

--------------------------------------------------------------------------------
-- 12P120 Optical Port Config Scalar
--------------------------------------------------------------------------------
    tn12p120PortConfigAttributeTotal OBJECT-TYPE
        SYNTAX         Integer32
        MAX-ACCESS     read-only
        STATUS         current
        DESCRIPTION    "."
        ::= { tnOpticalPortConfig 315 }

--------------------------------------------------------------------------------
-- 12P120 Optical Port Config Table
--------------------------------------------------------------------------------
    tn12p120PortConfigTable OBJECT-TYPE
        SYNTAX         SEQUENCE OF Tn12p120PortConfigEntry
        MAX-ACCESS     not-accessible
        STATUS         current
        DESCRIPTION    "The ports on a 12P120 optical card."
        ::= { tnOpticalPortConfig 316 }

    tn12p120PortConfigEntry OBJECT-TYPE
        SYNTAX         Tn12p120PortConfigEntry
        MAX-ACCESS     not-accessible
        STATUS         current
        DESCRIPTION    "."
        INDEX { ifIndex }
        ::= { tn12p120PortConfigTable 1 }

    Tn12p120PortConfigEntry ::=
        SEQUENCE {
            tn12p120PortConfigFunction  INTEGER
        }

    tn12p120PortConfigFunction OBJECT-TYPE
        SYNTAX         INTEGER {
                         network(1),
                         client(2),
                         evoa(3),
                         backplane(4)
                       }
        MAX-ACCESS     read-only
        STATUS         current
        DESCRIPTION    "Indicates the functional type of this 12P120 port."
        ::= { tn12p120PortConfigEntry 1 }

--------------------------------------------------------------------------------
-- 20P200 Optical Port Config Scalar
--------------------------------------------------------------------------------
    tn20p200PortConfigAttributeTotal OBJECT-TYPE
        SYNTAX         Integer32
        MAX-ACCESS     read-only
        STATUS         current
        DESCRIPTION    "."
        ::= { tnOpticalPortConfig 317 }

--------------------------------------------------------------------------------
-- 20P200 Optical Port Config Table
--------------------------------------------------------------------------------
    tn20p200PortConfigTable OBJECT-TYPE
        SYNTAX         SEQUENCE OF Tn20p200PortConfigEntry
        MAX-ACCESS     not-accessible
        STATUS         current
        DESCRIPTION    "The ports on a 20P200 optical card."
        ::= { tnOpticalPortConfig 318 }

    tn20p200PortConfigEntry OBJECT-TYPE
        SYNTAX         Tn20p200PortConfigEntry
        MAX-ACCESS     not-accessible
        STATUS         current
        DESCRIPTION    "."
        INDEX { ifIndex }
        ::= { tn20p200PortConfigTable 1 }

    Tn20p200PortConfigEntry ::=
        SEQUENCE {
            tn20p200PortConfigFunction  INTEGER
        }

    tn20p200PortConfigFunction OBJECT-TYPE
        SYNTAX         INTEGER {
                         network(1),
                         client(2),
                         backplane(3)
                       }
        MAX-ACCESS     read-only
        STATUS         current
        DESCRIPTION    "Indicates the functional type of this 20P200 port."
        ::= { tn20p200PortConfigEntry 1 }

--------------------------------------------------------------------------------
-- 1UD200 Optical Port Config Scalar
--------------------------------------------------------------------------------
    tn1ud200PortConfigAttributeTotal OBJECT-TYPE
        SYNTAX         Integer32
        MAX-ACCESS     read-only
        STATUS         current
        DESCRIPTION    "."
        ::= { tnOpticalPortConfig 319 }

--------------------------------------------------------------------------------
-- 1UD200 Optical Port Config Table
--------------------------------------------------------------------------------
    tn1ud200PortConfigTable OBJECT-TYPE
        SYNTAX         SEQUENCE OF Tn1ud200PortConfigEntry
        MAX-ACCESS     not-accessible
        STATUS         current
        DESCRIPTION    "The ports on a 1UD200 optical card."
        ::= { tnOpticalPortConfig 320 }

    tn1ud200PortConfigEntry OBJECT-TYPE
        SYNTAX         Tn1ud200PortConfigEntry
        MAX-ACCESS     not-accessible
        STATUS         current
        DESCRIPTION    "."
        INDEX { ifIndex }
        ::= { tn1ud200PortConfigTable 1 }

    Tn1ud200PortConfigEntry ::=
        SEQUENCE {
            tn1ud200PortConfigFunction  INTEGER
        }

    tn1ud200PortConfigFunction OBJECT-TYPE
        SYNTAX         INTEGER {
                         network(1),
                         backplane(2)
                       }
        MAX-ACCESS     read-only
        STATUS         current
        DESCRIPTION    "Indicates the functional type of this 1UD200 port."
        ::= { tn1ud200PortConfigEntry 1 }

--------------------------------------------------------------------------------
-- OT130SNQ10 Optical Port Config Scalar
--------------------------------------------------------------------------------
    tnOt130snq10PortConfigAttributeTotal OBJECT-TYPE
        SYNTAX         Integer32
        MAX-ACCESS     read-only
        STATUS         current
        DESCRIPTION    "."
        ::= { tnOpticalPortConfig 321 }

--------------------------------------------------------------------------------
-- OT130SNQ10 Optical Port Config Table
--------------------------------------------------------------------------------
    tnOt130snq10PortConfigTable OBJECT-TYPE
        SYNTAX         SEQUENCE OF TnOt130snq10PortConfigEntry
        MAX-ACCESS     not-accessible
        STATUS         current
        DESCRIPTION    "The ports on a OT130SNQ10 optical card."
        ::= { tnOpticalPortConfig 322 }

    tnOt130snq10PortConfigEntry OBJECT-TYPE
        SYNTAX         TnOt130snq10PortConfigEntry
        MAX-ACCESS     not-accessible
        STATUS         current
        DESCRIPTION    "."
        INDEX { ifIndex }
        ::= { tnOt130snq10PortConfigTable 1 }

    TnOt130snq10PortConfigEntry ::=
        SEQUENCE {
            tnOt130snq10PortConfigFunction  INTEGER
        }

    tnOt130snq10PortConfigFunction OBJECT-TYPE
        SYNTAX         INTEGER {
                         network(1),
                         client(2)
                       }
        MAX-ACCESS     read-only
        STATUS         current
        DESCRIPTION    "Indicates the functional type of this OT130SNQ10 port."
        ::= { tnOt130snq10PortConfigEntry 1 }

--------------------------------------------------------------------------------
-- IROADMV Optical Port Config Scalar
--------------------------------------------------------------------------------
    tnIroadmvPortConfigAttributeTotal OBJECT-TYPE
        SYNTAX         Integer32
        MAX-ACCESS     read-only
        STATUS         current
        DESCRIPTION    "."
        ::= { tnOpticalPortConfig 323 }

--------------------------------------------------------------------------------
-- IROADMV Optical Port Config Table
--------------------------------------------------------------------------------
    tnIroadmvPortConfigTable OBJECT-TYPE
        SYNTAX         SEQUENCE OF TnIroadmvPortConfigEntry
        MAX-ACCESS     not-accessible
        STATUS         current
        DESCRIPTION    "The ports on a IROADMV optical card."
        ::= { tnOpticalPortConfig 324 }

    tnIroadmvPortConfigEntry OBJECT-TYPE
        SYNTAX         TnIroadmvPortConfigEntry
        MAX-ACCESS     not-accessible
        STATUS         current
        DESCRIPTION    "."
        INDEX { ifIndex }
        ::= { tnIroadmvPortConfigTable 1 }

    TnIroadmvPortConfigEntry ::=
        SEQUENCE {
            tnIroadmvPortConfigFunction           INTEGER
        }

    tnIroadmvPortConfigFunction OBJECT-TYPE
        SYNTAX         INTEGER {
                         lineIn(1),
                         inv(2),
                         osc(3),
                         lineOut(4),
                         oscSfp(5),
                         adt(6),
                         dcm(7),
                         custLan(8)
                       }
        MAX-ACCESS     read-only
        STATUS         current
        DESCRIPTION    "Indicates the functional type of this IROADMV port."
        ::= { tnIroadmvPortConfigEntry 1 }

--------------------------------------------------------------------------------
-- IROADMF Optical Port Config Scalar
--------------------------------------------------------------------------------
    tnIroadmfPortConfigAttributeTotal OBJECT-TYPE
        SYNTAX         Integer32
        MAX-ACCESS     read-only
        STATUS         current
        DESCRIPTION    "."
        ::= { tnOpticalPortConfig 325 }

--------------------------------------------------------------------------------
-- IROADMF Optical Port Config Table
--------------------------------------------------------------------------------
    tnIroadmfPortConfigTable OBJECT-TYPE
        SYNTAX         SEQUENCE OF TnIroadmfPortConfigEntry
        MAX-ACCESS     not-accessible
        STATUS         current
        DESCRIPTION    "The ports on a IROADMF optical card."
        ::= { tnOpticalPortConfig 326 }

    tnIroadmfPortConfigEntry OBJECT-TYPE
        SYNTAX         TnIroadmfPortConfigEntry
        MAX-ACCESS     not-accessible
        STATUS         current
        DESCRIPTION    "."
        INDEX { ifIndex }
        ::= { tnIroadmfPortConfigTable 1 }

    TnIroadmfPortConfigEntry ::=
        SEQUENCE {
            tnIroadmfPortConfigFunction  INTEGER
        }

    tnIroadmfPortConfigFunction OBJECT-TYPE
        SYNTAX         INTEGER {
                         lineIn(1),
                         inv(2),
                         osc(3),
                         lineOut(4),
                         oscSfp(5),
                         adt(6),
                         custLan(7)
                       }
        MAX-ACCESS     read-only
        STATUS         current
        DESCRIPTION    "Indicates the functional type of this IROADMF port."
        ::= { tnIroadmfPortConfigEntry 1 }

--------------------------------------------------------------------------------
-- IROADM Optical Port Config Scalar
--------------------------------------------------------------------------------
    tnIroadmPortConfigAttributeTotal OBJECT-TYPE
        SYNTAX         Integer32
        MAX-ACCESS     read-only
        STATUS         current
        DESCRIPTION    "Total no of attributes in
                        tnIroadmPortConfigTable."
        ::= { tnOpticalPortConfig 327 }

--------------------------------------------------------------------------------
-- IROADM Optical Port Config Table
--------------------------------------------------------------------------------
    tnIroadmPortConfigTable OBJECT-TYPE
        SYNTAX         SEQUENCE OF TnIroadmPortConfigEntry
        MAX-ACCESS     not-accessible
        STATUS         current
        DESCRIPTION    "Attributes related to IROADM optical cards."
        ::= { tnOpticalPortConfig 328 }

    tnIroadmPortConfigEntry OBJECT-TYPE
        SYNTAX         TnIroadmPortConfigEntry
        MAX-ACCESS     not-accessible
        STATUS         current
        DESCRIPTION    "."
        INDEX { ifIndex }
        ::= { tnIroadmPortConfigTable 1 }

    TnIroadmPortConfigEntry ::=
        SEQUENCE {
            tnIroadmPortConfigPowerGain                Unsigned32,
            tnIroadmPortConfigPowerGainBackoff         Unsigned32,
            tnIroadmPortConfigTargetTilt               Integer32,
            tnIroadmPortConfigVoaSet                   Unsigned32,
            tnIroadmPortConfigNominalSpanLossOut       Integer32,
            tnIroadmPortConfigFiberTypeOut             INTEGER,
            tnIroadmPortConfigFiberLengthKm            Unsigned32,
            tnIroadmPortConfigAddMinChannelPower       Integer32,
            tnIroadmPortConfigEgressOaRippleToRemove   Unsigned32,
            tnIroadmPortConfigExpressMinChannelPower   Integer32,
            tnIroadmPortConfigIngressOaGainMin         Unsigned32,
            tnIroadmPortConfigIngressOaGainMax         Unsigned32,
            tnIroadmPortConfigTargetPpcOut             Integer32,
            tnIroadmPortConfigIngressOaTargetPpcOut    Integer32,
            tnIroadmPortConfigIngressOaTargetPpcAdj    Integer32,
            tnIroadmPortConfigSignalFailThreshold      Unsigned32,
            tnIroadmPortConfigSignalDegradeThreshold   Unsigned32,
            tnIroadmPortConfigAprDisable               TruthValue,
            tnIroadmPortConfigForcedTargetPpcOut       Integer32,
            tnIroadmPortConfigLineDcmConnAddress       InterfaceIndexOrZero,
            tnIroadmPortConfigAprMode                  INTEGER,
            tnIroadmPortConfigGainRange                INTEGER,
            tnIroadmPortConfigOSCVoaAtten              Unsigned32,
            tnIroadmPortConfigDropMaxTargetPower       Integer32,
            tnIroadmPortConfigDropMinTargetPower       Integer32,
            tnIroadmPortConfigDropInitTargetPower      Integer32,
            tnIroadmPortConfigDropExpressTargetPower   Integer32,
            tnIroadmPortConfigGainRangeL               INTEGER,
            tnIroadmPortConfigIngressOaTargetPpcOutL   Integer32,
            tnIroadmPortConfigPowerGainL               Unsigned32,
            tnIroadmPortConfigIngressOaGainMaxL        Unsigned32,
            tnIroadmPortConfigIngressOaGainMinL        Unsigned32,
            tnIroadmPortConfigTargetTiltL              Integer32,
            tnIroadmPortConfigVoaSetL                  Unsigned32,
            tnIroadmPortConfigTargetPpcOutL            Integer32,
            tnIroadmPortConfigAlienWaveBank            TruthValue,
            tnIroadmPortConfigSpanLossTh               Integer32,
            tnIroadmPortConfigAsellEnabled             TruthValue,
            tnIroadmPortConfigTargetPowerWidth         NokiaAmpPortTargetPowerWidth,
            tnIroadmPortConfigTargetPowerWidthL        NokiaAmpPortTargetPowerWidth,
            tnIroadmPortConfigIngressTargetPowerWidth  NokiaAmpPortTargetPowerWidth
        }

    tnIroadmPortConfigPowerGain OBJECT-TYPE
        SYNTAX         Unsigned32
        UNITS          "mB"
        MAX-ACCESS     read-create
        STATUS         current
        DESCRIPTION    "Current configurable range:

                       For LineOut:
                       Iroadmv: 1500 to 2500
                       Iroadmf: 1500 to 2100.
                       For LineIn:
                       Iroadmv: 1500 to 3100
                       Iroadmf: 1300 to 1900.

                       Current defaults:

                       For LineOut:
                       Iroadmv: 2000
                       Iroadmf: 1800.
                       For LineIn:
                       Iroadmv: 1500
                       Iroadmf: 1600."
        ::= { tnIroadmPortConfigEntry 1 }

    tnIroadmPortConfigPowerGainBackoff OBJECT-TYPE
        SYNTAX         Unsigned32
        UNITS          "mB"
        MAX-ACCESS     read-create
        STATUS         current
        DESCRIPTION    "Current configurable range:

                        0 to 1000."
        DEFVAL         { 0 }
        ::= { tnIroadmPortConfigEntry 2 }

    tnIroadmPortConfigTargetTilt OBJECT-TYPE
        SYNTAX         Integer32
        UNITS          "mB"
        MAX-ACCESS     read-create
        STATUS         current
        DESCRIPTION    "Current configurable range:

                        For LineOut:
                        No configurable range.

                        For LineIn:
                        Iroadmf: 0
                        Iroadmv: -300 to 300."
        DEFVAL         { 0 }
        ::= { tnIroadmPortConfigEntry 3 }

    tnIroadmPortConfigVoaSet OBJECT-TYPE
        SYNTAX         Unsigned32
        UNITS          "mB"
        MAX-ACCESS     read-create
        STATUS         current
        DESCRIPTION    "."
        ::= { tnIroadmPortConfigEntry 4 }

    tnIroadmPortConfigNominalSpanLossOut OBJECT-TYPE
        SYNTAX         Integer32
        UNITS          "mB"
        MAX-ACCESS     read-create
        STATUS         current
        DESCRIPTION    "."
        ::= { tnIroadmPortConfigEntry 5 }

    tnIroadmPortConfigFiberTypeOut OBJECT-TYPE
        SYNTAX         INTEGER {
                         notConfigured(1),
                         ssmf(2),
                         eleaf(3),
                         twrs(4),
                         dsf(5),
                         twc(6),
                         twp(7),
                         ls(8)
                       }
        MAX-ACCESS     read-create
        STATUS         current
        DESCRIPTION    "."
        DEFVAL         { ssmf }
        ::= { tnIroadmPortConfigEntry 6 }

    tnIroadmPortConfigFiberLengthKm OBJECT-TYPE
        SYNTAX         Unsigned32
        UNITS          "kilometers"
        MAX-ACCESS     read-create
        STATUS         current
        DESCRIPTION    "Current configurable range:

                        0 to 150
                        Current default:

                        Iroadmv:70
                        Iroadmf:40."
        ::= { tnIroadmPortConfigEntry 7 }

    tnIroadmPortConfigAddMinChannelPower OBJECT-TYPE
        SYNTAX         Integer32
        UNITS          "mBm"
        MAX-ACCESS     read-create
        STATUS         current
        DESCRIPTION    "Current configurable range:

                        -2000 to -500."
        DEFVAL         { -1300 }
        ::= { tnIroadmPortConfigEntry 8 }

    tnIroadmPortConfigEgressOaRippleToRemove OBJECT-TYPE
        SYNTAX         Unsigned32
        UNITS          "mB"
        MAX-ACCESS     read-create
        STATUS         current
        DESCRIPTION    "Current configurable range:

                        0 to 600.
                        Current default:

                        Iroadmv:150
                        Iroadmf:150."
        ::= { tnIroadmPortConfigEntry 9 }

    tnIroadmPortConfigExpressMinChannelPower OBJECT-TYPE
        SYNTAX         Integer32
        UNITS          "mBm"
        MAX-ACCESS     read-create
        STATUS         current
        DESCRIPTION    "Current configurable range:

                        -2000 to -500."
        DEFVAL         { -1300 }
        ::= { tnIroadmPortConfigEntry 10 }

    tnIroadmPortConfigIngressOaGainMin OBJECT-TYPE
        SYNTAX         Unsigned32
        UNITS          "mB"
        MAX-ACCESS     read-create
        STATUS         current
        DESCRIPTION    "Current configurable range:
                        Iroadmv: 1500 to 2500.

                        Current default:

                        Iroadmv:1500."
        ::= { tnIroadmPortConfigEntry 11 }

    tnIroadmPortConfigIngressOaGainMax OBJECT-TYPE
        SYNTAX         Unsigned32
        UNITS          "mB"
        MAX-ACCESS     read-create
        STATUS         current
        DESCRIPTION    "Current configurable range:
                        Iroadmv: 1500 to 3100

                        Current default:

                        Iroadmv:2500."
        ::= { tnIroadmPortConfigEntry 12 }

    tnIroadmPortConfigTargetPpcOut OBJECT-TYPE
        SYNTAX         Integer32
        UNITS          "mBm"
        MAX-ACCESS     read-create
        STATUS         current
        DESCRIPTION    "Current configurable range:

                        -3000 to 1100
                        Current default:

                        Iroadmv:56
                        Iroadmf:56."
        ::= { tnIroadmPortConfigEntry 13 }

    tnIroadmPortConfigIngressOaTargetPpcOut OBJECT-TYPE
        SYNTAX         Integer32
        UNITS          "mBm"
        MAX-ACCESS     read-create
        STATUS         current
        DESCRIPTION    "Current configurable range:
                        -3000 to 1100

                        Current default:
                        Iroadmv:50
                        Iroadmf:550."
        ::= { tnIroadmPortConfigEntry 14 }

    tnIroadmPortConfigIngressOaTargetPpcAdj OBJECT-TYPE
        SYNTAX         Integer32
        UNITS          "mB"
        MAX-ACCESS     read-create
        STATUS         current
        DESCRIPTION    "Current configurable range:

                        -1000 to 0."
        DEFVAL         { 0 }
        ::= { tnIroadmPortConfigEntry 15 }

    tnIroadmPortConfigSignalFailThreshold OBJECT-TYPE
        SYNTAX         Unsigned32
        MAX-ACCESS     read-create
        STATUS         current
        DESCRIPTION    "Current configurable range:

                        4 or 5."
        DEFVAL         { 4 }
        ::= { tnIroadmPortConfigEntry 16 }

    tnIroadmPortConfigSignalDegradeThreshold OBJECT-TYPE
        SYNTAX         Unsigned32
        MAX-ACCESS     read-create
        STATUS         current
        DESCRIPTION    "Current configurable range:

                        5 to 9."
        DEFVAL         { 6 }
        ::= { tnIroadmPortConfigEntry 17 }

    tnIroadmPortConfigAprDisable OBJECT-TYPE
        SYNTAX         TruthValue
        MAX-ACCESS     read-create
        STATUS         current
        DESCRIPTION    "Auto Power Reduction disable."
        DEFVAL         { false }
        ::= { tnIroadmPortConfigEntry 18 }

    tnIroadmPortConfigForcedTargetPpcOut OBJECT-TYPE
        SYNTAX         Integer32
        UNITS          "mBm"
        MAX-ACCESS     read-create
        STATUS         current
        DESCRIPTION    "Current configurable range:

                        -9900,
                        -1500 to 1000"
        DEFVAL         { -9900 }
        ::= { tnIroadmPortConfigEntry 19 }

    tnIroadmPortConfigLineDcmConnAddress OBJECT-TYPE
        SYNTAX         InterfaceIndexOrZero
        MAX-ACCESS     read-create
        STATUS         current
        DESCRIPTION    "."
        ::= { tnIroadmPortConfigEntry 20 }

    tnIroadmPortConfigAprMode OBJECT-TYPE
        SYNTAX         INTEGER {
                         auto(1),
                         force(2)
                       }
        MAX-ACCESS     read-create
        STATUS         current
        DESCRIPTION    "APR Mode for IROADM Gen 2 packs."
        DEFVAL         { auto }
        ::= { tnIroadmPortConfigEntry 21 }

    tnIroadmPortConfigGainRange OBJECT-TYPE
        SYNTAX         INTEGER {
                         low(1),
                         high(2)
                       }
        MAX-ACCESS     read-create
        STATUS         current
        DESCRIPTION    "Gain range for ingress OA of IROADM Gen 2 packs."
        DEFVAL         { low }
        ::= { tnIroadmPortConfigEntry 22 }

    tnIroadmPortConfigOSCVoaAtten OBJECT-TYPE
        SYNTAX         Unsigned32
        UNITS          "mB"
        MAX-ACCESS     read-create
        STATUS         current
        DESCRIPTION    "Set OSC drop eVOA attenuation.

                        Current configurable range: 0 to 2000."
        DEFVAL         { 1500 }
        ::= { tnIroadmPortConfigEntry 23 }

    tnIroadmPortConfigDropMaxTargetPower OBJECT-TYPE
        SYNTAX         Integer32 (-2000..0)
        UNITS          "mBm"
        MAX-ACCESS     read-create
        STATUS         current
        DESCRIPTION    "Upper limit for SCOT drop target adjustment loop.
                        For advanced users only.

                        Current configurable range: -2000 to 0."
        DEFVAL         { -600 }
        ::= { tnIroadmPortConfigEntry 24 }

    tnIroadmPortConfigDropMinTargetPower OBJECT-TYPE
        SYNTAX         Integer32 (-2000..0)
        UNITS          "mBm"
        MAX-ACCESS     read-create
        STATUS         current
        DESCRIPTION    "Lower limit for SCOT drop target adjustment loop.
                        For advanced users only.

                        Current configurable range: -2000 to 0."
        DEFVAL         { -1200 }
        ::= { tnIroadmPortConfigEntry 25 }

    tnIroadmPortConfigDropInitTargetPower OBJECT-TYPE
        SYNTAX         Integer32 (-2000..0)
        UNITS          "mBm"
        MAX-ACCESS     read-create
        STATUS         current
        DESCRIPTION    "The initial target power used for dropped channels.

                        Current configurable range: -2000 to 0."
        DEFVAL         { -1200 }
        ::= { tnIroadmPortConfigEntry 26 }

    tnIroadmPortConfigDropExpressTargetPower OBJECT-TYPE
        SYNTAX         Integer32 (-2000..300)
        UNITS          "mBm"
        MAX-ACCESS     read-create
        STATUS         current
        DESCRIPTION    "The target power used to set drop side WSS
                        attenuation value for expressed channels.

                        Current configurable range: -2000 to 300."
        DEFVAL         { -800 }
        ::= { tnIroadmPortConfigEntry 27 }

    tnIroadmPortConfigGainRangeL OBJECT-TYPE
        SYNTAX         INTEGER {
                         low(1),
                         high(2)
                       }
        MAX-ACCESS     read-create
        STATUS         current
        DESCRIPTION    "GainL range for ingress OA of IROADM Gen 2 packs."
        DEFVAL         { low }
        ::= { tnIroadmPortConfigEntry 28 }

    tnIroadmPortConfigIngressOaTargetPpcOutL OBJECT-TYPE
        SYNTAX         Integer32
        UNITS          "mBm"
        MAX-ACCESS     read-create
        STATUS         current
        DESCRIPTION    "."
        ::= { tnIroadmPortConfigEntry 29 }

    tnIroadmPortConfigPowerGainL OBJECT-TYPE
        SYNTAX         Unsigned32
        UNITS          "mB"
        MAX-ACCESS     read-create
        STATUS         current
        DESCRIPTION    "."
        ::= { tnIroadmPortConfigEntry 30 }

    tnIroadmPortConfigIngressOaGainMaxL OBJECT-TYPE
        SYNTAX         Unsigned32
        UNITS          "mB"
        MAX-ACCESS     read-create
        STATUS         current
        DESCRIPTION    "."
        ::= { tnIroadmPortConfigEntry 31 }

    tnIroadmPortConfigIngressOaGainMinL OBJECT-TYPE
        SYNTAX         Unsigned32
        UNITS          "mB"
        MAX-ACCESS     read-create
        STATUS         current
        DESCRIPTION    "."
        ::= { tnIroadmPortConfigEntry 32 }

    tnIroadmPortConfigTargetTiltL OBJECT-TYPE
        SYNTAX         Integer32
        UNITS          "mB"
        MAX-ACCESS     read-create
        STATUS         current
        DESCRIPTION    "."
        DEFVAL         { 0 }
        ::= { tnIroadmPortConfigEntry 33 }

    tnIroadmPortConfigVoaSetL OBJECT-TYPE
        SYNTAX         Unsigned32
        UNITS          "mB"
        MAX-ACCESS     read-create
        STATUS         current
        DESCRIPTION    "."
        ::= { tnIroadmPortConfigEntry 34 }

    tnIroadmPortConfigTargetPpcOutL OBJECT-TYPE
        SYNTAX         Integer32
        UNITS          "mBm"
        MAX-ACCESS     read-create
        STATUS         current
        DESCRIPTION    "."
        ::= { tnIroadmPortConfigEntry 35 }

    tnIroadmPortConfigAlienWaveBank OBJECT-TYPE
        SYNTAX         TruthValue
        MAX-ACCESS     read-create
        STATUS         current
        DESCRIPTION    "Alien wave bank allowed.

                        true  - multiple alien unkeyed optical cross
                                connections allowed at ADT port.
                        false - single alien unkeyed optical cross connection
                                allowed at ADT port."
        DEFVAL         { false }
        ::= { tnIroadmPortConfigEntry 36 }

    tnIroadmPortConfigSpanLossTh OBJECT-TYPE
        SYNTAX         Integer32
        UNITS          "mB"
        MAX-ACCESS     read-create
        STATUS         current
        DESCRIPTION    "Span loss threshold."
        DEFVAL         { -9900 }
        ::= { tnIroadmPortConfigEntry 37 }

    tnIroadmPortConfigAsellEnabled OBJECT-TYPE
        SYNTAX         TruthValue
        MAX-ACCESS     read-create
        STATUS         current
        DESCRIPTION    "."
        DEFVAL         { false }
        ::= { tnIroadmPortConfigEntry 38 }

    tnIroadmPortConfigTargetPowerWidth OBJECT-TYPE
        SYNTAX         NokiaAmpPortTargetPowerWidth
        MAX-ACCESS     read-create
        STATUS         current
        DESCRIPTION    "."
        DEFVAL         { channelWidth50GHz }
        ::= { tnIroadmPortConfigEntry 39 }

    tnIroadmPortConfigTargetPowerWidthL OBJECT-TYPE
        SYNTAX         NokiaAmpPortTargetPowerWidth
        MAX-ACCESS     read-create
        STATUS         current
        DESCRIPTION    "."
        DEFVAL         { channelWidth50GHz }
        ::= { tnIroadmPortConfigEntry 40 }

    tnIroadmPortConfigIngressTargetPowerWidth OBJECT-TYPE
        SYNTAX         NokiaAmpPortTargetPowerWidth
        MAX-ACCESS     read-create
        STATUS         current
        DESCRIPTION    "."
        DEFVAL         { channelWidth50GHz }
        ::= { tnIroadmPortConfigEntry 41 }

--------------------------------------------------------------------------------
-- MON-OCM Optical Port Config Scalar
--------------------------------------------------------------------------------
    tnMonOcmPortConfigAttributeTotal OBJECT-TYPE
        SYNTAX         Integer32
        MAX-ACCESS     read-only
        STATUS         current
        DESCRIPTION    "Total no of attributes in tnMonOcmPortConfigTable."
        ::= { tnOpticalPortConfig 329 }

--------------------------------------------------------------------------------
-- MON-OCM Optical Port Config Table
--------------------------------------------------------------------------------
    tnMonOcmPortConfigTable OBJECT-TYPE
        SYNTAX         SEQUENCE OF TnMonOcmPortConfigEntry
        MAX-ACCESS     not-accessible
        STATUS         current
        DESCRIPTION    "The ports on a MON-OCM card."
        ::= { tnOpticalPortConfig 330 }

    tnMonOcmPortConfigEntry OBJECT-TYPE
        SYNTAX         TnMonOcmPortConfigEntry
        MAX-ACCESS     not-accessible
        STATUS         current
        DESCRIPTION    "."
        INDEX { ifIndex }
        ::= { tnMonOcmPortConfigTable 1 }

    TnMonOcmPortConfigEntry ::=
        SEQUENCE {
            tnMonOcmPortConfigFunction            INTEGER,
            tnMonOcmPortConfigUserLabel           SnmpAdminString,
            tnMonOcmPortAssociatedFirstRoadmTx    SnmpAdminString,
            tnMonOcmPortAssociatedSecondRoadmTx   SnmpAdminString,
            tnMonOcmPortAssociatedFirstRoadmRx    SnmpAdminString,
            tnMonOcmPortAssociatedSecondRoadmRx   SnmpAdminString,
            tnMonOcmPortAssociatedOlpOpsRx        SnmpAdminString,
            tnMonOcmPortAssociatedOlpOpsTx        SnmpAdminString
        }

    tnMonOcmPortConfigFunction OBJECT-TYPE
        SYNTAX         INTEGER {
                         output(1),
                         input(2),
                         monitor(3)
                       }
        MAX-ACCESS     read-only
        STATUS         current
        DESCRIPTION    "Indicates the functional type of this MON-OCM port."
        ::= { tnMonOcmPortConfigEntry 1 }

    tnMonOcmPortConfigUserLabel OBJECT-TYPE
        SYNTAX         SnmpAdminString (SIZE(0..255))
        MAX-ACCESS     read-create
        STATUS         current
        DESCRIPTION    "User text field for labeling port usage."
        ::= { tnMonOcmPortConfigEntry 2 }

    tnMonOcmPortAssociatedFirstRoadmTx OBJECT-TYPE
        SYNTAX         SnmpAdminString (SIZE(0..256))
        MAX-ACCESS     read-create
        STATUS         current
        DESCRIPTION    "User text field format Text1<space>Text2."
        DEFVAL         { "" }
        ::= { tnMonOcmPortConfigEntry 3 }

    tnMonOcmPortAssociatedSecondRoadmTx OBJECT-TYPE
        SYNTAX         SnmpAdminString (SIZE(0..256))
        MAX-ACCESS     read-create
        STATUS         current
        DESCRIPTION    "User text field format Text1<space>Text2."
        DEFVAL         { "" }
        ::= { tnMonOcmPortConfigEntry 4 }

    tnMonOcmPortAssociatedFirstRoadmRx OBJECT-TYPE
        SYNTAX         SnmpAdminString (SIZE(0..256))
        MAX-ACCESS     read-create
        STATUS         current
        DESCRIPTION    "User text field format Text1<space>Text2."
        DEFVAL         { "" }
        ::= { tnMonOcmPortConfigEntry 5 }

    tnMonOcmPortAssociatedSecondRoadmRx OBJECT-TYPE
        SYNTAX         SnmpAdminString (SIZE(0..256))
        MAX-ACCESS     read-create
        STATUS         current
        DESCRIPTION    "User text field format Text1<space>Text2."
        DEFVAL         { "" }
        ::= { tnMonOcmPortConfigEntry 6 }

    tnMonOcmPortAssociatedOlpOpsRx OBJECT-TYPE
        SYNTAX         SnmpAdminString (SIZE(0..256))
        MAX-ACCESS     read-create
        STATUS         current
        DESCRIPTION    "User text field format Text1<space>Text2."
        DEFVAL         { "" }
        ::= { tnMonOcmPortConfigEntry 7 }

    tnMonOcmPortAssociatedOlpOpsTx OBJECT-TYPE
        SYNTAX         SnmpAdminString (SIZE(0..256))
        MAX-ACCESS     read-create
        STATUS         current
        DESCRIPTION    "User text field format Text1<space>Text2."
        DEFVAL         { "" }
        ::= { tnMonOcmPortConfigEntry 8 }

--------------------------------------------------------------------------------
-- Ul2uc400 Optical Port Config Scalar
--------------------------------------------------------------------------------
    tnUl2uc400PortConfigAttributeTotal OBJECT-TYPE
        SYNTAX         Integer32
        MAX-ACCESS     read-only
        STATUS         current
        DESCRIPTION    "Total no of attributes in  tnUl2uc400PortConfigTable"
        ::= { tnOpticalPortConfig 331 }

--------------------------------------------------------------------------------
-- Ul2uc400 Optical Port Config Table
--------------------------------------------------------------------------------
    tnUl2uc400PortConfigTable OBJECT-TYPE
        SYNTAX         SEQUENCE OF TnUl2uc400PortConfigEntry
        MAX-ACCESS     not-accessible
        STATUS         current
        DESCRIPTION    "The ports on a Ul2uc400 optical card."
        ::= { tnOpticalPortConfig 332 }

    tnUl2uc400PortConfigEntry OBJECT-TYPE
        SYNTAX         TnUl2uc400PortConfigEntry
        MAX-ACCESS     not-accessible
        STATUS         current
        DESCRIPTION    "."
        INDEX { ifIndex }
        ::= { tnUl2uc400PortConfigTable 1 }

    TnUl2uc400PortConfigEntry ::=
        SEQUENCE {
            tnUl2uc400PortConfigFunction  INTEGER
        }

    tnUl2uc400PortConfigFunction OBJECT-TYPE
        SYNTAX         INTEGER {
                         network(1)
                       }
        MAX-ACCESS     read-only
        STATUS         current
        DESCRIPTION    "Indicates the functional type of this Ul2uc400 port."
        ::= { tnUl2uc400PortConfigEntry 1 }


--------------------------------------------------------------------------------
-- Ul4uc400 Optical Port Config Scalar
--------------------------------------------------------------------------------
    tnUl4uc400PortConfigAttributeTotal OBJECT-TYPE
        SYNTAX         Integer32
        MAX-ACCESS     read-only
        STATUS         current
        DESCRIPTION    "Total no of attributes in tnUl4uc400PortConfigTable."
        ::= { tnOpticalPortConfig 333 }

--------------------------------------------------------------------------------
-- Ul4uc400 Optical Port Config Table
--------------------------------------------------------------------------------
    tnUl4uc400PortConfigTable OBJECT-TYPE
        SYNTAX         SEQUENCE OF TnUl4uc400PortConfigEntry
        MAX-ACCESS     not-accessible
        STATUS         current
        DESCRIPTION    "The ports on a Ul4uc400 optical card."
        ::= { tnOpticalPortConfig 334 }

    tnUl4uc400PortConfigEntry OBJECT-TYPE
        SYNTAX         TnUl4uc400PortConfigEntry
        MAX-ACCESS     not-accessible
        STATUS         current
        DESCRIPTION    "."
        INDEX { ifIndex }
        ::= { tnUl4uc400PortConfigTable 1 }

    TnUl4uc400PortConfigEntry ::=
        SEQUENCE {
            tnUl4uc400PortConfigFunction  INTEGER
        }

    tnUl4uc400PortConfigFunction OBJECT-TYPE
        SYNTAX         INTEGER {
                         network(1)
                       }
        MAX-ACCESS     read-only
        STATUS         current
        DESCRIPTION    "Indicates the functional type of this Ul4uc400 port."
        ::= { tnUl4uc400PortConfigEntry 1 }

--------------------------------------------------------------------------------
-- Ul20uc200 Optical Port Config Scalar
--------------------------------------------------------------------------------
    tnUl20uc200PortConfigAttributeTotal OBJECT-TYPE
        SYNTAX         Integer32
        MAX-ACCESS     read-only
        STATUS         current
        DESCRIPTION    "Total no of attributes in tnUl20uc200PortConfigTable."
        ::= { tnOpticalPortConfig 335 }

--------------------------------------------------------------------------------
-- Ul20uc200 Optical Port Config Table
--------------------------------------------------------------------------------
    tnUl20uc200PortConfigTable OBJECT-TYPE
        SYNTAX         SEQUENCE OF TnUl20uc200PortConfigEntry
        MAX-ACCESS     not-accessible
        STATUS         current
        DESCRIPTION    "The ports on a Ul20uc200 optical card."
        ::= { tnOpticalPortConfig 336 }

    tnUl20uc200PortConfigEntry OBJECT-TYPE
        SYNTAX         TnUl20uc200PortConfigEntry
        MAX-ACCESS     not-accessible
        STATUS         current
        DESCRIPTION    "."
        INDEX { ifIndex }
        ::= { tnUl20uc200PortConfigTable 1 }

    TnUl20uc200PortConfigEntry ::=
        SEQUENCE {
            tnUl20uc200PortConfigFunction  INTEGER
        }

    tnUl20uc200PortConfigFunction OBJECT-TYPE
        SYNTAX         INTEGER {
                         network(1)
                       }
        MAX-ACCESS     read-only
        STATUS         current
        DESCRIPTION    "Indicates the functional type of this Ul20uc200 port."
        ::= { tnUl20uc200PortConfigEntry 1 }

--------------------------------------------------------------------------------
-- D5X500 Optical Port Config Scalar
--------------------------------------------------------------------------------
    tnD5x500PortConfigAttributeTotal OBJECT-TYPE
        SYNTAX         Integer32
        MAX-ACCESS     read-only
        STATUS         current
        DESCRIPTION    "."
        ::= { tnOpticalPortConfig 337 }

--------------------------------------------------------------------------------
-- D5X500 Optical Port Config Table
--------------------------------------------------------------------------------
    tnD5x500PortConfigTable OBJECT-TYPE
        SYNTAX         SEQUENCE OF TnD5x500PortConfigEntry
        MAX-ACCESS     not-accessible
        STATUS         current
        DESCRIPTION    "The ports on a D5X500 optical card."
        ::= { tnOpticalPortConfig 338 }

    tnD5x500PortConfigEntry OBJECT-TYPE
        SYNTAX         TnD5x500PortConfigEntry
        MAX-ACCESS     not-accessible
        STATUS         current
        DESCRIPTION    "."
        INDEX { ifIndex }
        ::= { tnD5x500PortConfigTable 1 }

    TnD5x500PortConfigEntry ::=
        SEQUENCE {
            tnD5x500PortConfigFunction INTEGER
        }

    tnD5x500PortConfigFunction OBJECT-TYPE
        SYNTAX         INTEGER {
                         network(1),
                         client(2),
                         backplane(3)
                       }
        MAX-ACCESS     read-only
        STATUS         current
        DESCRIPTION    "Indicates the functional type of this D5X500 port."
        ::= { tnD5x500PortConfigEntry 1 }

--------------------------------------------------------------------------------
-- OTS11M100 Optical Port Config Scalar
--------------------------------------------------------------------------------
    tnOtS11M100PortConfigAttributeTotal OBJECT-TYPE
        SYNTAX         Integer32
        MAX-ACCESS     read-only
        STATUS         current
        DESCRIPTION    "."
        ::= { tnOpticalPortConfig 339 }

--------------------------------------------------------------------------------
-- OTS11M100 Optical Port Config Table
--------------------------------------------------------------------------------
    tnOtS11M100PortConfigTable OBJECT-TYPE
        SYNTAX         SEQUENCE OF TnOtS11M100PortConfigEntry
        MAX-ACCESS     not-accessible
        STATUS         current
        DESCRIPTION    "The ports on a OTS11M100 optical card."
        ::= { tnOpticalPortConfig 340 }

    tnOtS11M100PortConfigEntry OBJECT-TYPE
        SYNTAX         TnOtS11M100PortConfigEntry
        MAX-ACCESS     not-accessible
        STATUS         current
        DESCRIPTION    "."
        INDEX { ifIndex }
        ::= { tnOtS11M100PortConfigTable 1 }

    TnOtS11M100PortConfigEntry ::=
        SEQUENCE {
            tnOtS11M100PortConfigFunction  INTEGER
        }

    tnOtS11M100PortConfigFunction OBJECT-TYPE
        SYNTAX         INTEGER {
                         network(1),
                         client(2)
                       }
        MAX-ACCESS     read-only
        STATUS         current
        DESCRIPTION    "Indicates the functional type of this OtS11M100 port."
        ::= { tnOtS11M100PortConfigEntry 1 }

--------------------------------------------------------------------------------
-- MON-OTDR (MON-Optical Time Domain Reflectometer) Optical Port Config Scalar
--------------------------------------------------------------------------------
    tnMonOtdrPortConfigAttributeTotal OBJECT-TYPE
        SYNTAX         Integer32
        MAX-ACCESS     read-only
        STATUS         current
        DESCRIPTION    "."
        ::= { tnOpticalPortConfig 341 }
--------------------------------------------------------------------------------
-- MON-OTDR (MON-Optical Time Domain Reflectometer) Optical Port Config Table
--------------------------------------------------------------------------------
    tnMonOtdrPortConfigTable OBJECT-TYPE
        SYNTAX         SEQUENCE OF TnMonOtdrPortConfigEntry
        MAX-ACCESS     not-accessible
        STATUS         current
        DESCRIPTION    "The ports on a MON-OTDR optical card."
        ::= { tnOpticalPortConfig 342 }

    tnMonOtdrPortConfigEntry OBJECT-TYPE
        SYNTAX         TnMonOtdrPortConfigEntry
        MAX-ACCESS     not-accessible
        STATUS         current
        DESCRIPTION    "."
        INDEX { ifIndex }
        ::= { tnMonOtdrPortConfigTable 1 }

    TnMonOtdrPortConfigEntry ::=
        SEQUENCE {
            tnMonOtdrPortConfigFunction     INTEGER,
            tnMonOtdrPortConfigConnAddress  InterfaceIndexOrZero
        }

    tnMonOtdrPortConfigFunction OBJECT-TYPE
        SYNTAX         INTEGER {
                         lineIn(1),
                         otdrRx(2),
                         otdrTx(3),
                         lineOut(4),
                         sigIn(5),
                         sigOut(6)
                       }
        MAX-ACCESS     read-only
        STATUS         current
        DESCRIPTION    "Indicates the functional type of this MON-OTDR port."
        ::= { tnMonOtdrPortConfigEntry 1 }

    tnMonOtdrPortConfigConnAddress OBJECT-TYPE
        SYNTAX         InterfaceIndexOrZero
        MAX-ACCESS     read-create
        STATUS         current
        DESCRIPTION    "Specifies the assigned LD port that
                        is connected to the MON-OTDR port."
        ::= { tnMonOtdrPortConfigEntry 2 }

--------------------------------------------------------------------------------
-- PSS96 Power Filter Port Config Scalar
--------------------------------------------------------------------------------
    tnPSS96PowerFilterPortConfigAttributeTotal OBJECT-TYPE
        SYNTAX         Integer32
        MAX-ACCESS     read-only
        STATUS         current
        DESCRIPTION    "."
        ::= { tnOpticalPortConfig 343 }

--------------------------------------------------------------------------------
-- PSS96 Power Filter Port Config Table
--------------------------------------------------------------------------------
    tnPSS96PowerFilterPortConfigTable OBJECT-TYPE
        SYNTAX         SEQUENCE OF TnPSS96PowerFilterPortConfigEntry
        MAX-ACCESS     not-accessible
        STATUS         current
        DESCRIPTION    "The ports on a PSS96PowerFilter optical card."
        ::= { tnOpticalPortConfig 344 }

    tnPSS96PowerFilterPortConfigEntry OBJECT-TYPE
        SYNTAX         TnPSS96PowerFilterPortConfigEntry
        MAX-ACCESS     not-accessible
        STATUS         current
        DESCRIPTION    "."
        INDEX { ifIndex }
        ::= { tnPSS96PowerFilterPortConfigTable 1 }

    TnPSS96PowerFilterPortConfigEntry ::=
        SEQUENCE {
            tnPSS96PowerFilterPortConfigFunction  INTEGER,
            tnPSS96ExpectedAmps                   Unsigned32
        }

    tnPSS96PowerFilterPortConfigFunction OBJECT-TYPE
        SYNTAX         INTEGER {
                         powerFilterPort1(1),
                         powerFilterPort2(2),
                         powerFilterPort3(3)
                       }
        MAX-ACCESS     read-only
        STATUS         current
        DESCRIPTION    "Indicates the functional type of this PSS96 PowerFilter port."
        ::= { tnPSS96PowerFilterPortConfigEntry 1 }

    tnPSS96ExpectedAmps OBJECT-TYPE
        SYNTAX         Unsigned32
        MAX-ACCESS     read-create
        STATUS         current
        DESCRIPTION    "Displays the configured expected amps of the circuit
                        breaker of the power branch.

                        auto - value 4 is mapped internally."
        DEFVAL         { 60 }
        ::= { tnPSS96PowerFilterPortConfigEntry 2 }

--------------------------------------------------------------------------------
-- 103SCEC/11OCEC Optical Port Config Scalar
--------------------------------------------------------------------------------
    tn103scecPortConfigAttributeTotal OBJECT-TYPE
        SYNTAX         Integer32
        MAX-ACCESS     read-only
        STATUS         current
        DESCRIPTION    "Total number of attributes in tnOcsPacketPortConfigTable."
        ::= { tnOpticalPortConfig 345 }

--------------------------------------------------------------------------------
-- 103SCEC/11OCEC Optical Port Config Table
--------------------------------------------------------------------------------
    tnOcsPacketPortConfigTable OBJECT-TYPE
        SYNTAX         SEQUENCE OF TnOcsPacketPortConfigEntry
        MAX-ACCESS     not-accessible
        STATUS         current
        DESCRIPTION    "The ports on a 103SCEC/11OCEC optical card."
        ::= { tnOpticalPortConfig 346 }

    tnOcsPacketPortConfigEntry OBJECT-TYPE
        SYNTAX         TnOcsPacketPortConfigEntry
        MAX-ACCESS     not-accessible
        STATUS         current
        DESCRIPTION    "."
        INDEX { ifIndex }
        ::={ tnOcsPacketPortConfigTable 1 }

    TnOcsPacketPortConfigEntry ::= SEQUENCE {
        tnOcsPacketPortConfigLPTCSFConsequenceAction     INTEGER,
        tnOcsPacketPortConfigLPTSSFConsequenceAction     INTEGER,
        tnOcsPacketLptRFISuppress                        INTEGER,
        tnOcsPacketLptHoldoffTime                        Unsigned32,
        tnOcsPacketLptSendControl                        INTEGER,
        tnOcsPacketLlcfDownstreamPotlist                 PortList,
        tnOcsPacketLlcfUpstreamPotlist                   PortList
    }

    tnOcsPacketPortConfigLPTCSFConsequenceAction OBJECT-TYPE
        SYNTAX         INTEGER {
                         disable(1),
                         shutDown(2),
                         ethais(3),
                         shutDownAllandEthais(4)
                       }
        MAX-ACCESS     read-create
        STATUS         current
        DESCRIPTION    "Indicates the 103SCEC/11OCEC
                        port LPT CSF ConsequenceAction."
        DEFVAL         { disable }
        ::= { tnOcsPacketPortConfigEntry 1 }

    tnOcsPacketPortConfigLPTSSFConsequenceAction OBJECT-TYPE
        SYNTAX         INTEGER {
                         disable(1),
                         shutDown(2),
                         ethais(3),
                         shutDownAllandEthais(4)
                       }
        MAX-ACCESS     read-create
        STATUS         current
        DESCRIPTION    "Indicates the 103SCEC/11OCEC port LPT SSF ConsequenceAction."
        DEFVAL         { disable }
        ::= { tnOcsPacketPortConfigEntry 2 }

    tnOcsPacketLptRFISuppress OBJECT-TYPE
        SYNTAX         INTEGER {
                         disable(1),
                         enable(2)
                       }
        MAX-ACCESS     read-create
        STATUS         current
        DESCRIPTION    "Configure whether aRFI on WAN IF is suppressed by CSF CA
                        caused by dCMF-LOS/LOCS/FDI or dETH-LFI (for interworking
                        with 103SCEC/11OCEC) or not (for interworking with
                        10AN10G/130SCX10)"
        DEFVAL         { disable }
        ::= { tnOcsPacketPortConfigEntry 3 }

    tnOcsPacketLptHoldoffTime OBJECT-TYPE
        SYNTAX         Unsigned32
        MAX-ACCESS     read-create
        STATUS         current
        DESCRIPTION    "Configure the LPT hold-off time (on port basis ) at local
                        LAN port "
        DEFVAL         { 0 }
        ::= { tnOcsPacketPortConfigEntry 4 }

    tnOcsPacketLptSendControl OBJECT-TYPE
        SYNTAX         INTEGER {
                         disable(1),
                         enable(2)
                       }
        MAX-ACCESS     read-create
        STATUS         current
        DESCRIPTION    "Configure the LPT send control (on port basis) at local LAN
                        port, to enable/disable transmitting LPT indication out from
                        the corresponding WAN port."
        DEFVAL         { disable }
        ::= { tnOcsPacketPortConfigEntry 5 }

    tnOcsPacketLlcfDownstreamPotlist OBJECT-TYPE
        SYNTAX         PortList
        MAX-ACCESS     read-create
        STATUS         current
        DESCRIPTION    "Configure in a hub node the downstream (from Hub to Spoke)
                        WAN port list on a LAN interface to decide over which WAN
                        interfaces LPT indications should be sent.  When a WAN port
                        is configured in this list, it takes effect to enable GFP/ODU
                        CSF insertion is enabled on this WAN port."
        DEFVAL         { "" }
        ::= { tnOcsPacketPortConfigEntry 6 }

    tnOcsPacketLlcfUpstreamPotlist OBJECT-TYPE
        SYNTAX         PortList
        MAX-ACCESS     read-create
        STATUS         current
        DESCRIPTION    "Configure in a hub node the upstream (from Spoke to Hub)
                        port list on a LAN interface to list those WAN interfaces
                        able to trigger LPT CSF/SSF consequent actions on this LAN
                        interface.  When the list on LAN port is configured to
                        non-empty, it requires that both ssfconsaction and
                        csfconsaction should have the same value on this LAN port."
        DEFVAL         { "" }
        ::= { tnOcsPacketPortConfigEntry 7 }

-------------------------------------------------------------------------------
-- 1CE100 Optical Port Config Scalar
-------------------------------------------------------------------------------
    tn1ce100PortConfigAttributeTotal OBJECT-TYPE
        SYNTAX         Integer32
        MAX-ACCESS     read-only
        STATUS         current
        DESCRIPTION    "."
        ::= { tnOpticalPortConfig 347 }

-------------------------------------------------------------------------------
-- 1CE100 Optical Port Config Table
-------------------------------------------------------------------------------
    tn1ce100PortConfigTable OBJECT-TYPE
        SYNTAX         SEQUENCE OF Tn1ce100PortConfigEntry
        MAX-ACCESS     not-accessible
        STATUS         current
        DESCRIPTION    "The ports on a 1CE100 optical card."
        ::= { tnOpticalPortConfig 348 }

    tn1ce100PortConfigEntry OBJECT-TYPE
        SYNTAX         Tn1ce100PortConfigEntry
        MAX-ACCESS     not-accessible
        STATUS         current
        DESCRIPTION    "."
        INDEX { ifIndex }
        ::= { tn1ce100PortConfigTable 1 }

    Tn1ce100PortConfigEntry ::=
        SEQUENCE {
            tn1ce100PortConfigFunction INTEGER
        }

    tn1ce100PortConfigFunction OBJECT-TYPE
        SYNTAX         INTEGER {
                         client(1),
                         backplane(2),
                         tod(3),
                         ethman(4)
                       }
        MAX-ACCESS     read-only
        STATUS         current
        DESCRIPTION    "Indicates the functional type of this 1CE100 port."
        ::= { tn1ce100PortConfigEntry 1 }

--------------------------------------------------------------------------------
-- LCI1000 Optical Port Config Scalar
--------------------------------------------------------------------------------
    tnLcI1000PortConfigAttributeTotal OBJECT-TYPE
        SYNTAX         Integer32
        MAX-ACCESS     read-only
        STATUS         current
        DESCRIPTION    "."
        ::= { tnOpticalPortConfig 349 }

--------------------------------------------------------------------------------
-- LCI1000 Optical Port Config Table
--------------------------------------------------------------------------------
    tnLcI1000PortConfigTable OBJECT-TYPE
        SYNTAX         SEQUENCE OF TnLcI1000PortConfigEntry
        MAX-ACCESS     not-accessible
        STATUS         current
        DESCRIPTION    "The ports on a LcI1000 optical card."
        ::= { tnOpticalPortConfig 350 }

    tnLcI1000PortConfigEntry OBJECT-TYPE
        SYNTAX         TnLcI1000PortConfigEntry
        MAX-ACCESS     not-accessible
        STATUS         current
        DESCRIPTION    "."
        INDEX { ifIndex }
        ::= { tnLcI1000PortConfigTable 1 }

    TnLcI1000PortConfigEntry ::= SEQUENCE {
        tnLcI1000PortConfigFunction INTEGER
    }

    tnLcI1000PortConfigFunction OBJECT-TYPE
        SYNTAX         INTEGER {
                         network(1),
                         client(2)
                       }
        MAX-ACCESS     read-only
        STATUS         current
        DESCRIPTION    "Indicates the functional type of
                        this LcI1000 port."
        ::= { tnLcI1000PortConfigEntry 1 }

-------------------------------------------------------------------------------
-- AWBEGR Optical Port Config Scalar
-------------------------------------------------------------------------------
    tnAwbegrPortConfigAttributeTotal OBJECT-TYPE
        SYNTAX         Integer32
        MAX-ACCESS     read-only
        STATUS         current
        DESCRIPTION    "."
        ::= { tnOpticalPortConfig 351 }

-------------------------------------------------------------------------------
-- AWBEGR Optical Port Config Table
-------------------------------------------------------------------------------
    tnAwbegrPortConfigTable OBJECT-TYPE
        SYNTAX         SEQUENCE OF TnAwbegrPortConfigEntry
        MAX-ACCESS     not-accessible
        STATUS         current
        DESCRIPTION    "The ports on a AWBEGR optical card."
        ::= { tnOpticalPortConfig 352 }

    tnAwbegrPortConfigEntry OBJECT-TYPE
        SYNTAX         TnAwbegrPortConfigEntry
        MAX-ACCESS     not-accessible
        STATUS         current
        DESCRIPTION    "."
        INDEX { ifIndex }
        ::= { tnAwbegrPortConfigTable 1 }

    TnAwbegrPortConfigEntry ::=
        SEQUENCE {
            tnAwbegrPortConfigFunction INTEGER
        }

    tnAwbegrPortConfigFunction OBJECT-TYPE
        SYNTAX         INTEGER {
                         sigCin(1),
                         sigLin(2),
                         otdrTx(3),
                         lineOut(4),
                         osc(5)
                       }
        MAX-ACCESS     read-only
        STATUS         current
        DESCRIPTION    "Indicates the functional type of this AWBEGR port."
        ::= { tnAwbegrPortConfigEntry 1 }

-------------------------------------------------------------------------------
-- AWBING Optical Port Config Scalar
-------------------------------------------------------------------------------
    tnAwbingPortConfigAttributeTotal OBJECT-TYPE
        SYNTAX         Integer32
        MAX-ACCESS     read-only
        STATUS         current
        DESCRIPTION    "."
        ::= { tnOpticalPortConfig 353 }

-------------------------------------------------------------------------------
-- AWBING Optical Port Config Table
-------------------------------------------------------------------------------
    tnAwbingPortConfigTable OBJECT-TYPE
        SYNTAX         SEQUENCE OF TnAwbingPortConfigEntry
        MAX-ACCESS     not-accessible
        STATUS         current
        DESCRIPTION    "The ports on a AWBING optical card."
        ::= { tnOpticalPortConfig 354 }

    tnAwbingPortConfigEntry OBJECT-TYPE
        SYNTAX         TnAwbingPortConfigEntry
        MAX-ACCESS     not-accessible
        STATUS         current
        DESCRIPTION    "."
        INDEX { ifIndex }
        ::= { tnAwbingPortConfigTable 1 }

    TnAwbingPortConfigEntry ::=
        SEQUENCE {
            tnAwbingPortConfigFunction INTEGER
        }

    tnAwbingPortConfigFunction OBJECT-TYPE
        SYNTAX         INTEGER {
                         lineIn(1),
                         otdrRx(2),
                         sigLout(3),
                         sigCout(4),
                         oscSfp(5),
                         osc(6),
                         custLan(7)
                       }
        MAX-ACCESS     read-only
        STATUS         current
        DESCRIPTION    "Indicates the functional type of this AWBING port."
        ::= { tnAwbingPortConfigEntry 1 }

-------------------------------------------------------------------------------
-- AWBILA Optical Port Config Scalar
-------------------------------------------------------------------------------
    tnAwbilaPortConfigAttributeTotal OBJECT-TYPE
        SYNTAX         Integer32
        MAX-ACCESS     read-only
        STATUS         current
        DESCRIPTION    "."
        ::= { tnOpticalPortConfig 355 }

-------------------------------------------------------------------------------
-- AWBILA Optical Port Config Table
-------------------------------------------------------------------------------
    tnAwbilaPortConfigTable OBJECT-TYPE
        SYNTAX         SEQUENCE OF TnAwbilaPortConfigEntry
        MAX-ACCESS     not-accessible
        STATUS         current
        DESCRIPTION    "The ports on a AWBILA optical card."
        ::= { tnOpticalPortConfig 356 }

    tnAwbilaPortConfigEntry OBJECT-TYPE
        SYNTAX         TnAwbilaPortConfigEntry
        MAX-ACCESS     not-accessible
        STATUS         current
        DESCRIPTION    "."
        INDEX { ifIndex }
        ::= { tnAwbilaPortConfigTable 1 }

    TnAwbilaPortConfigEntry ::=
        SEQUENCE {
            tnAwbilaPortConfigFunction INTEGER
        }

    tnAwbilaPortConfigFunction OBJECT-TYPE
        SYNTAX         INTEGER {
                         lineIn(1),
                         otdrRx(2),
                         otdrTx(3),
                         lineOut(4),
                         oscSfp(5),
                         osc(6),
                         custLan(7)
                       }
        MAX-ACCESS     read-only
        STATUS         current
        DESCRIPTION    "Indicates the functional type of this AWBILA port."
        ::= { tnAwbilaPortConfigEntry 1 }

--------------------------------------------------------------------------------
-- RA5P Optical Port Config Scalar
--------------------------------------------------------------------------------
    tnRa5pPortConfigAttributeTotal OBJECT-TYPE
        SYNTAX         Integer32
        MAX-ACCESS     read-only
        STATUS         current
        DESCRIPTION    "."
        ::= { tnOpticalPortConfig 357 }

--------------------------------------------------------------------------------
-- RA5P Optical Port Config Table
--------------------------------------------------------------------------------
    tnRa5pPortConfigTable OBJECT-TYPE
        SYNTAX         SEQUENCE OF TnRa5pPortConfigEntry
        MAX-ACCESS     not-accessible
        STATUS         current
        DESCRIPTION    "The ports on a RA5P optical card."
        ::= { tnOpticalPortConfig 358 }

    tnRa5pPortConfigEntry OBJECT-TYPE
        SYNTAX         TnRa5pPortConfigEntry
        MAX-ACCESS     not-accessible
        STATUS         current
        DESCRIPTION    "."
        INDEX { ifIndex }
        ::= { tnRa5pPortConfigTable 1 }

    TnRa5pPortConfigEntry ::=
        SEQUENCE {
            tnRa5pPortConfigFunction INTEGER
        }

    tnRa5pPortConfigFunction OBJECT-TYPE
        SYNTAX         INTEGER {
                         lineIn(1),
                         lineOut(2)
                       }
        MAX-ACCESS     read-only
        STATUS         current
        DESCRIPTION    "Indicates the functional type of this RA5P port."
        ::= { tnRa5pPortConfigEntry 1 }

--------------------------------------------------------------------------------
-- IROADM9M Optical Port Config Scalar
--------------------------------------------------------------------------------
    tnIroadm9mPortConfigAttributeTotal OBJECT-TYPE
        SYNTAX         Integer32
        MAX-ACCESS     read-only
        STATUS         current
        DESCRIPTION    "."
        ::= { tnOpticalPortConfig 359 }

--------------------------------------------------------------------------------
-- IROADM9M Optical Port Config Table
--------------------------------------------------------------------------------
    tnIroadm9mPortConfigTable OBJECT-TYPE
        SYNTAX         SEQUENCE OF TnIroadm9mPortConfigEntry
        MAX-ACCESS     not-accessible
        STATUS         current
        DESCRIPTION    "The ports on a IROADM9M optical card."
        ::= { tnOpticalPortConfig 360 }

    tnIroadm9mPortConfigEntry OBJECT-TYPE
        SYNTAX         TnIroadm9mPortConfigEntry
        MAX-ACCESS     not-accessible
        STATUS         current
        DESCRIPTION    "."
        INDEX { ifIndex }
        ::= { tnIroadm9mPortConfigTable 1 }

    TnIroadm9mPortConfigEntry ::=
        SEQUENCE {
            tnIroadm9mPortConfigFunction INTEGER
        }

    tnIroadm9mPortConfigFunction OBJECT-TYPE
        SYNTAX         INTEGER {
                         lineIn(1),
                         inv(2),
                         osc(3),
                         lineOut(4),
                         oscSfp(5),
                         adt(6),
                         dcm(7),
                         custLan(8)
                       }
        MAX-ACCESS     read-only
        STATUS         current
        DESCRIPTION    "Indicates the functional type of this IROADM9M port."
        ::= { tnIroadm9mPortConfigEntry 1 }

--------------------------------------------------------------------------------
-- S13X100 Optical Port Config Scalar
--------------------------------------------------------------------------------
    tnS13x100PortConfigAttributeTotal OBJECT-TYPE
        SYNTAX         Integer32
        MAX-ACCESS     read-only
        STATUS         current
        DESCRIPTION    "."
        ::= { tnOpticalPortConfig 361 }

--------------------------------------------------------------------------------
-- S13X100 Optical Port Config Table
--------------------------------------------------------------------------------
    tnS13x100PortConfigTable OBJECT-TYPE
        SYNTAX         SEQUENCE OF TnS13x100PortConfigEntry
        MAX-ACCESS     not-accessible
        STATUS         current
        DESCRIPTION    "The ports on a S13X100 optical card."
        ::= { tnOpticalPortConfig 362 }

    tnS13x100PortConfigEntry OBJECT-TYPE
        SYNTAX         TnS13x100PortConfigEntry
        MAX-ACCESS     not-accessible
        STATUS         current
        DESCRIPTION    "."
        INDEX { ifIndex }
        ::= { tnS13x100PortConfigTable 1 }

    TnS13x100PortConfigEntry ::=
        SEQUENCE {
            tnS13x100PortConfigFunction INTEGER
        }

    tnS13x100PortConfigFunction OBJECT-TYPE
        SYNTAX         INTEGER {
                         network(1),
                         client(2),
                         backplane(3)
                       }
        MAX-ACCESS     read-only
        STATUS         current
        DESCRIPTION    "Indicates the functional type of this S13X100 port."
        ::= { tnS13x100PortConfigEntry 1 }

--------------------------------------------------------------------------------
-- 12CE121 Optical Port Config Scalar
--------------------------------------------------------------------------------
    tn12ce121PortConfigAttributeTotal OBJECT-TYPE
        SYNTAX         Integer32
        MAX-ACCESS     read-only
        STATUS         current
        DESCRIPTION    "."
        ::= { tnOpticalPortConfig 363 }

--------------------------------------------------------------------------------
-- 12CE121 Optical Port Config Table
--------------------------------------------------------------------------------
    tn12ce121PortConfigTable OBJECT-TYPE
        SYNTAX         SEQUENCE OF Tn12ce121PortConfigEntry
        MAX-ACCESS     not-accessible
        STATUS         current
        DESCRIPTION    "The ports on a 12CE121 optical card."
        ::= { tnOpticalPortConfig 364 }

    tn12ce121PortConfigEntry OBJECT-TYPE
        SYNTAX         Tn12ce121PortConfigEntry
        MAX-ACCESS     not-accessible
        STATUS         current
        DESCRIPTION    "."
        INDEX { ifIndex }
        ::= { tn12ce121PortConfigTable 1 }

    Tn12ce121PortConfigEntry ::=
        SEQUENCE {
            tn12ce121PortConfigFunction INTEGER
        }

    tn12ce121PortConfigFunction OBJECT-TYPE
        SYNTAX         INTEGER {
                         client(1),
                         backplane(2),
                         tod(3),
                         ethman(4)
                       }
        MAX-ACCESS     read-only
        STATUS         current
        DESCRIPTION    "Indicates the functional type of this 12CE121 port."
        ::= { tn12ce121PortConfigEntry 1 }

--------------------------------------------------------------------------------
-- PTPIOCTL Optical Port Config Scalar
--------------------------------------------------------------------------------
    tnPtpioctlPortConfigAttributeTotal OBJECT-TYPE
        SYNTAX         Integer32
        MAX-ACCESS     read-only
        STATUS         current
        DESCRIPTION    "."
        ::= { tnOpticalPortConfig 365 }

--------------------------------------------------------------------------------
-- PTPIOCTL Optical Port Config Table
--------------------------------------------------------------------------------
    tnPtpioctlPortConfigTable OBJECT-TYPE
        SYNTAX         SEQUENCE OF TnPtpioctlPortConfigEntry
        MAX-ACCESS     not-accessible
        STATUS         current
        DESCRIPTION    "The ports on a Ptpioctl optical card."
        ::= { tnOpticalPortConfig 366 }

    tnPtpioctlPortConfigEntry OBJECT-TYPE
        SYNTAX         TnPtpioctlPortConfigEntry
        MAX-ACCESS     not-accessible
        STATUS         current
        DESCRIPTION    "."
        INDEX { ifIndex }
        ::= { tnPtpioctlPortConfigTable 1 }

    TnPtpioctlPortConfigEntry ::=
        SEQUENCE {
            tnPtpioctlPortConfigFunction           INTEGER,
            tnPtpioctlPortConfigFiberConnectPort   Unsigned32
        }

    tnPtpioctlPortConfigFunction OBJECT-TYPE
        SYNTAX         INTEGER {
                         oscLine(1),
                         oscSig(2),
                         otcLine(3),
                         otcSig(4)
                       }
        MAX-ACCESS     read-only
        STATUS         current
        DESCRIPTION    "Indicates the functional type of this Ptpioctl port."
        ::= { tnPtpioctlPortConfigEntry 1 }

    tnPtpioctlPortConfigFiberConnectPort OBJECT-TYPE
        SYNTAX         Unsigned32
        MAX-ACCESS     read-create
        STATUS         current
        DESCRIPTION    "Fiber Connection Port Index(Shelf/Slot/Port) and
                        Direction. 32-bit value defined as below:

                        +--------+--------+--------+--------+----+----+----+
                        | 32  25 | 24  17 | 16   9 | 8    4 |  3 |  2 |  1 |
                        +--------+--------+--------+--------+----+----+----+
                        | SHELF  | SLOT   | PORT   | NOTUSE | OS | RX | TX |
                        +--------+--------+--------+--------+----+----+----+

                        32-bit value 0 for Delete.

                        Bit 1(TX) and bit 2(RX) are used for direction:
                          Set bit 1(TX) to 1 for Out.
                          Set bit 2(RX) to 1 for In.
                          Set both bit 1(TX) and bit 2(RX) to 1 for other cases.

                        Bit 3(OS) is used for cards without OSCSFP port defined,
                        such as AHPHG/AHPLG/ALPHG/A2325A, etc.:

                          For AHPHG OSCSFP port, set bit 9 to 16 PORT field
                          to OSC port number, and set bit 3(OS) to 1.

                          Set bit 3(OS) to 0 for all other cases."
        ::= { tnPtpioctlPortConfigEntry 2 }

--------------------------------------------------------------------------------
-- AA2DONWB Port Config Scalar
--------------------------------------------------------------------------------
    tnAa2donwbPortConfigAttributeTotal OBJECT-TYPE
        SYNTAX         Integer32
        MAX-ACCESS     read-only
        STATUS         current
        DESCRIPTION    "."
        ::= { tnOpticalPortConfig 367 }

--------------------------------------------------------------------------------
-- AA2DONWB Port Config Table
--------------------------------------------------------------------------------
    tnAa2donwbPortConfigTable OBJECT-TYPE
        SYNTAX         SEQUENCE OF TnAa2donwbPortConfigEntry
        MAX-ACCESS     not-accessible
        STATUS         current
        DESCRIPTION    "The ports on an AA2DONWB optical card."
        ::= { tnOpticalPortConfig 368 }

    tnAa2donwbPortConfigEntry OBJECT-TYPE
        SYNTAX         TnAa2donwbPortConfigEntry
        MAX-ACCESS     not-accessible
        STATUS         current
        DESCRIPTION    "."
        INDEX { ifIndex }
        ::= { tnAa2donwbPortConfigTable 1 }

    TnAa2donwbPortConfigEntry ::=
        SEQUENCE {
            tnAa2donwbPortConfigFunction             INTEGER,
            tnAa2donwbPortConfigVoaMode              INTEGER,
            tnAa2donwbPortConfigAttenuationModeAtten Integer32,
            tnAa2donwbPortConfigConnToPort           InterfaceIndexOrZero
        }

    tnAa2donwbPortConfigFunction OBJECT-TYPE
        SYNTAX         INTEGER {
                         line(1),
                         signal(2),
                         inv(3),
                         osc(4),
                         oscSfp(5),
                         evoa(6)
                       }
        MAX-ACCESS     read-only
        STATUS         current
        DESCRIPTION    "Indicates the functional type of this AA2DONWB port."
        ::= { tnAa2donwbPortConfigEntry 1 }

    tnAa2donwbPortConfigVoaMode OBJECT-TYPE
        SYNTAX         INTEGER {
                         power(1),
                         attenuation(2)
                       }
        MAX-ACCESS     read-create
        STATUS         current
        DESCRIPTION    "Sets the port operating mode."
        DEFVAL         { power }
        ::= { tnAa2donwbPortConfigEntry 2 }

    tnAa2donwbPortConfigAttenuationModeAtten OBJECT-TYPE
        SYNTAX         Integer32
         UNITS         "mB"
        MAX-ACCESS     read-create
        STATUS         current
        DESCRIPTION    "Sets attenuation value in attenuation mode."
        DEFVAL         { 0 }
        ::= { tnAa2donwbPortConfigEntry 3 }

    tnAa2donwbPortConfigConnToPort OBJECT-TYPE
        SYNTAX         InterfaceIndexOrZero
        MAX-ACCESS     read-create
        STATUS         current
        DESCRIPTION    "Sets reference to degree input port when MVAC
                        port used external."
        DEFVAL         { 0 }
        ::= { tnAa2donwbPortConfigEntry 4 }

--------------------------------------------------------------------------------
-- OSCTAPR Optical Port Config Scalar
--------------------------------------------------------------------------------
    tnOsctaprPortConfigAttributeTotal OBJECT-TYPE
        SYNTAX         Integer32
        MAX-ACCESS     read-only
        STATUS         current
        DESCRIPTION    "."
        ::= { tnOpticalPortConfig 369 }

--------------------------------------------------------------------------------
-- OSCTAPR Optical Port Config Table
--------------------------------------------------------------------------------
    tnOsctaprPortConfigTable OBJECT-TYPE
        SYNTAX         SEQUENCE OF TnOsctaprPortConfigEntry
        MAX-ACCESS     not-accessible
        STATUS         current
        DESCRIPTION    "The ports on an OSCTAPR optical card."
        ::= { tnOpticalPortConfig 370 }

    tnOsctaprPortConfigEntry OBJECT-TYPE
        SYNTAX         TnOsctaprPortConfigEntry
        MAX-ACCESS     not-accessible
        STATUS         current
        DESCRIPTION    "."
        INDEX { ifIndex }
        ::= { tnOsctaprPortConfigTable 1 }

    TnOsctaprPortConfigEntry ::=
        SEQUENCE {
            tnOsctaprPortConfigFunction              INTEGER,
            tnOsctaprPortConfigVoaMode               INTEGER,
            tnOsctaprPortConfigAttenuationModeAtten  Integer32,
            tnOsctaprPortConfigConnToPort            InterfaceIndexOrZero
        }

    tnOsctaprPortConfigFunction OBJECT-TYPE
        SYNTAX         INTEGER {
                         signal(1),
                         line(2),
                         inv(3),
                         osc(4),
                         oscSfp(5),
                         evoa(6)
                       }
        MAX-ACCESS     read-only
        STATUS         current
        DESCRIPTION    "Indicates the functional type of this OSCTAPR port."
        ::= { tnOsctaprPortConfigEntry 1 }

    tnOsctaprPortConfigVoaMode OBJECT-TYPE
        SYNTAX         INTEGER {
                         power(1),
                         attenuation(2)
                       }
        MAX-ACCESS     read-create
        STATUS         current
        DESCRIPTION    "Sets the port operating mode."
        DEFVAL         { power }
        ::= { tnOsctaprPortConfigEntry 2 }

    tnOsctaprPortConfigAttenuationModeAtten OBJECT-TYPE
        SYNTAX         Integer32
         UNITS         "mB"
        MAX-ACCESS     read-create
        STATUS         current
        DESCRIPTION    "Sets attenuation value in attenuation mode."
        DEFVAL         { 0 }
        ::= { tnOsctaprPortConfigEntry 3 }

    tnOsctaprPortConfigConnToPort OBJECT-TYPE
        SYNTAX         InterfaceIndexOrZero
        MAX-ACCESS     read-create
        STATUS         current
        DESCRIPTION    "Sets reference to degree input port when MVAC
                        port used external."
        DEFVAL         { 0 }
        ::= { tnOsctaprPortConfigEntry 4 }

--------------------------------------------------------------------------------
-- 11QPA4B Optical Port Config Scalar
--------------------------------------------------------------------------------
    tn11qpa4bPortConfigAttributeTotal OBJECT-TYPE
        SYNTAX         Integer32
        MAX-ACCESS     read-only
        STATUS         current
        DESCRIPTION    "."
        ::= { tnOpticalPortConfig 371 }

--------------------------------------------------------------------------------
-- 11QPA4B Optical Port Config Table
--------------------------------------------------------------------------------
    tn11qpa4bPortConfigTable OBJECT-TYPE
        SYNTAX         SEQUENCE OF Tn11qpa4bPortConfigEntry
        MAX-ACCESS     not-accessible
        STATUS         current
        DESCRIPTION    "The ports on a 11QPA4B optical card."
        ::= { tnOpticalPortConfig 372 }

    tn11qpa4bPortConfigEntry OBJECT-TYPE
        SYNTAX         Tn11qpa4bPortConfigEntry
        MAX-ACCESS     not-accessible
        STATUS         current
        DESCRIPTION    "."
        INDEX { ifIndex }
        ::= { tn11qpa4bPortConfigTable 1 }

    Tn11qpa4bPortConfigEntry ::=
        SEQUENCE {
            tn11qpa4bPortConfigFunction INTEGER
        }

    tn11qpa4bPortConfigFunction OBJECT-TYPE
        SYNTAX         INTEGER {
                         network(1),
                         client(2),
                         evoa(3),
                         backplane(4)
                       }
        MAX-ACCESS     read-only
        STATUS         current
        DESCRIPTION    "Indicates the functional type of this 11QPA4B port."
        ::= { tn11qpa4bPortConfigEntry 1 }

--------------------------------------------------------------------------------
-- 1UX100 Optical Port Config Scalar
--------------------------------------------------------------------------------
    tn1ux100PortConfigAttributeTotal OBJECT-TYPE
        SYNTAX         Integer32
        MAX-ACCESS     read-only
        STATUS         current
        DESCRIPTION    "."
        ::= { tnOpticalPortConfig 373 }

--------------------------------------------------------------------------------
-- 1UX100 Optical Port Config Table
--------------------------------------------------------------------------------
    tn1ux100PortConfigTable OBJECT-TYPE
        SYNTAX         SEQUENCE OF Tn1ux100PortConfigEntry
        MAX-ACCESS     not-accessible
        STATUS         current
        DESCRIPTION    "The ports on a 1ux100 optical card."
        ::= { tnOpticalPortConfig 374 }

    tn1ux100PortConfigEntry OBJECT-TYPE
        SYNTAX         Tn1ux100PortConfigEntry
        MAX-ACCESS     not-accessible
        STATUS         current
        DESCRIPTION    "."
        INDEX { ifIndex }
        ::= { tn1ux100PortConfigTable 1 }

    Tn1ux100PortConfigEntry ::= SEQUENCE {
        tn1ux100PortConfigFunction INTEGER
    }

    tn1ux100PortConfigFunction OBJECT-TYPE
        SYNTAX         INTEGER {
                         network(1)
                       }
        MAX-ACCESS     read-only
        STATUS         current
        DESCRIPTION    "Indicates the functional type of
                        this 1ux100 port."
        ::= { tn1ux100PortConfigEntry 1 }

--------------------------------------------------------------------------------
-- 20AX200 Optical Port Config Scalar
--------------------------------------------------------------------------------
    tn20ax200PortConfigAttributeTotal OBJECT-TYPE
        SYNTAX         Integer32
        MAX-ACCESS     read-only
        STATUS         current
        DESCRIPTION    "."
        ::= { tnOpticalPortConfig 375 }

--------------------------------------------------------------------------------
-- 20AX200 Optical Port Config Table
--------------------------------------------------------------------------------
    tn20ax200PortConfigTable OBJECT-TYPE
        SYNTAX         SEQUENCE OF Tn20ax200PortConfigEntry
        MAX-ACCESS     not-accessible
        STATUS         current
        DESCRIPTION    "The ports on a 20ax200 optical card."
        ::= { tnOpticalPortConfig 376 }

    tn20ax200PortConfigEntry OBJECT-TYPE
        SYNTAX         Tn20ax200PortConfigEntry
        MAX-ACCESS     not-accessible
        STATUS         current
        DESCRIPTION    "."
        INDEX { ifIndex }
        ::= { tn20ax200PortConfigTable 1 }

    Tn20ax200PortConfigEntry ::= SEQUENCE {
        tn20ax200PortConfigFunction INTEGER
    }

    tn20ax200PortConfigFunction OBJECT-TYPE
        SYNTAX         INTEGER {
                         port(1)
                       }
        MAX-ACCESS     read-only
        STATUS         current
        DESCRIPTION    "Indicates the functional type of
                        this 20ax200 port."
        ::= { tn20ax200PortConfigEntry 1 }

--------------------------------------------------------------------------------
-- 20MX80 Optical Port Config Scalar
--------------------------------------------------------------------------------
    tn20mx80PortConfigAttributeTotal OBJECT-TYPE
        SYNTAX         Integer32
        MAX-ACCESS     read-only
        STATUS         current
        DESCRIPTION    "."
        ::= { tnOpticalPortConfig 377 }

--------------------------------------------------------------------------------
-- 20MX80 Optical Port Config Table
--------------------------------------------------------------------------------
    tn20mx80PortConfigTable OBJECT-TYPE
        SYNTAX         SEQUENCE OF Tn20mx80PortConfigEntry
        MAX-ACCESS     not-accessible
        STATUS         current
        DESCRIPTION    "The ports on a 20mx80 optical card."
        ::= { tnOpticalPortConfig 378 }

    tn20mx80PortConfigEntry OBJECT-TYPE
        SYNTAX         Tn20mx80PortConfigEntry
        MAX-ACCESS     not-accessible
        STATUS         current
        DESCRIPTION    "."
        INDEX { ifIndex }
        ::= { tn20mx80PortConfigTable 1 }

    Tn20mx80PortConfigEntry ::= SEQUENCE {
        tn20mx80PortConfigFunction INTEGER
    }

    tn20mx80PortConfigFunction OBJECT-TYPE
        SYNTAX         INTEGER {
                         port(1)
                       }
        MAX-ACCESS     read-only
        STATUS         current
        DESCRIPTION    "Indicates the functional type of
                        this 20mx80 port."
        ::= { tn20mx80PortConfigEntry 1 }

--------------------------------------------------------------------------------
-- AAR2X-8A Optical Port Config Scalar
--------------------------------------------------------------------------------
    tnAar2x8aPortConfigAttributeTotal OBJECT-TYPE
        SYNTAX         Integer32
        MAX-ACCESS     read-only
        STATUS         current
        DESCRIPTION    "."
        ::= { tnOpticalPortConfig 379 }

--------------------------------------------------------------------------------
-- AAR2X-8A Optical Port Config Table
--------------------------------------------------------------------------------
    tnAar2x8aPortConfigTable OBJECT-TYPE
        SYNTAX         SEQUENCE OF TnAar2x8aPortConfigEntry
        MAX-ACCESS     not-accessible
        STATUS         current
        DESCRIPTION    "The ports on an AAR2X-8A optical card."
        ::= { tnOpticalPortConfig 380 }

    tnAar2x8aPortConfigEntry OBJECT-TYPE
        SYNTAX         TnAar2x8aPortConfigEntry
        MAX-ACCESS     not-accessible
        STATUS         current
        DESCRIPTION    "."
        INDEX { ifIndex }
        ::= { tnAar2x8aPortConfigTable 1 }

    TnAar2x8aPortConfigEntry ::=
        SEQUENCE {
            tnAar2x8aPortConfigFunction   INTEGER
        }

    tnAar2x8aPortConfigFunction OBJECT-TYPE
        SYNTAX         INTEGER {
                         ampIn(1),
                         ampOut(2),
                         mpoFsm(3),
                         mpoMcs(4)
                       }
        MAX-ACCESS     read-only
        STATUS         current
        DESCRIPTION    "Indicates the functional type of this AAR2X-8A port."
        ::= { tnAar2x8aPortConfigEntry 1 }

--------------------------------------------------------------------------------
-- S13X100E Optical Port Config Scalar
--------------------------------------------------------------------------------
    tnS13x100ePortConfigAttributeTotal OBJECT-TYPE
        SYNTAX         Integer32
        MAX-ACCESS     read-only
        STATUS         current
        DESCRIPTION    "."
        ::= { tnOpticalPortConfig 381 }

--------------------------------------------------------------------------------
-- S13X100E Optical Port Config Table
--------------------------------------------------------------------------------
    tnS13x100ePortConfigTable OBJECT-TYPE
        SYNTAX         SEQUENCE OF TnS13x100ePortConfigEntry
        MAX-ACCESS     not-accessible
        STATUS         current
        DESCRIPTION    "The ports on a S13x100e optical card."
        ::= { tnOpticalPortConfig 382 }

    tnS13x100ePortConfigEntry OBJECT-TYPE
        SYNTAX         TnS13x100ePortConfigEntry
        MAX-ACCESS     not-accessible
        STATUS         current
        DESCRIPTION    "."
        INDEX { ifIndex }
        ::= { tnS13x100ePortConfigTable 1 }

    TnS13x100ePortConfigEntry ::=
        SEQUENCE {
            tnS13x100ePortConfigFunction INTEGER
        }

    tnS13x100ePortConfigFunction OBJECT-TYPE
        SYNTAX         INTEGER {
                         network(1),
                         client(2),
                         backplane(3)
                       }
        MAX-ACCESS     read-only
        STATUS         current
        DESCRIPTION    "Indicates the functional type of this S13X100E port."
        ::= { tnS13x100ePortConfigEntry 1 }

--------------------------------------------------------------------------------
-- WTOCMFL Optical Port Config Scalar
--------------------------------------------------------------------------------
    tnWtocmflPortConfigAttributeTotal OBJECT-TYPE
        SYNTAX         Integer32
        MAX-ACCESS     read-only
        STATUS         current
        DESCRIPTION    "."
        ::= { tnOpticalPortConfig 383 }

--------------------------------------------------------------------------------
-- WTOCMFL Optical Port Config Table
--------------------------------------------------------------------------------
    tnWtocmflPortConfigTable OBJECT-TYPE
        SYNTAX         SEQUENCE OF TnWtocmflPortConfigEntry
        MAX-ACCESS     not-accessible
        STATUS         current
        DESCRIPTION    "The ports on a WTOCMFL optical card."
        ::= { tnOpticalPortConfig 384 }

    tnWtocmflPortConfigEntry OBJECT-TYPE
        SYNTAX         TnWtocmflPortConfigEntry
        MAX-ACCESS     not-accessible
        STATUS         current
        DESCRIPTION    "."
        INDEX { ifIndex }
        ::= { tnWtocmflPortConfigTable 1 }

    TnWtocmflPortConfigEntry ::=
        SEQUENCE {
            tnWtocmflPortConfigFunction  INTEGER
        }

    tnWtocmflPortConfigFunction OBJECT-TYPE
        SYNTAX         INTEGER {
                         detect(1)
                       }
        MAX-ACCESS     read-only
        STATUS         current
        DESCRIPTION    "Indicates the functional type of this WTOCMFL port."
        ::= { tnWtocmflPortConfigEntry 1 }

--------------------------------------------------------------------------------
-- AAR2X-8AL Optical Port Config Scalar
--------------------------------------------------------------------------------
    tnAar2x8alPortConfigAttributeTotal OBJECT-TYPE
        SYNTAX         Integer32
        MAX-ACCESS     read-only
        STATUS         current
        DESCRIPTION    "."
        ::= { tnOpticalPortConfig 385 }

--------------------------------------------------------------------------------
-- AAR2X-8AL Optical Port Config Table
--------------------------------------------------------------------------------
    tnAar2x8alPortConfigTable OBJECT-TYPE
        SYNTAX         SEQUENCE OF TnAar2x8alPortConfigEntry
        MAX-ACCESS     not-accessible
        STATUS         current
        DESCRIPTION    "The ports on an AAR2X-8AL optical card."
        ::= { tnOpticalPortConfig 386 }

    tnAar2x8alPortConfigEntry OBJECT-TYPE
        SYNTAX         TnAar2x8alPortConfigEntry
        MAX-ACCESS     not-accessible
        STATUS         current
        DESCRIPTION    "."
        INDEX { ifIndex }
        ::= { tnAar2x8alPortConfigTable 1 }

    TnAar2x8alPortConfigEntry ::=
        SEQUENCE {
            tnAar2x8alPortConfigFunction   INTEGER
        }

    tnAar2x8alPortConfigFunction OBJECT-TYPE
        SYNTAX         INTEGER {
                         ampIn(1),
                         ampOut(2),
                         mpoFsm(3),
                         mpoMcs(4)
                       }
        MAX-ACCESS     read-only
        STATUS         current
        DESCRIPTION    "Indicates the functional type of this AAR2X-8AL port."
        ::= { tnAar2x8alPortConfigEntry 1 }

--------------------------------------------------------------------------------
-- WR20-TFML Optical Port Config Scalar
--------------------------------------------------------------------------------
    tnWr20tfmlPortConfigAttributeTotal OBJECT-TYPE
        SYNTAX         Integer32
        MAX-ACCESS     read-only
        STATUS         current
        DESCRIPTION    "."
        ::= { tnOpticalPortConfig 387 }

--------------------------------------------------------------------------------
-- WR20-TFML Optical Port Config Table
--------------------------------------------------------------------------------
    tnWr20tfmlPortConfigTable OBJECT-TYPE
        SYNTAX         SEQUENCE OF TnWr20tfmlPortConfigEntry
        MAX-ACCESS     not-accessible
        STATUS         current
        DESCRIPTION    "The ports on a WR20-TFML optical card."
        ::= { tnOpticalPortConfig 388 }

    tnWr20tfmlPortConfigEntry OBJECT-TYPE
        SYNTAX         TnWr20tfmlPortConfigEntry
        MAX-ACCESS     not-accessible
        STATUS         current
        DESCRIPTION    "."
        INDEX { ifIndex }
        ::= { tnWr20tfmlPortConfigTable 1 }

    TnWr20tfmlPortConfigEntry ::=
        SEQUENCE {
            tnWr20tfmlPortConfigFunction                        INTEGER
        }

    tnWr20tfmlPortConfigFunction OBJECT-TYPE
        SYNTAX         INTEGER {
                         signal(1),
                         adt(2),
                         ad(3),
                         inv(4),
                         mpoDropOut(5),
                         mpoAddIn(6)
                       }
        MAX-ACCESS     read-only
        STATUS         current
        DESCRIPTION    "Indicates the functional type of this WR20-TFML port."
        ::= { tnWr20tfmlPortConfigEntry 1 }

--------------------------------------------------------------------------------
-- MCS8-16L Optical Port Config Scalar
--------------------------------------------------------------------------------
    tnMcs8x16lPortConfigAttributeTotal OBJECT-TYPE
        SYNTAX         Integer32
        MAX-ACCESS     read-only
        STATUS         current
        DESCRIPTION    "."
        ::= { tnOpticalPortConfig 389 }

--------------------------------------------------------------------------------
-- MCS8-16L Optical Port Config Table
--------------------------------------------------------------------------------
    tnMcs8x16lPortConfigTable OBJECT-TYPE
        SYNTAX         SEQUENCE OF TnMcs8x16lPortConfigEntry
        MAX-ACCESS     not-accessible
        STATUS         current
        DESCRIPTION    "The ports on a MCS8-16L optical card."
        ::= { tnOpticalPortConfig 390 }

    tnMcs8x16lPortConfigEntry OBJECT-TYPE
        SYNTAX         TnMcs8x16lPortConfigEntry
        MAX-ACCESS     not-accessible
        STATUS         current
        DESCRIPTION    "."
        INDEX { ifIndex }
        ::= { tnMcs8x16lPortConfigTable 1 }

    TnMcs8x16lPortConfigEntry ::=
        SEQUENCE {
            tnMcs8x16lPortConfigFunction   INTEGER
        }

    tnMcs8x16lPortConfigFunction OBJECT-TYPE
        SYNTAX         INTEGER {
                         signal(1),
                         ad(2),
                         mpoAar(3)
                       }
        MAX-ACCESS     read-only
        STATUS         current
        DESCRIPTION    "Indicates the functional type of this MCS8-16L port."
        ::= { tnMcs8x16lPortConfigEntry 1 }

--------------------------------------------------------------------------------
-- PSS8x Power Filter Port Config Scalar
--------------------------------------------------------------------------------
    tnPSS8xPowerFilterPortConfigAttributeTotal OBJECT-TYPE
        SYNTAX         Integer32
        MAX-ACCESS     read-only
        STATUS         current
        DESCRIPTION    "."
        ::= { tnOpticalPortConfig 391 }

--------------------------------------------------------------------------------
-- PSS8x Power Filter Port Config Table
--------------------------------------------------------------------------------
    tnPSS8xPowerFilterPortConfigTable OBJECT-TYPE
        SYNTAX         SEQUENCE OF TnPSS8xPowerFilterPortConfigEntry
        MAX-ACCESS     not-accessible
        STATUS         current
        DESCRIPTION    "The ports on a PSS8xPowerFilter optical card."
        ::= { tnOpticalPortConfig 392 }

    tnPSS8xPowerFilterPortConfigEntry OBJECT-TYPE
        SYNTAX         TnPSS8xPowerFilterPortConfigEntry
        MAX-ACCESS     not-accessible
        STATUS         current
        DESCRIPTION    "."
        INDEX { ifIndex }
        ::= { tnPSS8xPowerFilterPortConfigTable 1 }

    TnPSS8xPowerFilterPortConfigEntry ::=
        SEQUENCE {
            tnPSS8xPowerFilterPortConfigFunction  INTEGER,
            tnPSS8xExpectedAmps                   Unsigned32
        }

    tnPSS8xPowerFilterPortConfigFunction OBJECT-TYPE
        SYNTAX         INTEGER {
                         powerFilterPort1(1)
                        }
        MAX-ACCESS     read-only
        STATUS         current
        DESCRIPTION    "Indicates the functional type of this PSS8x PowerFilter port."
        ::= { tnPSS8xPowerFilterPortConfigEntry 1 }

    tnPSS8xExpectedAmps OBJECT-TYPE
        SYNTAX         Unsigned32
        MAX-ACCESS     read-create
        STATUS         current
        DESCRIPTION    "Displays the configured expected amps of the circuit breaker
                        of the power branch.

                        auto - value 4 is mapped internally."
        DEFVAL         { 60 }
        ::= { tnPSS8xPowerFilterPortConfigEntry 2 }

--------------------------------------------------------------------------------
-- LCI2000 Optical Port Config Scalar
--------------------------------------------------------------------------------
    tnLcI2000PortConfigAttributeTotal OBJECT-TYPE
        SYNTAX         Integer32
        MAX-ACCESS     read-only
        STATUS         current
        DESCRIPTION    "."
        ::= { tnOpticalPortConfig 393 }

--------------------------------------------------------------------------------
-- LCI2000 Optical Port Config Table
--------------------------------------------------------------------------------
    tnLcI2000PortConfigTable OBJECT-TYPE
        SYNTAX         SEQUENCE OF TnLcI2000PortConfigEntry
        MAX-ACCESS     not-accessible
        STATUS         current
        DESCRIPTION    "The ports on a LCI2000 optical card."
        ::= { tnOpticalPortConfig 394 }

    tnLcI2000PortConfigEntry OBJECT-TYPE
        SYNTAX         TnLcI2000PortConfigEntry
        MAX-ACCESS     not-accessible
        STATUS         current
        DESCRIPTION    "."
        INDEX { ifIndex }
        ::= { tnLcI2000PortConfigTable 1 }

    TnLcI2000PortConfigEntry ::= SEQUENCE {
        tnLcI2000PortConfigFunction INTEGER
    }

    tnLcI2000PortConfigFunction OBJECT-TYPE
        SYNTAX         INTEGER {
                         network(1),
                         client(2)
                       }
        MAX-ACCESS     read-only
        STATUS         current
        DESCRIPTION    "Indicates the functional type of this LCI2000 port."
        ::= { tnLcI2000PortConfigEntry 1 }

--------------------------------------------------------------------------------
-- 30SE300 Optical Port Config Scalar
--------------------------------------------------------------------------------
    tn30se300PortConfigAttributeTotal OBJECT-TYPE
        SYNTAX         Integer32
        MAX-ACCESS     read-only
        STATUS         current
        DESCRIPTION    "."
        ::= { tnOpticalPortConfig 395 }

--------------------------------------------------------------------------------
-- 30SE300 Optical Port Config Table
--------------------------------------------------------------------------------
    tn30se300PortConfigTable OBJECT-TYPE
        SYNTAX         SEQUENCE OF Tn30se300PortConfigEntry
        MAX-ACCESS     not-accessible
        STATUS         current
        DESCRIPTION    "The ports on a 30SE300 optical card."
        ::= { tnOpticalPortConfig 396 }

    tn30se300PortConfigEntry OBJECT-TYPE
        SYNTAX         Tn30se300PortConfigEntry
        MAX-ACCESS     not-accessible
        STATUS         current
        DESCRIPTION    "."
        INDEX { ifIndex }
        ::= { tn30se300PortConfigTable 1 }

    Tn30se300PortConfigEntry ::=
        SEQUENCE {
            tn30se300PortConfigFunction  INTEGER
        }

    tn30se300PortConfigFunction OBJECT-TYPE
        SYNTAX         INTEGER {
                         client(1),
                         network(2),
                         backplane(3),
                         tod(4),
                         ethman(5)
                       }
        MAX-ACCESS     read-only
        STATUS         current
        DESCRIPTION    "Indicates the functional type of this 30SE300 port."
        ::= { tn30se300PortConfigEntry 1 }

--------------------------------------------------------------------------------
-- 6SE300 Optical Port Config Scalar
--------------------------------------------------------------------------------
    tn6se300PortConfigAttributeTotal OBJECT-TYPE
        SYNTAX         Integer32
        MAX-ACCESS     read-only
        STATUS         current
        DESCRIPTION    "."
        ::= { tnOpticalPortConfig 397 }

--------------------------------------------------------------------------------
-- 6SE300 Optical Port Config Table
--------------------------------------------------------------------------------
    tn6se300PortConfigTable OBJECT-TYPE
        SYNTAX         SEQUENCE OF Tn6se300PortConfigEntry
        MAX-ACCESS     not-accessible
        STATUS         current
        DESCRIPTION    "The ports on a 6SE300 optical card."
        ::= { tnOpticalPortConfig 398 }

    tn6se300PortConfigEntry OBJECT-TYPE
        SYNTAX         Tn6se300PortConfigEntry
        MAX-ACCESS     not-accessible
        STATUS         current
        DESCRIPTION    "."
        INDEX { ifIndex }
        ::= { tn6se300PortConfigTable 1 }

    Tn6se300PortConfigEntry ::=
        SEQUENCE {
            tn6se300PortConfigFunction  INTEGER
        }

    tn6se300PortConfigFunction OBJECT-TYPE
        SYNTAX         INTEGER {
                         client(1),
                         network(2),
                         backplane(3),
                         tod(4),
                         ethman(5)
                       }
        MAX-ACCESS     read-only
        STATUS         current
        DESCRIPTION    "Indicates the functional type of this 6SE300 port."
        ::= { tn6se300PortConfigEntry 1 }

--------------------------------------------------------------------------------
-- OTDRWB (Optical Time Domain Reflectometer WB) Optical Port Config Scalar
--------------------------------------------------------------------------------
    tnOtdrwbPortConfigAttributeTotal OBJECT-TYPE
        SYNTAX         Integer32
        MAX-ACCESS     read-only
        STATUS         current
        DESCRIPTION    "."
        ::= { tnOpticalPortConfig 399 }

--------------------------------------------------------------------------------
-- OTDRWB (Optical Time Domain Reflectometer WB) Optical Port Config Table
--------------------------------------------------------------------------------
    tnOtdrwbPortConfigTable OBJECT-TYPE
        SYNTAX         SEQUENCE OF TnOtdrwbPortConfigEntry
        MAX-ACCESS     not-accessible
        STATUS         current
        DESCRIPTION    "The ports on an OTDRWB optical card."
        ::= { tnOpticalPortConfig 400 }

    tnOtdrwbPortConfigEntry OBJECT-TYPE
        SYNTAX         TnOtdrwbPortConfigEntry
        MAX-ACCESS     not-accessible
        STATUS         current
        DESCRIPTION    "."
        INDEX { ifIndex }
        ::= { tnOtdrwbPortConfigTable 1 }

    TnOtdrwbPortConfigEntry ::=
        SEQUENCE {
            tnOtdrwbPortConfigFunction INTEGER,
            tnOtdrwbPortConfigConnAddress  Integer32
        }

    tnOtdrwbPortConfigFunction OBJECT-TYPE
        SYNTAX         INTEGER {
                         px(1)
                       }
        MAX-ACCESS     read-only
        STATUS         current
        DESCRIPTION    "Indicates the functional type of this OTDRWB port."
        ::= { tnOtdrwbPortConfigEntry 1 }

    tnOtdrwbPortConfigConnAddress OBJECT-TYPE
        SYNTAX         Integer32 (-1..2147483647)
        MAX-ACCESS     read-create
        STATUS         current
        DESCRIPTION    "Specifies the assigned LD port that
                        is connected to the OTDRWB port."
        ::= { tnOtdrwbPortConfigEntry 2 }

--------------------------------------------------------------------------------
-- 8DC30T Optical Port Config Scalar
--------------------------------------------------------------------------------
    tn8dc30tPortConfigAttributeTotal OBJECT-TYPE
        SYNTAX         Integer32
        MAX-ACCESS     read-only
        STATUS         current
        DESCRIPTION    "."
        ::= { tnOpticalPortConfig 401 }

--------------------------------------------------------------------------------
-- 8DC30T Optical Port Config Table
--------------------------------------------------------------------------------
    tn8dc30tPortConfigTable OBJECT-TYPE
        SYNTAX         SEQUENCE OF Tn8dc30tPortConfigEntry
        MAX-ACCESS     not-accessible
        STATUS         current
        DESCRIPTION    "The ports on a 8DC30T optical card."
        ::= { tnOpticalPortConfig 402 }

    tn8dc30tPortConfigEntry OBJECT-TYPE
        SYNTAX         Tn8dc30tPortConfigEntry
        MAX-ACCESS     not-accessible
        STATUS         current
        DESCRIPTION    "."
        INDEX { ifIndex }
        ::= { tn8dc30tPortConfigTable 1 }

    Tn8dc30tPortConfigEntry ::=
        SEQUENCE {
            tn8dc30tPortConfigFunction  INTEGER
        }

    tn8dc30tPortConfigFunction OBJECT-TYPE
        SYNTAX         INTEGER {
                         timing(1)
                       }
        MAX-ACCESS     read-only
        STATUS         current
        DESCRIPTION    "Indicates the functional type of this 8DC30T port."
        ::= { tn8dc30tPortConfigEntry 1 }

--------------------------------------------------------------------------------
-- 16DC65T Optical Port Config Scalar
--------------------------------------------------------------------------------
    tn16dc65tPortConfigAttributeTotal OBJECT-TYPE
        SYNTAX         Integer32
        MAX-ACCESS     read-only
        STATUS         current
        DESCRIPTION    "."
        ::= { tnOpticalPortConfig 403 }

--------------------------------------------------------------------------------
-- 16DC65T Optical Port Config Table
--------------------------------------------------------------------------------
    tn16dc65tPortConfigTable OBJECT-TYPE
        SYNTAX         SEQUENCE OF Tn16dc65tPortConfigEntry
        MAX-ACCESS     not-accessible
        STATUS         current
        DESCRIPTION    "The ports on a 16DC65T optical card."
        ::= { tnOpticalPortConfig 404 }

    tn16dc65tPortConfigEntry OBJECT-TYPE
        SYNTAX         Tn16dc65tPortConfigEntry
        MAX-ACCESS     not-accessible
        STATUS         current
        DESCRIPTION    "."
        INDEX { ifIndex }
        ::= { tn16dc65tPortConfigTable 1 }

    Tn16dc65tPortConfigEntry ::=
        SEQUENCE {
            tn16dc65tPortConfigFunction  INTEGER
        }

    tn16dc65tPortConfigFunction OBJECT-TYPE
        SYNTAX         INTEGER {
                         timing(1),
                         tod(2),
                         bits(3)
                       }
        MAX-ACCESS     read-only
        STATUS         current
        DESCRIPTION    "Indicates the functional type of this 16DC65T port."
        ::= { tn16dc65tPortConfigEntry 1 }

--------------------------------------------------------------------------------
-- D5X500L Optical Port Config Scalar
--------------------------------------------------------------------------------
    tnD5x500lPortConfigAttributeTotal OBJECT-TYPE
        SYNTAX         Integer32
        MAX-ACCESS     read-only
        STATUS         current
        DESCRIPTION    "."
        ::= { tnOpticalPortConfig 405 }

--------------------------------------------------------------------------------
-- D5X500L Optical Port Config Table
--------------------------------------------------------------------------------
    tnD5x500lPortConfigTable OBJECT-TYPE
        SYNTAX         SEQUENCE OF TnD5x500lPortConfigEntry
        MAX-ACCESS     not-accessible
        STATUS         current
        DESCRIPTION    "The ports on a D5X500L optical card."
        ::= { tnOpticalPortConfig 406 }

    tnD5x500lPortConfigEntry OBJECT-TYPE
        SYNTAX         TnD5x500lPortConfigEntry
        MAX-ACCESS     not-accessible
        STATUS         current
        DESCRIPTION    "."
        INDEX { ifIndex }
        ::= { tnD5x500lPortConfigTable 1 }

    TnD5x500lPortConfigEntry ::=
        SEQUENCE {
            tnD5x500lPortConfigFunction INTEGER
        }

    tnD5x500lPortConfigFunction OBJECT-TYPE
        SYNTAX         INTEGER {
                         network(1),
                         client(2),
                         backplane(3)
                       }
        MAX-ACCESS     read-only
        STATUS         current
        DESCRIPTION    "Indicates the functional type of this D5X500L port."
        ::= { tnD5x500lPortConfigEntry 1 }

--------------------------------------------------------------------------------
-- LCI2000L Optical Port Config Scalar
--------------------------------------------------------------------------------
    tnLcI2000lPortConfigAttributeTotal OBJECT-TYPE
        SYNTAX         Integer32
        MAX-ACCESS     read-only
        STATUS         current
        DESCRIPTION    "."
        ::= { tnOpticalPortConfig 407 }

--------------------------------------------------------------------------------
-- LCI2000L Optical Port Config Table
--------------------------------------------------------------------------------
    tnLcI2000lPortConfigTable OBJECT-TYPE
        SYNTAX         SEQUENCE OF TnLcI2000lPortConfigEntry
        MAX-ACCESS     not-accessible
        STATUS         current
        DESCRIPTION    "The ports on a LCI2000L optical card."
        ::= { tnOpticalPortConfig 408 }

    tnLcI2000lPortConfigEntry OBJECT-TYPE
        SYNTAX         TnLcI2000lPortConfigEntry
        MAX-ACCESS     not-accessible
        STATUS         current
        DESCRIPTION    "."
        INDEX { ifIndex }
        ::= { tnLcI2000lPortConfigTable 1 }

    TnLcI2000lPortConfigEntry ::= SEQUENCE {
        tnLcI2000lPortConfigFunction INTEGER
    }

    tnLcI2000lPortConfigFunction OBJECT-TYPE
        SYNTAX         INTEGER {
                         network(1),
                         client(2)
                       }
        MAX-ACCESS     read-only
        STATUS         current
        DESCRIPTION    "Indicates the functional type of this LCI2000L port."
        ::= { tnLcI2000lPortConfigEntry 1 }

--------------------------------------------------------------------------------
-- IROADM9R Optical Port Config Scalar
--------------------------------------------------------------------------------
    tnIroadm9rPortConfigAttributeTotal OBJECT-TYPE
        SYNTAX         Integer32
        MAX-ACCESS     read-only
        STATUS         current
        DESCRIPTION    "."
        ::= { tnOpticalPortConfig 409 }

--------------------------------------------------------------------------------
-- IROADM9R Optical Port Config Table
--------------------------------------------------------------------------------
    tnIroadm9rPortConfigTable OBJECT-TYPE
        SYNTAX         SEQUENCE OF TnIroadm9rPortConfigEntry
        MAX-ACCESS     not-accessible
        STATUS         current
        DESCRIPTION    "The ports on a IROADM9R optical card."
        ::= { tnOpticalPortConfig 410 }

    tnIroadm9rPortConfigEntry OBJECT-TYPE
        SYNTAX         TnIroadm9rPortConfigEntry
        MAX-ACCESS     not-accessible
        STATUS         current
        DESCRIPTION    "."
        INDEX { ifIndex }
        ::= { tnIroadm9rPortConfigTable 1 }

    TnIroadm9rPortConfigEntry ::=
        SEQUENCE {
            tnIroadm9rPortConfigFunction INTEGER
        }
    tnIroadm9rPortConfigFunction OBJECT-TYPE
        SYNTAX         INTEGER {
                         lineIn(1),
                         inv(2),
                         osc(3),
                         lineOut(4),
                         oscSfp(5),
                         adt(6),
                         otdrRx(7),
                         otdrTx(8),
                         custLan(9)
                       }
        MAX-ACCESS     read-only
        STATUS         current
        DESCRIPTION    "Indicates the functional type of this IROADM9R port."
        ::= { tnIroadm9rPortConfigEntry 1 }

--------------------------------------------------------------------------------
-- RA2P96 Optical Port Config Scalar
--------------------------------------------------------------------------------
    tnRa2p96PortConfigAttributeTotal OBJECT-TYPE
        SYNTAX         Integer32
        MAX-ACCESS     read-only
        STATUS         current
        DESCRIPTION    "."
        ::= { tnOpticalPortConfig 411 }

--------------------------------------------------------------------------------
-- RA2P96 Optical Port Config Table
--------------------------------------------------------------------------------
    tnRa2p96PortConfigTable OBJECT-TYPE
        SYNTAX         SEQUENCE OF TnRa2p96PortConfigEntry
        MAX-ACCESS     not-accessible
        STATUS         current
        DESCRIPTION    "The ports on a RA2P96 optical card."
        ::= { tnOpticalPortConfig 412 }

    tnRa2p96PortConfigEntry OBJECT-TYPE
        SYNTAX         TnRa2p96PortConfigEntry
        MAX-ACCESS     not-accessible
        STATUS         current
        DESCRIPTION    "."
        INDEX { ifIndex }
        ::= { tnRa2p96PortConfigTable 1 }

    TnRa2p96PortConfigEntry ::=
        SEQUENCE {
            tnRa2p96PortConfigFunction INTEGER
        }

    tnRa2p96PortConfigFunction OBJECT-TYPE
        SYNTAX         INTEGER {
                         lineIn(1),
                         lineOut(2),
                         oscOut(3),
                         otdrRx(4)
                       }
        MAX-ACCESS     read-only
        STATUS         current
        DESCRIPTION    "Indicates the functional type of this Ra2p96 port."
        ::= { tnRa2p96PortConfigEntry 1 }

--------------------------------------------------------------------------------
-- OTDRM (Optical Time Domain Reflectometer) Optical Port Config Scalar
--------------------------------------------------------------------------------
    tnOtdrmPortConfigAttributeTotal OBJECT-TYPE
        SYNTAX         Integer32
        MAX-ACCESS     read-only
        STATUS         current
        DESCRIPTION    "."
        ::= { tnOpticalPortConfig 413 }

--------------------------------------------------------------------------------
-- OTDRM (Optical Time Domain Reflectometer) Optical Port Config Table
--------------------------------------------------------------------------------
    tnOtdrmPortConfigTable OBJECT-TYPE
        SYNTAX         SEQUENCE OF TnOtdrmPortConfigEntry
        MAX-ACCESS     not-accessible
        STATUS         current
        DESCRIPTION    "The ports on an OTDRM optical card."
        ::= { tnOpticalPortConfig 414 }

    tnOtdrmPortConfigEntry OBJECT-TYPE
        SYNTAX         TnOtdrmPortConfigEntry
        MAX-ACCESS     not-accessible
        STATUS         current
        DESCRIPTION    "."
        INDEX { ifIndex }
        ::= { tnOtdrmPortConfigTable 1 }

    TnOtdrmPortConfigEntry ::=
        SEQUENCE {
            tnOtdrmPortConfigFunction        INTEGER,
            tnOtdrmPortConfigConnAddress     Integer32
        }

    tnOtdrmPortConfigFunction OBJECT-TYPE
        SYNTAX         INTEGER {
                         px(1)
                       }
        MAX-ACCESS     read-only
        STATUS         current
        DESCRIPTION    "Indicates the functional type of this Otdrm port."
        ::= { tnOtdrmPortConfigEntry 1 }

    tnOtdrmPortConfigConnAddress OBJECT-TYPE
        SYNTAX         Integer32 (-1..2147483647)
        MAX-ACCESS     read-create
        STATUS         current
        DESCRIPTION    "Specifies the assigned LD port that is connected
                        to the OTDRM port."
        ::= { tnOtdrmPortConfigEntry 2 }

--------------------------------------------------------------------------------
-- 12CE120 Optical Port Config Scalar
--------------------------------------------------------------------------------
    tn12ce120PortConfigAttributeTotal OBJECT-TYPE
        SYNTAX         Integer32
        MAX-ACCESS     read-only
        STATUS         current
        DESCRIPTION    "."
        ::= { tnOpticalPortConfig 415 }

-------------------------------------------------------------------------------
-- 12CE120 Optical Port Config Table
-------------------------------------------------------------------------------
    tn12ce120PortConfigTable OBJECT-TYPE
        SYNTAX         SEQUENCE OF Tn12ce120PortConfigEntry
        MAX-ACCESS     not-accessible
        STATUS         current
        DESCRIPTION    "The ports on a 12CE120 optical card."
        ::= { tnOpticalPortConfig 416 }

    tn12ce120PortConfigEntry OBJECT-TYPE
        SYNTAX         Tn12ce120PortConfigEntry
        MAX-ACCESS     not-accessible
        STATUS         current
        DESCRIPTION    "."
        INDEX { ifIndex }
        ::= { tn12ce120PortConfigTable 1 }

    Tn12ce120PortConfigEntry ::=
        SEQUENCE {
            tn12ce120PortConfigFunction INTEGER
        }

    tn12ce120PortConfigFunction OBJECT-TYPE
        SYNTAX         INTEGER {
                         network(1),
                         client(2),
                         backplane(3),
                         tod(4),
                         ethman(5)
                       }
        MAX-ACCESS     read-only
        STATUS         current
        DESCRIPTION    "Indicates the functional type of this 12CE120 port."
        ::= { tn12ce120PortConfigEntry 1 }

--------------------------------------------------------------------------------
-- 20AN80 Optical Port Config Scalar
--------------------------------------------------------------------------------
    tn20an80PortConfigAttributeTotal OBJECT-TYPE
        SYNTAX         Integer32
        MAX-ACCESS     read-only
        STATUS         current
        DESCRIPTION    "."
        ::= { tnOpticalPortConfig 417 }

--------------------------------------------------------------------------------
-- 20AN80 Optical Port Config Table
--------------------------------------------------------------------------------
    tn20an80PortConfigTable OBJECT-TYPE
        SYNTAX         SEQUENCE OF Tn20an80PortConfigEntry
        MAX-ACCESS     not-accessible
        STATUS         current
        DESCRIPTION    "The ports on a 20an80 optical card."
        ::= { tnOpticalPortConfig 418 }

    tn20an80PortConfigEntry OBJECT-TYPE
        SYNTAX         Tn20an80PortConfigEntry
        MAX-ACCESS     not-accessible
        STATUS         current
        DESCRIPTION    "."
        INDEX { ifIndex }
        ::= { tn20an80PortConfigTable 1 }

    Tn20an80PortConfigEntry ::= SEQUENCE {
        tn20an80PortConfigFunction INTEGER
    }

    tn20an80PortConfigFunction OBJECT-TYPE
        SYNTAX         INTEGER {
                         port(1)
                       }
        MAX-ACCESS     read-only
        STATUS         current
        DESCRIPTION    "Indicates the functional type of
                        this 20an80 port."
        ::= { tn20an80PortConfigEntry 1 }

--------------------------------------------------------------------------------
-- 10AN400 Optical Port Config Scalar
--------------------------------------------------------------------------------
    tn10an400PortConfigAttributeTotal OBJECT-TYPE
        SYNTAX         Integer32
        MAX-ACCESS     read-only
        STATUS         current
        DESCRIPTION    "."
        ::= { tnOpticalPortConfig 419 }

--------------------------------------------------------------------------------
-- 10AN400 Optical Port Config Table
--------------------------------------------------------------------------------
    tn10an400PortConfigTable OBJECT-TYPE
        SYNTAX         SEQUENCE OF Tn10an400PortConfigEntry
        MAX-ACCESS     not-accessible
        STATUS         current
        DESCRIPTION    "The ports on a 10an400 optical card."
        ::= { tnOpticalPortConfig 420 }

    tn10an400PortConfigEntry OBJECT-TYPE
        SYNTAX         Tn10an400PortConfigEntry
        MAX-ACCESS     not-accessible
        STATUS         current
        DESCRIPTION    "."
        INDEX { ifIndex }
        ::= { tn10an400PortConfigTable 1 }

    Tn10an400PortConfigEntry ::= SEQUENCE {
        tn10an400PortConfigFunction INTEGER
    }

    tn10an400PortConfigFunction OBJECT-TYPE
        SYNTAX         INTEGER {
                         port(1)
                       }
        MAX-ACCESS     read-only
        STATUS         current
        DESCRIPTION    "Indicates the functional type of
                        this 10an400 port."
        ::= { tn10an400PortConfigEntry 1 }

--------------------------------------------------------------------------------
-- 8P20 Optical Port Config Scalar
--------------------------------------------------------------------------------
    tn8p20PortConfigAttributeTotal OBJECT-TYPE
        SYNTAX         Integer32
        MAX-ACCESS     read-only
        STATUS         current
        DESCRIPTION    "."
        ::= { tnOpticalPortConfig 421 }

--------------------------------------------------------------------------------
-- 8P20 Optical Port Config Table
--------------------------------------------------------------------------------
    tn8p20PortConfigTable OBJECT-TYPE
        SYNTAX         SEQUENCE OF Tn8p20PortConfigEntry
        MAX-ACCESS     not-accessible
        STATUS         current
        DESCRIPTION    "The ports on a 8P20 optical card."
        ::= { tnOpticalPortConfig 422 }

    tn8p20PortConfigEntry OBJECT-TYPE
        SYNTAX         Tn8p20PortConfigEntry
        MAX-ACCESS     not-accessible
        STATUS         current
        DESCRIPTION    "."
        INDEX { ifIndex }
        ::= { tn8p20PortConfigTable 1 }

    Tn8p20PortConfigEntry ::=
        SEQUENCE {
            tn8p20PortConfigFunction INTEGER
        }

    tn8p20PortConfigFunction OBJECT-TYPE
        SYNTAX         INTEGER {
                         network(1),
                         client(2),
                         evoa(3),
                         backplane(4)
                       }
        MAX-ACCESS     read-only
        STATUS         current
        DESCRIPTION    "Indicates the functional type of this 8P20 port."
        ::= { tn8p20PortConfigEntry 1 }

--------------------------------------------------------------------------------
-- OPSFLEX Optical Port Config Scalar
--------------------------------------------------------------------------------
    tnOpsflexPortConfigAttributeTotal OBJECT-TYPE
        SYNTAX         Integer32
        MAX-ACCESS     read-only
        STATUS         current
        DESCRIPTION    "."
        ::= { tnOpticalPortConfig 423 }

--------------------------------------------------------------------------------
-- OPSFLEX Optical Port Config Table
--------------------------------------------------------------------------------
    tnOpsflexPortConfigTable OBJECT-TYPE
        SYNTAX         SEQUENCE OF TnOpsflexPortConfigEntry
        MAX-ACCESS     not-accessible
        STATUS         current
        DESCRIPTION    "The ports on an OPSFLEX optical card."
        ::= { tnOpticalPortConfig 424 }

    tnOpsflexPortConfigEntry OBJECT-TYPE
        SYNTAX         TnOpsflexPortConfigEntry
        MAX-ACCESS     not-accessible
        STATUS         current
        DESCRIPTION    "."
        INDEX { ifIndex }
        ::= { tnOpsflexPortConfigTable 1 }

    TnOpsflexPortConfigEntry ::=
        SEQUENCE {
            tnOpsflexPortConfigFunction     INTEGER
        }

    tnOpsflexPortConfigFunction OBJECT-TYPE
        SYNTAX         INTEGER {
                         signal(1),
                         workingProtected(2)
                       }
        MAX-ACCESS     read-only
        STATUS         current
        DESCRIPTION    "Indicates the functional type of this Opsflex port."
        ::= { tnOpsflexPortConfigEntry 1 }

--------------------------------------------------------------------------------
-- D5X500Q Optical Port Config Scalar
--------------------------------------------------------------------------------
    tnD5x500qPortConfigAttributeTotal OBJECT-TYPE
        SYNTAX         Integer32
        MAX-ACCESS     read-only
        STATUS         current
        DESCRIPTION    "."
        ::= { tnOpticalPortConfig 425 }

--------------------------------------------------------------------------------
-- D5X500Q Optical Port Config Table
--------------------------------------------------------------------------------
    tnD5x500qPortConfigTable OBJECT-TYPE
        SYNTAX         SEQUENCE OF TnD5x500qPortConfigEntry
        MAX-ACCESS     not-accessible
        STATUS         current
        DESCRIPTION    "The ports on a D5X500Q optical card."
        ::= { tnOpticalPortConfig 426 }

    tnD5x500qPortConfigEntry OBJECT-TYPE
        SYNTAX         TnD5x500qPortConfigEntry
        MAX-ACCESS     not-accessible
        STATUS         current
        DESCRIPTION    "."
        INDEX { ifIndex }
        ::= { tnD5x500qPortConfigTable 1 }

    TnD5x500qPortConfigEntry ::=
        SEQUENCE {
            tnD5x500qPortConfigFunction INTEGER
        }

    tnD5x500qPortConfigFunction OBJECT-TYPE
        SYNTAX         INTEGER {
                         network(1),
                         client(2),
                         backplane(3)
                       }
        MAX-ACCESS     read-only
        STATUS         current
        DESCRIPTION    "Indicates the functional type of this D5x500q port."
        ::= { tnD5x500qPortConfigEntry 1 }

--------------------------------------------------------------------------------
-- 18P40 Optical Port Config Scalar
--------------------------------------------------------------------------------
    tn18p40PortConfigAttributeTotal OBJECT-TYPE
        SYNTAX         Integer32
        MAX-ACCESS     read-only
        STATUS         current
        DESCRIPTION    "."
        ::= { tnOpticalPortConfig 427 }

--------------------------------------------------------------------------------
-- 18P40 Optical Port Config Table
--------------------------------------------------------------------------------
    tn18p40PortConfigTable OBJECT-TYPE
        SYNTAX         SEQUENCE OF Tn18p40PortConfigEntry
        MAX-ACCESS     not-accessible
        STATUS         current
        DESCRIPTION    "The ports on a 18P40 optical card."
        ::= { tnOpticalPortConfig 428 }

    tn18p40PortConfigEntry OBJECT-TYPE
        SYNTAX         Tn18p40PortConfigEntry
        MAX-ACCESS     not-accessible
        STATUS         current
        DESCRIPTION    "."
        INDEX { ifIndex }
        ::= { tn18p40PortConfigTable 1 }

    Tn18p40PortConfigEntry ::=
        SEQUENCE {
            tn18p40PortConfigFunction INTEGER
        }

    tn18p40PortConfigFunction OBJECT-TYPE
        SYNTAX         INTEGER {
                         network(1),
                         client(2),
                         evoa(3),
                         backplane(4)
                       }
        MAX-ACCESS     read-only
        STATUS         current
        DESCRIPTION    "Indicates the functional type of this 18P40 port."
        ::= { tn18p40PortConfigEntry 1 }

--------------------------------------------------------------------------------
-- DA2C4 Optical Port Config Scalar
--------------------------------------------------------------------------------
    tnDa2c4PortConfigAttributeTotal OBJECT-TYPE
        SYNTAX         Integer32
        MAX-ACCESS     read-only
        STATUS         current
        DESCRIPTION    "."
        ::= { tnOpticalPortConfig 429 }

--------------------------------------------------------------------------------
-- DA2C4 Optical Port Config Table
--------------------------------------------------------------------------------
    tnDa2c4PortConfigTable OBJECT-TYPE
        SYNTAX         SEQUENCE OF TnDa2c4PortConfigEntry
        MAX-ACCESS     not-accessible
        STATUS         current
        DESCRIPTION    "The ports on a Da2c4 optical card."
        ::= { tnOpticalPortConfig 430 }

    tnDa2c4PortConfigEntry OBJECT-TYPE
        SYNTAX         TnDa2c4PortConfigEntry
        MAX-ACCESS     not-accessible
        STATUS         current
        DESCRIPTION    "."
        INDEX { ifIndex }
        ::= { tnDa2c4PortConfigTable 1 }

    TnDa2c4PortConfigEntry ::=
        SEQUENCE {
            tnDa2c4PortConfigFunction INTEGER
        }

    tnDa2c4PortConfigFunction OBJECT-TYPE
        SYNTAX         INTEGER {
                         network(1),
                         client(2)
                       }
        MAX-ACCESS     read-only
        STATUS         current
        DESCRIPTION    "Indicates the functional type of this Da2c4 port."
        ::= { tnDa2c4PortConfigEntry 1 }

--------------------------------------------------------------------------------
-- 130SLA1 Optical Port Config Scalar
--------------------------------------------------------------------------------
    tn130sla1PortConfigAttributeTotal OBJECT-TYPE
        SYNTAX         Integer32
        MAX-ACCESS     read-only
        STATUS         current
        DESCRIPTION    "."
        ::= { tnOpticalPortConfig 431 }

--------------------------------------------------------------------------------
-- 130SLA1 Optical Port Config Table
--------------------------------------------------------------------------------
    tn130sla1PortConfigTable OBJECT-TYPE
        SYNTAX         SEQUENCE OF Tn130sla1PortConfigEntry
        MAX-ACCESS     not-accessible
        STATUS         current
        DESCRIPTION    "The ports on a 130SLA1 optical card."
        ::= { tnOpticalPortConfig 432 }

    tn130sla1PortConfigEntry OBJECT-TYPE
        SYNTAX         Tn130sla1PortConfigEntry
        MAX-ACCESS     not-accessible
        STATUS         current
        DESCRIPTION    "."
        INDEX { ifIndex }
        ::= { tn130sla1PortConfigTable 1 }

    Tn130sla1PortConfigEntry ::=
        SEQUENCE {
            tn130sla1PortConfigFunction INTEGER
        }

    tn130sla1PortConfigFunction OBJECT-TYPE
        SYNTAX         INTEGER {
                         network(1),
                         client(2)
                       }
        MAX-ACCESS     read-only
        STATUS         current
        DESCRIPTION    "Indicates the functional type of this 130SLA1 port."
        ::= { tn130sla1PortConfigEntry 1 }

--------------------------------------------------------------------------------
-- 130SLX10 Optical Port Config Scalar
--------------------------------------------------------------------------------
    tn130slx10PortConfigAttributeTotal OBJECT-TYPE
        SYNTAX         Integer32
        MAX-ACCESS     read-only
        STATUS         current
        DESCRIPTION    "."
        ::= { tnOpticalPortConfig 433 }

--------------------------------------------------------------------------------
-- 130SLX10 Optical Port Config Table
--------------------------------------------------------------------------------
    tn130slx10PortConfigTable OBJECT-TYPE
        SYNTAX         SEQUENCE OF Tn130slx10PortConfigEntry
        MAX-ACCESS     not-accessible
        STATUS         current
        DESCRIPTION    "The ports on a 130SLX10 optical card."
        ::= { tnOpticalPortConfig 434 }

    tn130slx10PortConfigEntry OBJECT-TYPE
        SYNTAX         Tn130slx10PortConfigEntry
        MAX-ACCESS     not-accessible
        STATUS         current
        DESCRIPTION    "."
        INDEX { ifIndex }
        ::= { tn130slx10PortConfigTable 1 }

    Tn130slx10PortConfigEntry ::=
        SEQUENCE {
            tn130slx10PortConfigFunction  INTEGER
        }

    tn130slx10PortConfigFunction OBJECT-TYPE
        SYNTAX         INTEGER {
                         network(1),
                         client(2)
                       }
        MAX-ACCESS     read-only
        STATUS         current
        DESCRIPTION    "Indicates the functional type of this 130SLX10 port."
        ::= { tn130slx10PortConfigEntry 1 }

--------------------------------------------------------------------------------
-- PSS12x Power Filter Port Config Scalar
--------------------------------------------------------------------------------
    tnPSS12xPowerFilterPortConfigAttributeTotal OBJECT-TYPE
        SYNTAX         Integer32
        MAX-ACCESS     read-only
        STATUS         current
        DESCRIPTION    "."
        ::= { tnOpticalPortConfig 435 }

--------------------------------------------------------------------------------
-- PSS12x Power Filter Port Config Table
--------------------------------------------------------------------------------
    tnPSS12xPowerFilterPortConfigTable OBJECT-TYPE
        SYNTAX         SEQUENCE OF TnPSS12xPowerFilterPortConfigEntry
        MAX-ACCESS     not-accessible
        STATUS         current
        DESCRIPTION    "The ports on a PSS12xPowerFilter optical card."
        ::= { tnOpticalPortConfig 436 }

    tnPSS12xPowerFilterPortConfigEntry OBJECT-TYPE
        SYNTAX         TnPSS12xPowerFilterPortConfigEntry
        MAX-ACCESS     not-accessible
        STATUS         current
        DESCRIPTION    "."
        INDEX { ifIndex }
        ::= { tnPSS12xPowerFilterPortConfigTable 1 }

    TnPSS12xPowerFilterPortConfigEntry ::=
        SEQUENCE {
            tnPSS12xPowerFilterPortConfigFunction  INTEGER,
            tnPSS12xExpectedAmps                   Unsigned32
        }

    tnPSS12xPowerFilterPortConfigFunction OBJECT-TYPE
        SYNTAX         INTEGER {
                         powerFilterPort1(1),
                         powerFilterPort2(2),
                         powerFilterPort3(3)
                       }
        MAX-ACCESS     read-only
        STATUS         current
        DESCRIPTION    "Indicates the functional type of this PSS12x PowerFilter port."
        ::= { tnPSS12xPowerFilterPortConfigEntry 1 }

    tnPSS12xExpectedAmps OBJECT-TYPE
        SYNTAX         Unsigned32
        MAX-ACCESS     read-create
        STATUS         current
        DESCRIPTION    "Displays the configured expected amps of the circuit
                        breaker of the power branch.

                        auto - value 4 is mapped internally."
        DEFVAL         { 60 }
        ::= { tnPSS12xPowerFilterPortConfigEntry 2 }

--------------------------------------------------------------------------------
-- IROADM20 Optical Port Config Scalar
--------------------------------------------------------------------------------
    tnIroadm20PortConfigAttributeTotal OBJECT-TYPE
        SYNTAX         Integer32
        MAX-ACCESS     read-only
        STATUS         current
        DESCRIPTION    "."
        ::= { tnOpticalPortConfig 437 }

--------------------------------------------------------------------------------
-- IROADM20 Optical Port Config Table
--------------------------------------------------------------------------------
    tnIroadm20PortConfigTable OBJECT-TYPE
        SYNTAX         SEQUENCE OF TnIroadm20PortConfigEntry
        MAX-ACCESS     not-accessible
        STATUS         current
        DESCRIPTION    "The ports on a IROADM20 optical card."
        ::= { tnOpticalPortConfig 438 }

    tnIroadm20PortConfigEntry OBJECT-TYPE
        SYNTAX         TnIroadm20PortConfigEntry
        MAX-ACCESS     not-accessible
        STATUS         current
        DESCRIPTION    "."
        INDEX { ifIndex }
        ::= { tnIroadm20PortConfigTable 1 }

    TnIroadm20PortConfigEntry ::=
        SEQUENCE {
            tnIroadm20PortConfigFunction INTEGER
        }
    tnIroadm20PortConfigFunction OBJECT-TYPE
        SYNTAX         INTEGER {
                         lineIn(1),
                         inv(2),
                         osc(3),
                         lineOut(4),
                         oscSfp(5),
                         adt(6),
                         otdrRx(7),
                         otdrTx(8),
                         custLan(9),
                         testLaser(10),
                         mpoAddDrop(11)
                       }
        MAX-ACCESS     read-only
        STATUS         current
        DESCRIPTION    "Indicates the functional type of this IROADM20 port."
        ::= { tnIroadm20PortConfigEntry 1 }

--------------------------------------------------------------------------------
-- S2AD200 Optical Port Config Scalar
--------------------------------------------------------------------------------
    tnS2ad200PortConfigAttributeTotal OBJECT-TYPE
        SYNTAX         Integer32
        MAX-ACCESS     read-only
        STATUS         current
        DESCRIPTION    "."
        ::= { tnOpticalPortConfig 439 }

--------------------------------------------------------------------------------
-- S2AD200 Optical Port Config Table
--------------------------------------------------------------------------------
    tnS2ad200PortConfigTable OBJECT-TYPE
        SYNTAX         SEQUENCE OF TnS2ad200PortConfigEntry
        MAX-ACCESS     not-accessible
        STATUS         current
        DESCRIPTION    "The ports on a S2AD200 optical card."
        ::= { tnOpticalPortConfig 440 }

    tnS2ad200PortConfigEntry OBJECT-TYPE
        SYNTAX         TnS2ad200PortConfigEntry
        MAX-ACCESS     not-accessible
        STATUS         current
        DESCRIPTION    "."
        INDEX { ifIndex }
        ::= { tnS2ad200PortConfigTable 1 }

    TnS2ad200PortConfigEntry ::=
        SEQUENCE {
            tnS2ad200PortConfigFunction INTEGER
        }
    tnS2ad200PortConfigFunction OBJECT-TYPE
        SYNTAX         INTEGER {
                         network(1),
                         client(2)
                       }
        MAX-ACCESS     read-only
        STATUS         current
        DESCRIPTION    "Indicates the functional type of this S2AD200 port."
        ::= { tnS2ad200PortConfigEntry 1 }

--------------------------------------------------------------------------------
-- MSH4-FSB Optical Port Config Scalar
--------------------------------------------------------------------------------
    tnMsh4fsbPortConfigAttributeTotal OBJECT-TYPE
        SYNTAX         Integer32
        MAX-ACCESS     read-only
        STATUS         current
        DESCRIPTION    "."
        ::= { tnOpticalPortConfig 441 }

--------------------------------------------------------------------------------
-- MSH4-FSB Optical Port Config Table
--------------------------------------------------------------------------------
    tnMsh4fsbPortConfigTable OBJECT-TYPE
        SYNTAX         SEQUENCE OF TnMsh4fsbPortConfigEntry
        MAX-ACCESS     not-accessible
        STATUS         current
        DESCRIPTION    "The ports on a MSH4-FSB optical card."
        ::= { tnOpticalPortConfig 442 }

    tnMsh4fsbPortConfigEntry OBJECT-TYPE
        SYNTAX         TnMsh4fsbPortConfigEntry
        MAX-ACCESS     not-accessible
        STATUS         current
        DESCRIPTION    "."
        INDEX { ifIndex }
        ::= { tnMsh4fsbPortConfigTable 1 }

    TnMsh4fsbPortConfigEntry ::=
        SEQUENCE {
            tnMsh4fsbPortConfigFunction   INTEGER
        }

    tnMsh4fsbPortConfigFunction OBJECT-TYPE
        SYNTAX         INTEGER {
                         mpoWss(1),
                         mpoAde(2),
                         mpoAdm(3)
                       }
        MAX-ACCESS     read-only
        STATUS         current
        DESCRIPTION    "Indicates the functional type of this MSH4-FSB port."
        ::= { tnMsh4fsbPortConfigEntry 1 }

--------------------------------------------------------------------------------
-- 2UX200 Optical Port Config Scalar
--------------------------------------------------------------------------------
    tn2ux200PortConfigAttributeTotal OBJECT-TYPE
        SYNTAX         Integer32
        MAX-ACCESS     read-only
        STATUS         current
        DESCRIPTION    "."
        ::= { tnOpticalPortConfig 443 }

--------------------------------------------------------------------------------
-- 2UX200 Optical Port Config Table
--------------------------------------------------------------------------------
    tn2ux200PortConfigTable OBJECT-TYPE
        SYNTAX         SEQUENCE OF Tn2ux200PortConfigEntry
        MAX-ACCESS     not-accessible
        STATUS         current
        DESCRIPTION    "The ports on a 2UX200 optical card."
        ::= { tnOpticalPortConfig 444 }

    tn2ux200PortConfigEntry OBJECT-TYPE
        SYNTAX         Tn2ux200PortConfigEntry
        MAX-ACCESS     not-accessible
        STATUS         current
        DESCRIPTION    "."
        INDEX { ifIndex }
        ::= { tn2ux200PortConfigTable 1 }

    Tn2ux200PortConfigEntry ::=
        SEQUENCE {
            tn2ux200PortConfigFunction INTEGER
        }
    tn2ux200PortConfigFunction OBJECT-TYPE
        SYNTAX         INTEGER {
                         network(1)
                       }
        MAX-ACCESS     read-only
        STATUS         current
        DESCRIPTION    "Indicates the functional type of this 2UX200 port."
        ::= { tn2ux200PortConfigEntry 1 }

--------------------------------------------------------------------------------
-- 4MX200 Optical Port Config Scalar
--------------------------------------------------------------------------------
    tn4mx200PortConfigAttributeTotal OBJECT-TYPE
        SYNTAX         Integer32
        MAX-ACCESS     read-only
        STATUS         current
        DESCRIPTION    "."
        ::= { tnOpticalPortConfig 445 }

--------------------------------------------------------------------------------
-- 4MX200 Optical Port Config Table
--------------------------------------------------------------------------------
    tn4mx200PortConfigTable OBJECT-TYPE
        SYNTAX         SEQUENCE OF Tn4mx200PortConfigEntry
        MAX-ACCESS     not-accessible
        STATUS         current
        DESCRIPTION    "The ports on a 4MX200 optical card."
        ::= { tnOpticalPortConfig 446 }

    tn4mx200PortConfigEntry OBJECT-TYPE
        SYNTAX         Tn4mx200PortConfigEntry
        MAX-ACCESS     not-accessible
        STATUS         current
        DESCRIPTION    "."
        INDEX { ifIndex }
        ::= { tn4mx200PortConfigTable 1 }

    Tn4mx200PortConfigEntry ::=
        SEQUENCE {
            tn4mx200PortConfigFunction INTEGER
        }
    tn4mx200PortConfigFunction OBJECT-TYPE
        SYNTAX         INTEGER {
                         client(1)
                       }
        MAX-ACCESS     read-only
        STATUS         current
        DESCRIPTION    "Indicates the functional type of this 4MX200 port."
        ::= { tn4mx200PortConfigEntry 1 }

--------------------------------------------------------------------------------
-- OPSB5 Optical Port Config Scalar
--------------------------------------------------------------------------------
    tnOpsb5PortConfigAttributeTotal OBJECT-TYPE
        SYNTAX         Integer32
        MAX-ACCESS     read-only
        STATUS         current
        DESCRIPTION    "."
        ::= { tnOpticalPortConfig 447 }

--------------------------------------------------------------------------------
-- OPSB5 Optical Port Config Table
--------------------------------------------------------------------------------
    tnOpsb5PortConfigTable OBJECT-TYPE
        SYNTAX         SEQUENCE OF TnOpsb5PortConfigEntry
        MAX-ACCESS     not-accessible
        STATUS         current
        DESCRIPTION    "The ports on an OPSB5 optical card."
        ::= { tnOpticalPortConfig 448 }

    tnOpsb5PortConfigEntry OBJECT-TYPE
        SYNTAX         TnOpsb5PortConfigEntry
        MAX-ACCESS     not-accessible
        STATUS         current
        DESCRIPTION    "."
        INDEX { ifIndex }
        ::= { tnOpsb5PortConfigTable 1 }

    TnOpsb5PortConfigEntry ::=
        SEQUENCE {
            tnOpsb5PortConfigFunction     INTEGER
        }

    tnOpsb5PortConfigFunction OBJECT-TYPE
        SYNTAX         INTEGER {
                         signal(1),
                         workingProtected(2)
                       }
        MAX-ACCESS     read-only
        STATUS         current
        DESCRIPTION    "Indicates the functional type of this OPSB5 port."
        ::= { tnOpsb5PortConfigEntry 1 }

--------------------------------------------------------------------------------
-- ASWG-L Optical Port Config Scalar
--------------------------------------------------------------------------------
    tnAswglPortConfigAttributeTotal OBJECT-TYPE
        SYNTAX         Integer32
        MAX-ACCESS     read-only
        STATUS         current
        DESCRIPTION    "."
        ::= { tnOpticalPortConfig 449 }

--------------------------------------------------------------------------------
-- ASWG-L Optical Port Config Table
--------------------------------------------------------------------------------
    tnAswglPortConfigTable OBJECT-TYPE
        SYNTAX         SEQUENCE OF TnAswglPortConfigEntry
        MAX-ACCESS     not-accessible
        STATUS         current
        DESCRIPTION    "The ports on an ASWG-L optical card."
        ::= { tnOpticalPortConfig 450 }

    tnAswglPortConfigEntry OBJECT-TYPE
        SYNTAX         TnAswglPortConfigEntry
        MAX-ACCESS     not-accessible
        STATUS         current
        DESCRIPTION    "."
        INDEX { ifIndex }
        ::= { tnAswglPortConfigTable 1 }

    TnAswglPortConfigEntry ::=
        SEQUENCE {
            tnAswglPortConfigFunction INTEGER
        }

    tnAswglPortConfigFunction OBJECT-TYPE
        SYNTAX         INTEGER {
                         lineIn(1),
                         otdrRx(2),
                         otdrTx(3),
                         lineOut(4),
                         oscSfp(5),
                         osc(6),
                         custLan(7)
                       }
        MAX-ACCESS     read-only
        STATUS         current
        DESCRIPTION    "Indicates the functional type of this ASWG-L port."
        ::= { tnAswglPortConfigEntry 1 }

--------------------------------------------------------------------------------
-- IPREAMP Optical Port Config Scalar
--------------------------------------------------------------------------------
    tnIpreampPortConfigAttributeTotal OBJECT-TYPE
        SYNTAX         Integer32
        MAX-ACCESS     read-only
        STATUS         current
        DESCRIPTION    "."
        ::= { tnOpticalPortConfig 451 }

--------------------------------------------------------------------------------
-- IPREAMP Optical Port Config Table
--------------------------------------------------------------------------------
    tnIpreampPortConfigTable OBJECT-TYPE
        SYNTAX         SEQUENCE OF TnIpreampPortConfigEntry
        MAX-ACCESS     not-accessible
        STATUS         current
        DESCRIPTION    "The ports on a IPREAMP optical card."
        ::= { tnOpticalPortConfig 452 }

    tnIpreampPortConfigEntry OBJECT-TYPE
        SYNTAX         TnIpreampPortConfigEntry
        MAX-ACCESS     not-accessible
        STATUS         current
        DESCRIPTION    "."
        INDEX { ifIndex }
        ::= { tnIpreampPortConfigTable 1 }

    TnIpreampPortConfigEntry ::=
        SEQUENCE {
            tnIpreampPortConfigFunction INTEGER
        }
    tnIpreampPortConfigFunction OBJECT-TYPE
        SYNTAX         INTEGER {
                         lineIn(1),
                         sigOut(2),
                         sigIn(3),
                         lineOut(4),
                         oscSfp(5),
                         osc(6),
                         otdrRx(7),
                         otdrTx(8),
                         custLan(9)
                       }
        MAX-ACCESS     read-only
        STATUS         current
        DESCRIPTION    "Indicates the functional type of this IPREAMP port."
        ::= { tnIpreampPortConfigEntry 1 }


--    obsolete
--    tn40cx800PortConfigAttributeTotal OBJECT-TYPE ::= { tnOpticalPortConfig 453 }
--    tn40cx800PortConfigTable          OBJECT-TYPE ::= { tnOpticalPortConfig 454 }

--------------------------------------------------------------------------------
-- IRDM32 Optical Port Config Scalar
--------------------------------------------------------------------------------
    tnIrdm32PortConfigAttributeTotal OBJECT-TYPE
        SYNTAX         Integer32
        MAX-ACCESS     read-only
        STATUS         current
        DESCRIPTION    "."
        ::= { tnOpticalPortConfig 455 }

--------------------------------------------------------------------------------
-- IRDM32 Optical Port Config Table
--------------------------------------------------------------------------------
    tnIrdm32PortConfigTable OBJECT-TYPE
        SYNTAX         SEQUENCE OF TnIrdm32PortConfigEntry
        MAX-ACCESS     not-accessible
        STATUS         current
        DESCRIPTION    "The ports on a IRDM32 optical card."
        ::= { tnOpticalPortConfig 456 }

    tnIrdm32PortConfigEntry OBJECT-TYPE
        SYNTAX         TnIrdm32PortConfigEntry
        MAX-ACCESS     not-accessible
        STATUS         current
        DESCRIPTION    "."
        INDEX { ifIndex }
        ::= { tnIrdm32PortConfigTable 1 }

    TnIrdm32PortConfigEntry ::=
        SEQUENCE {
            tnIrdm32PortConfigFunction INTEGER
        }
    tnIrdm32PortConfigFunction OBJECT-TYPE
        SYNTAX         INTEGER {
                         lineIn(1),
                         inv(2),
                         osc(3),
                         lineOut(4),
                         oscSfp(5),
                         adt(6),
                         lineLoading(7),
                         otdrRx(8),
                         otdrTx(9),
                         custLan(10),
                         testLaser(11),
                         mpoFs(12),
                         oscLan(13)
                       }
        MAX-ACCESS     read-only
        STATUS         current
        DESCRIPTION    "Indicates the functional type of this IRDM32 port."
        ::= { tnIrdm32PortConfigEntry 1 }

--------------------------------------------------------------------------------
-- RA4P Optical Port Config Scalar
--------------------------------------------------------------------------------
    tnRa4pPortConfigAttributeTotal OBJECT-TYPE
        SYNTAX         Integer32
        MAX-ACCESS     read-only
        STATUS         current
        DESCRIPTION    "."
        ::= { tnOpticalPortConfig 457 }

--------------------------------------------------------------------------------
-- RA4P Optical Port Config Table
--------------------------------------------------------------------------------
    tnRa4pPortConfigTable OBJECT-TYPE
        SYNTAX         SEQUENCE OF TnRa4pPortConfigEntry
        MAX-ACCESS     not-accessible
        STATUS         current
        DESCRIPTION    "The ports on a RA4P optical card."
        ::= { tnOpticalPortConfig 458 }

    tnRa4pPortConfigEntry OBJECT-TYPE
        SYNTAX         TnRa4pPortConfigEntry
        MAX-ACCESS     not-accessible
        STATUS         current
        DESCRIPTION    "."
        INDEX { ifIndex }
        ::= { tnRa4pPortConfigTable 1 }

    TnRa4pPortConfigEntry ::=
        SEQUENCE {
            tnRa4pPortConfigFunction INTEGER
        }

    tnRa4pPortConfigFunction OBJECT-TYPE
        SYNTAX         INTEGER {
                         lineIn(1),
                         lineOut(2),
                         oscOut(3)
                       }
        MAX-ACCESS     read-only
        STATUS         current
        DESCRIPTION    "Indicates the functional type of this RA4P port."
        ::= { tnRa4pPortConfigEntry 1 }

-------------------------------------------------------------------------------
-- EILA Optical Port Config Scalar
-------------------------------------------------------------------------------
    tnEilaPortConfigAttributeTotal OBJECT-TYPE
        SYNTAX         Integer32
        MAX-ACCESS     read-only
        STATUS         current
        DESCRIPTION    "."
        ::= { tnOpticalPortConfig 459 }

-------------------------------------------------------------------------------
-- EILA Optical Port Config Table
-------------------------------------------------------------------------------
    tnEilaPortConfigTable OBJECT-TYPE
        SYNTAX         SEQUENCE OF TnEilaPortConfigEntry
        MAX-ACCESS     not-accessible
        STATUS         current
        DESCRIPTION    "The ports on a EILA optical card."
        ::= { tnOpticalPortConfig 460 }

    tnEilaPortConfigEntry OBJECT-TYPE
        SYNTAX         TnEilaPortConfigEntry
        MAX-ACCESS     not-accessible
        STATUS         current
        DESCRIPTION    "."
        INDEX { ifIndex }
        ::= { tnEilaPortConfigTable 1 }

    TnEilaPortConfigEntry ::=
        SEQUENCE {
            tnEilaPortConfigFunction INTEGER
        }

    tnEilaPortConfigFunction OBJECT-TYPE
        SYNTAX         INTEGER {
                         lineIn(1),
                         otdrRx(2),
                         otdrTx(3),
                         lineOut(4),
                         oscSfp(5),
                         osc(6),
                         custLan(7),
                         inv(8),
                         oscLan(9)
                       }
        MAX-ACCESS     read-only
        STATUS         current
        DESCRIPTION    "Indicates the functional type of this EILA port."
        ::= { tnEilaPortConfigEntry 1 }

--    obsolete
--    tn8cx800PortConfigAttributeTotal OBJECT-TYPE ::= { tnOpticalPortConfig 461 }
--    tn8cx800PortConfigTable          OBJECT-TYPE ::= { tnOpticalPortConfig 462 }
--    tn6px800PortConfigAttributeTotal OBJECT-TYPE ::= { tnOpticalPortConfig 463 }
--    tn6px800PortConfigTable          OBJECT-TYPE ::= { tnOpticalPortConfig 464 }

--------------------------------------------------------------------------------
-- MCS16x15 Optical Port Config Scalar
--------------------------------------------------------------------------------
    tnMcs16x15PortConfigAttributeTotal OBJECT-TYPE
        SYNTAX         Integer32
        MAX-ACCESS     read-only
        STATUS         current
        DESCRIPTION    "."
        ::= { tnOpticalPortConfig 465 }

--------------------------------------------------------------------------------
-- MCS16x15 Optical Port Config Table
--------------------------------------------------------------------------------
    tnMcs16x15PortConfigTable OBJECT-TYPE
        SYNTAX         SEQUENCE OF TnMcs16x15PortConfigEntry
        MAX-ACCESS     not-accessible
        STATUS         current
        DESCRIPTION    "The ports on a MCS16x15 optical card."
        ::= { tnOpticalPortConfig 466 }

    tnMcs16x15PortConfigEntry OBJECT-TYPE
        SYNTAX         TnMcs16x15PortConfigEntry
        MAX-ACCESS     not-accessible
        STATUS         current
        DESCRIPTION    "."
        INDEX { ifIndex }
        ::= { tnMcs16x15PortConfigTable 1 }

    TnMcs16x15PortConfigEntry ::=
        SEQUENCE {
            tnMcs16x15PortConfigFunction   INTEGER
        }

    tnMcs16x15PortConfigFunction OBJECT-TYPE
        SYNTAX         INTEGER {
                         signal(1),
                         ad(2),
                         mpoAar(3)
                       }
        MAX-ACCESS     read-only
        STATUS         current
        DESCRIPTION    "Indicates the functional type of this MCS16x15 port."
        ::= { tnMcs16x15PortConfigEntry 1 }

--------------------------------------------------------------------------------
-- 10AN1T Optical Port Config Scalar
--------------------------------------------------------------------------------
    tn10an1tPortConfigAttributeTotal OBJECT-TYPE
        SYNTAX         Integer32
        MAX-ACCESS     read-only
        STATUS         current
        DESCRIPTION    "."
        ::= { tnOpticalPortConfig 467 }

--------------------------------------------------------------------------------
-- 10AN1T Optical Port Config Table
--------------------------------------------------------------------------------
    tn10an1tPortConfigTable OBJECT-TYPE
        SYNTAX         SEQUENCE OF Tn10an1tPortConfigEntry
        MAX-ACCESS     not-accessible
        STATUS         current
        DESCRIPTION    "The ports on a 10AN1T optical card."
        ::= { tnOpticalPortConfig 468 }

    tn10an1tPortConfigEntry OBJECT-TYPE
        SYNTAX         Tn10an1tPortConfigEntry
        MAX-ACCESS     not-accessible
        STATUS         current
        DESCRIPTION    "."
        INDEX { ifIndex }
        ::= { tn10an1tPortConfigTable 1 }

    Tn10an1tPortConfigEntry ::=
        SEQUENCE {
            tn10an1tPortConfigFunction INTEGER
        }

    tn10an1tPortConfigFunction OBJECT-TYPE
        SYNTAX         INTEGER {
                         client(1)
                       }
        MAX-ACCESS     read-only
        STATUS         current
        DESCRIPTION    "Indicates the functional type of this 10AN1T port."
        ::= { tn10an1tPortConfigEntry 1 }

--------------------------------------------------------------------------------
-- 8UC1T Optical Port Config Scalar
--------------------------------------------------------------------------------
    tn8uc1tPortConfigAttributeTotal OBJECT-TYPE
        SYNTAX         Integer32
        MAX-ACCESS     read-only
        STATUS         current
        DESCRIPTION    "."
        ::= { tnOpticalPortConfig 469 }

--------------------------------------------------------------------------------
-- 8UC1T Optical Port Config Table
--------------------------------------------------------------------------------
    tn8uc1tPortConfigTable OBJECT-TYPE
        SYNTAX         SEQUENCE OF Tn8uc1tPortConfigEntry
        MAX-ACCESS     not-accessible
        STATUS         current
        DESCRIPTION    "The ports on a 8UC1T optical card."
        ::= { tnOpticalPortConfig 470 }

    tn8uc1tPortConfigEntry OBJECT-TYPE
        SYNTAX         Tn8uc1tPortConfigEntry
        MAX-ACCESS     not-accessible
        STATUS         current
        DESCRIPTION    "."
        INDEX { ifIndex }
        ::= { tn8uc1tPortConfigTable 1 }

    Tn8uc1tPortConfigEntry ::=
        SEQUENCE {
            tn8uc1tPortConfigFunction INTEGER
        }

    tn8uc1tPortConfigFunction OBJECT-TYPE
        SYNTAX         INTEGER {
                         network(1)
                       }
        MAX-ACCESS     read-only
        STATUS         current
        DESCRIPTION    "Indicates the functional type of this 8UC1T port."
        ::= { tn8uc1tPortConfigEntry 1 }

--------------------------------------------------------------------------------
-- DFC12 Optical Port Config Scalar
--------------------------------------------------------------------------------
    tnDfc12PortConfigAttributeTotal OBJECT-TYPE
        SYNTAX         Integer32
        MAX-ACCESS     read-only
        STATUS         current
        DESCRIPTION    "."
        ::= { tnOpticalPortConfig 471 }

--------------------------------------------------------------------------------
-- DFC12 Optical Port Config Table
--------------------------------------------------------------------------------
    tnDfc12PortConfigTable OBJECT-TYPE
        SYNTAX         SEQUENCE OF TnDfc12PortConfigEntry
        MAX-ACCESS     not-accessible
        STATUS         current
        DESCRIPTION    "The ports on a Dfc12 optical card."
        ::= { tnOpticalPortConfig 472 }

    tnDfc12PortConfigEntry OBJECT-TYPE
        SYNTAX         TnDfc12PortConfigEntry
        MAX-ACCESS     not-accessible
        STATUS         current
        DESCRIPTION    "."
        INDEX { ifIndex }
        ::= { tnDfc12PortConfigTable 1 }

    TnDfc12PortConfigEntry ::=
        SEQUENCE {
            tnDfc12PortConfigFunction INTEGER
        }

    tnDfc12PortConfigFunction OBJECT-TYPE
        SYNTAX         INTEGER {
                         network(1),
                         client(2)
                       }
        MAX-ACCESS     read-only
        STATUS         current
        DESCRIPTION    "Indicates the functional type of this Dfc12 port."
        ::= { tnDfc12PortConfigEntry 1 }

--------------------------------------------------------------------------------
-- IRDM32L Optical Port Config Scalar
--------------------------------------------------------------------------------
    tnIrdm32lPortConfigAttributeTotal OBJECT-TYPE
        SYNTAX         Integer32
        MAX-ACCESS     read-only
        STATUS         current
        DESCRIPTION    "."
        ::= { tnOpticalPortConfig 473 }

--------------------------------------------------------------------------------
-- IRDM32L Optical Port Config Table
--------------------------------------------------------------------------------
    tnIrdm32lPortConfigTable OBJECT-TYPE
        SYNTAX         SEQUENCE OF TnIrdm32lPortConfigEntry
        MAX-ACCESS     not-accessible
        STATUS         current
        DESCRIPTION    "The ports on a IRDM32L optical card."
        ::= { tnOpticalPortConfig 474 }

    tnIrdm32lPortConfigEntry OBJECT-TYPE
        SYNTAX         TnIrdm32lPortConfigEntry
        MAX-ACCESS     not-accessible
        STATUS         current
        DESCRIPTION    "."
        INDEX { ifIndex }
        ::= { tnIrdm32lPortConfigTable 1 }

    TnIrdm32lPortConfigEntry ::=
        SEQUENCE {
            tnIrdm32lPortConfigFunction     INTEGER
        }

    tnIrdm32lPortConfigFunction OBJECT-TYPE
        SYNTAX         INTEGER {
                         lineIn(1),
                         inv(2),
                         osc(3),
                         lineOut(4),
                         oscSfp(5),
                         adt(6),
                         lineLoading(7),
                         otdrRx(8),
                         otdrTx(9),
                         custLan(10),
                         testLaser(11),
                         mpoFs(12),
                         oscLan(13)
                       }
        MAX-ACCESS     read-only
        STATUS         current
        DESCRIPTION    "Indicates the functional type of this IRDM32L port."
        ::= { tnIrdm32lPortConfigEntry 1 }

--------------------------------------------------------------------------------
-- S4X400 Optical Port Config Scalar
--------------------------------------------------------------------------------
    tnS4x400PortConfigAttributeTotal OBJECT-TYPE
        SYNTAX         Integer32
        MAX-ACCESS     read-only
        STATUS         current
        DESCRIPTION    "."
        ::= { tnOpticalPortConfig 475 }

--------------------------------------------------------------------------------
-- S4X400 Optical Port Config Table
--------------------------------------------------------------------------------
    tnS4x400PortConfigTable OBJECT-TYPE
        SYNTAX         SEQUENCE OF TnS4x400PortConfigEntry
        MAX-ACCESS     not-accessible
        STATUS         current
        DESCRIPTION    "The ports on a S4x400 optical card."
        ::= { tnOpticalPortConfig 476 }

    tnS4x400PortConfigEntry OBJECT-TYPE
        SYNTAX         TnS4x400PortConfigEntry
        MAX-ACCESS     not-accessible
        STATUS         current
        DESCRIPTION    "."
        INDEX { ifIndex }
        ::= { tnS4x400PortConfigTable 1 }

    TnS4x400PortConfigEntry ::=
        SEQUENCE {
            tnS4x400PortConfigFunction INTEGER
        }

    tnS4x400PortConfigFunction OBJECT-TYPE
        SYNTAX         INTEGER {
                         network(1),
                         client(2),
                         backplane(3)
                       }
        MAX-ACCESS     read-only
        STATUS         current
        DESCRIPTION    "Indicates the functional type of this S4X400 port."
        ::= { tnS4x400PortConfigEntry 1 }

--------------------------------------------------------------------------------
-- 1830 TPS-24 PS1 Optical Port Config Scalar
--------------------------------------------------------------------------------
    tnTPS24PS1PortConfigAttributeTotal OBJECT-TYPE
        SYNTAX         Integer32
        MAX-ACCESS     read-only
        STATUS         current
        DESCRIPTION    "."
        ::= { tnOpticalPortConfig 477 }

--------------------------------------------------------------------------------
-- 1830 TPS-24 PS1 Optical Port Config Table
--------------------------------------------------------------------------------
    tnTPS24PS1PortConfigTable OBJECT-TYPE
        SYNTAX         SEQUENCE OF TnTPS24PS1PortConfigEntry
        MAX-ACCESS     not-accessible
        STATUS         current
        DESCRIPTION    "The ports on a 1830 TPS-24 PS1 card."
        ::= { tnOpticalPortConfig 478 }

    tnTPS24PS1PortConfigEntry OBJECT-TYPE
        SYNTAX         TnTPS24PS1PortConfigEntry
        MAX-ACCESS     not-accessible
        STATUS         current
        DESCRIPTION    "."
        INDEX { ifIndex }
        ::= { tnTPS24PS1PortConfigTable 1 }

    TnTPS24PS1PortConfigEntry ::=
        SEQUENCE {
            tnTPS24PS1PortConfigFunction     INTEGER,
            tnTPS24PS1LptCons                INTEGER,
            tnTPS24PS1LptHoldOffTime         Integer32,
            tnTPS24PS1LptFlsDelayTime        Integer32,
            tnTPS24PS1LptTxDisDelayTime      Integer32,
            tnTPS24PS1LptExtensionTime       Integer32
        }

    tnTPS24PS1PortConfigFunction OBJECT-TYPE
        SYNTAX         INTEGER {
                         network(1),
                         client(2),
                         tod(3),
                         bits(4),
                         otc(5),
                         ethman(6)
                       }
        MAX-ACCESS     read-create
        STATUS         current
        DESCRIPTION    "Indicates the functional type of this 1830 TPS-24 PS1 port."
        ::= { tnTPS24PS1PortConfigEntry 1 }

    tnTPS24PS1LptCons OBJECT-TYPE
        SYNTAX         INTEGER {
                         disable(0),
                         shutdownall(1),
                         ethais(2),
                         shutdownallethais(3),
                         fls(4),
                         cpritxdis(5)
                       }
        MAX-ACCESS     read-create
        STATUS         current
        DESCRIPTION    "LPT parameters on the client C port of in the TPS-24
                        PS1 card.  Following actions are valid for GBE port:
                          disable(0),
                          shutdownall(1),
                          ethais(2),
                          shutdownall and ethais(3),
                        Following actions are valid for CPRI/OBSAI port:
                          disabled(0),
                          fls(4)       - Force this LAN port's Transmitter/Laser
                                         shutdown.
                          cpritxdis(5) - Disable CPRI Tx over this LAN port.
                                         Applies to CPRIn. "
        DEFVAL         { 0 }
        ::= { tnTPS24PS1PortConfigEntry 2 }

    tnTPS24PS1LptHoldOffTime OBJECT-TYPE
        SYNTAX         Integer32 (0..10000)
        MAX-ACCESS     read-create
        STATUS         current
        DESCRIPTION    "The LPT hold-off time (on port basis ) at local LAN
                        port, valid for GBE port only.  Range is 0 - 10000 ms,
                        in a granularity of 100ms."
        DEFVAL         { 0 }
        ::= { tnTPS24PS1PortConfigEntry 3 }

    tnTPS24PS1LptFlsDelayTime OBJECT-TYPE
        SYNTAX         Integer32 (0..300000)
        MAX-ACCESS     read-create
        STATUS         current
        DESCRIPTION    "The LPT SSF CA FLS delay time on port basis at local
                        LAN port.  Delay time on LAN port is used to postpone
                        the consequent actions on LAN port to take effect, in
                        order to avoid the conflicts with server protection,
                        valid for cpri-obsai only.  Range is 0 - 300000 ms, in
                        a unit of ms"
        DEFVAL         { 0 }
        ::= { tnTPS24PS1PortConfigEntry 4 }

    tnTPS24PS1LptTxDisDelayTime OBJECT-TYPE
        SYNTAX         Integer32 (0..300000)
        MAX-ACCESS     read-create
        STATUS         current
        DESCRIPTION    "the LPT CA CPRITxDis delay time on port basis at local
                        LAN port.  Delay time on LAN port is used to postpone
                        the consequent actions on LAN port to take effect, in
                        order to avoid the conflicts with server protection,
                        valid for cpri-obsai only.  Range is 0 - 300000 ms, in
                        a unit of ms."
        DEFVAL         { 0 }
        ::= { tnTPS24PS1PortConfigEntry 5 }

    tnTPS24PS1LptExtensionTime OBJECT-TYPE
        SYNTAX         Integer32 (0..300000)
        MAX-ACCESS     read-create
        STATUS         current
        DESCRIPTION    "The LPT SSF/CSF CA extension time on port basis at
                        local LAN port.  The consequent action is extended to
                        be at least extension time long enough to trigger the
                        reset or restart calibration at BBU/RU, valid for
                        cpri-obsai only.  Range is 0 - 300000 ms, in a unit
                        of ms."
        DEFVAL         { 0 }
        ::= { tnTPS24PS1PortConfigEntry 6 }

--------------------------------------------------------------------------------
-- 1830 TPS-24 PS2 Optical Port Config Scalar
--------------------------------------------------------------------------------
    tnTPS24PS2PortConfigAttributeTotal OBJECT-TYPE
        SYNTAX         Integer32
        MAX-ACCESS     read-only
        STATUS         current
        DESCRIPTION    "."
        ::= { tnOpticalPortConfig 479 }

--------------------------------------------------------------------------------
-- 1830 TPS-24 PS2 Optical Port Config Table
--------------------------------------------------------------------------------
    tnTPS24PS2PortConfigTable OBJECT-TYPE
        SYNTAX         SEQUENCE OF TnTPS24PS2PortConfigEntry
        MAX-ACCESS     not-accessible
        STATUS         current
        DESCRIPTION    "The ports on a 1830 TPS-24 PS2 card."
        ::= { tnOpticalPortConfig 480 }

    tnTPS24PS2PortConfigEntry OBJECT-TYPE
        SYNTAX         TnTPS24PS2PortConfigEntry
        MAX-ACCESS     not-accessible
        STATUS         current
        DESCRIPTION    "."
        INDEX { ifIndex }
        ::= { tnTPS24PS2PortConfigTable 1 }

    TnTPS24PS2PortConfigEntry ::=
        SEQUENCE {
            tnTPS24PS2PortConfigFunction     INTEGER,
            tnTPS24PS2LptCons                INTEGER,
            tnTPS24PS2LptHoldOffTime         Integer32,
            tnTPS24PS2LptFlsDelayTime        Integer32,
            tnTPS24PS2LptTxDisDelayTime      Integer32,
            tnTPS24PS2LptExtensionTime       Integer32
        }

    tnTPS24PS2PortConfigFunction OBJECT-TYPE
        SYNTAX         INTEGER {
                         network(1),
                         client(2),
                         tod(3),
                         bits(4),
                         otc(5),
                         ethman(6)
                       }
        MAX-ACCESS     read-create
        STATUS         current
        DESCRIPTION    "Indicates the functional type of this 1830 TPS-24 PS2 port."
        ::= { tnTPS24PS2PortConfigEntry 1 }

    tnTPS24PS2LptCons OBJECT-TYPE
        SYNTAX         INTEGER {
                         disable(0),
                         shutdownall(1),
                         ethais(2),
                         shutdownallethais(3),
                         fls(4),
                         cpritxdis(5)
                       }
        MAX-ACCESS     read-create
        STATUS         current
        DESCRIPTION    "LPT parameters on the client C port of in the TPS-24
                        PS2 card.  Following actions are valid for GBE port:
                          disable(0),
                          shutdownall(1),
                          ethais(2),
                          shutdownall and ethais(3),
                        Following actions are valid for CPRI/OBSAI port:
                          disabled(0),
                          fls(4)       - Force this LAN port's Transmitter/Laser
                                         shutdown.
                          cpritxdis(5) - Disable CPRI Tx over this LAN port.
                                         Applies to CPRIn."
        DEFVAL         { 0 }
        ::= { tnTPS24PS2PortConfigEntry 2 }

    tnTPS24PS2LptHoldOffTime OBJECT-TYPE
        SYNTAX         Integer32 (0..10000)
        MAX-ACCESS     read-create
        STATUS         current
        DESCRIPTION    "The LPT hold-off time (on port basis ) at local LAN
                        port, valid for GBE port only.  0 - 10000 ms, in a
                        granularity of 100ms."
        DEFVAL         { 0 }
        ::= { tnTPS24PS2PortConfigEntry 3 }

    tnTPS24PS2LptFlsDelayTime OBJECT-TYPE
        SYNTAX         Integer32 (0..300000)
        MAX-ACCESS     read-create
        STATUS         current
        DESCRIPTION    "The LPT SSF CA FLS delay time on port basis at local
                        LAN port.  Delay time on LAN port is used to postpone
                        the consequent actions on LAN port to take effect, in
                        order to avoid the conflicts with server protection,
                        valid for cpri-obsai only.  Range is 0 - 300000 ms,
                        in a unit of ms."
        DEFVAL         { 0 }
        ::= { tnTPS24PS2PortConfigEntry 4 }

    tnTPS24PS2LptTxDisDelayTime OBJECT-TYPE
        SYNTAX         Integer32 (0..300000)
        MAX-ACCESS     read-create
        STATUS         current
        DESCRIPTION    "the LPT CA CPRITxDis delay time on port basis at local
                        LAN port.  Delay time on LAN port is used to postpone
                        the consequent actions on LAN port to take effect, in
                        order to avoid the conflicts with server protection,
                        valid for cpri-obsai only.  Range is 0 - 300000 ms, in
                        a unit of ms."
        DEFVAL         { 0 }
        ::= { tnTPS24PS2PortConfigEntry 5 }

    tnTPS24PS2LptExtensionTime OBJECT-TYPE
        SYNTAX         Integer32 (0..300000)
        MAX-ACCESS     read-create
        STATUS         current
        DESCRIPTION    "The LPT SSF/CSF CA extension time on port basis at
                        local LAN port.  The consequent action is extended to
                        be at least extension time long enough to trigger the
                        reset or restart calibration at BBU/RU, valid for
                        cpri-obsai only.  Range is 0 - 300000 ms, in a unit
                        of ms."
        DEFVAL         { 0 }
        ::= { tnTPS24PS2PortConfigEntry 6 }

--------------------------------------------------------------------------------
-- 1830 TPS-12 PS Optical Port Config Scalar
--------------------------------------------------------------------------------
    tnTPS12PSPortConfigAttributeTotal OBJECT-TYPE
        SYNTAX         Integer32
        MAX-ACCESS     read-only
        STATUS         current
        DESCRIPTION    "."
        ::= { tnOpticalPortConfig 481 }

--------------------------------------------------------------------------------
-- 1830 TPS-12 PS Optical Port Config Table
--------------------------------------------------------------------------------
    tnTPS12PSPortConfigTable OBJECT-TYPE
        SYNTAX         SEQUENCE OF TnTPS12PSPortConfigEntry
        MAX-ACCESS     not-accessible
        STATUS         current
        DESCRIPTION    "The ports on a 1830 TPS-12 PS card."
        ::= { tnOpticalPortConfig 482 }

    tnTPS12PSPortConfigEntry OBJECT-TYPE
        SYNTAX         TnTPS12PSPortConfigEntry
        MAX-ACCESS     not-accessible
        STATUS         current
        DESCRIPTION    "."
        INDEX { ifIndex }
        ::= { tnTPS12PSPortConfigTable 1 }

    TnTPS12PSPortConfigEntry ::=
        SEQUENCE {
            tnTPS12PSPortConfigFunction     INTEGER,
            tnTPS12PSLptCons                INTEGER,
            tnTPS12PSLptHoldOffTime         Integer32,
            tnTPS12PSLptFlsDelayTime        Integer32,
            tnTPS12PSLptTxDisDelayTime      Integer32,
            tnTPS12PSLptExtensionTime       Integer32
        }
    tnTPS12PSPortConfigFunction OBJECT-TYPE
        SYNTAX         INTEGER {
                         network(1),
                         client(2),
                         tod(3),
                         otc(4),
                         ethman(5)
                       }
        MAX-ACCESS     read-create
        STATUS         current
        DESCRIPTION    "Indicates the functional type of this 1830 TPS-12 PS port."
        ::= { tnTPS12PSPortConfigEntry 1 }

    tnTPS12PSLptCons OBJECT-TYPE
        SYNTAX         INTEGER {
                         disable(0),
                         shutdownall(1),
                         ethais(2),
                         shutdownallethais(3),
                         fls(4),
                         cpritxdis(5)
                       }
        MAX-ACCESS     read-create
        STATUS         current
        DESCRIPTION    "LPT parameters on the client C port of in the TPS-12
                        PS card.  Following actions are valid for GBE port:
                          disable(0),
                          shutdownall(1),
                          ethais(2),
                          shutdownall and ethais(3),
                        Following actions are valid for CPRI/OBSAI port:
                          disabled(0),
                          fls(4)       - Force this LAN port's Transmitter/Laser
                                         shutdown.
                          cpritxdis(5) - Disable CPRI Tx over this LAN port.
                                         Applies to CPRIn. "
        DEFVAL         { 0 }
        ::= { tnTPS12PSPortConfigEntry 2 }

    tnTPS12PSLptHoldOffTime OBJECT-TYPE
        SYNTAX         Integer32 (0..10000)
        MAX-ACCESS     read-create
        STATUS         current
        DESCRIPTION    "The LPT hold-off time (on port basis ) at local LAN
                        port, valid for GBE port only.  Range is 0 - 10000 ms,
                        in a granularity of 100ms."
        DEFVAL         { 0 }
        ::= { tnTPS12PSPortConfigEntry 3 }

    tnTPS12PSLptFlsDelayTime OBJECT-TYPE
        SYNTAX         Integer32 (0..300000)
        MAX-ACCESS     read-create
        STATUS         current
        DESCRIPTION    "The LPT SSF CA FLS delay time on port basis at local
                        LAN port.  Delay time on LAN port is used to postpone
                        the consequent actions on LAN port to take effect, in
                        order to avoid the conflicts with server protection,
                        valid for cpri-obsai only.  Range is 0 - 300000 ms,
                        in a unit of ms"
        DEFVAL         { 0 }
        ::= { tnTPS12PSPortConfigEntry 4 }

    tnTPS12PSLptTxDisDelayTime OBJECT-TYPE
        SYNTAX         Integer32 (0..300000)
        MAX-ACCESS     read-create
        STATUS         current
        DESCRIPTION    "the LPT CA CPRITxDis delay time on port basis at local
                        LAN port.  Delay time on LAN port is used to postpone
                        the consequent actions on LAN port to take effect, in
                        order to avoid the conflicts with server protection,
                        valid for cpri-obsai only.  Range is 0 - 300000 ms, in
                        a unit of ms."
        DEFVAL         { 0 }
        ::= { tnTPS12PSPortConfigEntry 5 }

    tnTPS12PSLptExtensionTime OBJECT-TYPE
        SYNTAX         Integer32 (0..300000)
        MAX-ACCESS     read-create
        STATUS         current
        DESCRIPTION    "The LPT SSF/CSF CA extension time on port basis at
                        local LAN port.  The consequent action is extended
                        to be at least extension time long enough to trigger
                        the reset or restart calibration at BBU/RU, valid for
                        cpri-obsai only.  Range is 0 - 300000 ms, in a unit
                        of ms."
        DEFVAL         { 0 }
        ::= { tnTPS12PSPortConfigEntry 6 }

-------------------------------------------------------------------------------
-- Esre Optical Port Config Scalar
-------------------------------------------------------------------------------
    tnEsrePortConfigAttributeTotal OBJECT-TYPE
        SYNTAX         Integer32
        MAX-ACCESS     read-only
        STATUS         current
        DESCRIPTION    "."
        ::= { tnOpticalPortConfig 483 }

-------------------------------------------------------------------------------
-- Esre Optical Port Config Table
-------------------------------------------------------------------------------
    tnEsrePortConfigTable OBJECT-TYPE
        SYNTAX         SEQUENCE OF TnEsrePortConfigEntry
        MAX-ACCESS     not-accessible
        STATUS         current
        DESCRIPTION    "The ports on an Esre optical card."
        ::= { tnOpticalPortConfig 484 }

    tnEsrePortConfigEntry OBJECT-TYPE
        SYNTAX         TnEsrePortConfigEntry
        MAX-ACCESS     not-accessible
        STATUS         current
        DESCRIPTION    "."
        INDEX { ifIndex }
        ::= { tnEsrePortConfigTable 1 }

    TnEsrePortConfigEntry ::=
        SEQUENCE {
            tnEsrePortConfigFunction     INTEGER
        }
    tnEsrePortConfigFunction OBJECT-TYPE
        SYNTAX         INTEGER {
                         oes1(1),
                         ees1(2),
                         oes2(3),
                         ees2(4)
                       }
        MAX-ACCESS     read-only
        STATUS         current
        DESCRIPTION    "Indicates the functional type of this Esre port."
        ::= { tnEsrePortConfigEntry 1 }

--------------------------------------------------------------------------------
-- Generic OT Optical Port Config Scalar
--------------------------------------------------------------------------------
    tnGenericOtPortConfigAttributeTotal OBJECT-TYPE
        SYNTAX         Integer32
        MAX-ACCESS     read-only
        STATUS         current
        DESCRIPTION    "."
        ::= { tnOpticalPortConfig 485 }

--------------------------------------------------------------------------------
-- Generic OT Optical Port Config Table
--------------------------------------------------------------------------------
    tnGenericOtPortConfigTable OBJECT-TYPE
        SYNTAX         SEQUENCE OF TnGenericPortConfigEntry
        MAX-ACCESS     not-accessible
        STATUS         current
        DESCRIPTION    "The ports on a Generic OT optical card."
        ::= { tnOpticalPortConfig 486 }

    tnGenericOtPortConfigEntry OBJECT-TYPE
        SYNTAX         TnGenericPortConfigEntry
        MAX-ACCESS     not-accessible
        STATUS         current
        DESCRIPTION    "."
        INDEX { ifIndex }
        ::= { tnGenericOtPortConfigTable 1 }

    TnGenericPortConfigEntry ::=
        SEQUENCE {
            tnGenericOtPortConfigFunction  INTEGER,
            tnGenericOtLineAttributes      SnmpAdminString,
            tnGenericOtClientAttributes    SnmpAdminString
        }

    tnGenericOtPortConfigFunction OBJECT-TYPE
        SYNTAX         INTEGER {
                         network(1),
                         client(2),
                         backPlane(3)
                       }
        MAX-ACCESS     read-only
        STATUS         current
        DESCRIPTION    "Indicates the functional type of this Generic OT port."
        ::= { tnGenericOtPortConfigEntry 1 }

    tnGenericOtLineAttributes OBJECT-TYPE
        SYNTAX         SnmpAdminString (SIZE(0..1024))
        MAX-ACCESS     read-only
        STATUS         current
        DESCRIPTION    "."
        ::= { tnGenericOtPortConfigEntry 2 }

    tnGenericOtClientAttributes OBJECT-TYPE
        SYNTAX         SnmpAdminString (SIZE(0..1024))
        MAX-ACCESS     read-only
        STATUS         current
        DESCRIPTION    "."
        ::= { tnGenericOtPortConfigEntry 3}

-------------------------------------------------------------------------------
-- 1ety100 Optical Port Config Scalar
-------------------------------------------------------------------------------
    tn1ety100PortConfigAttributeTotal OBJECT-TYPE
        SYNTAX         Integer32
        MAX-ACCESS     read-only
        STATUS         current
        DESCRIPTION    "."
        ::= { tnOpticalPortConfig 487 }

-------------------------------------------------------------------------------
-- 1ety100 Optical Port Config Table
-------------------------------------------------------------------------------
    tn1ety100PortConfigTable OBJECT-TYPE
        SYNTAX         SEQUENCE OF Tn1ety100PortConfigEntry
        MAX-ACCESS     not-accessible
        STATUS         current
        DESCRIPTION    "The ports on an 1ety100 card."
        ::= { tnOpticalPortConfig 488 }

    tn1ety100PortConfigEntry OBJECT-TYPE
        SYNTAX         Tn1ety100PortConfigEntry
        MAX-ACCESS     not-accessible
        STATUS         current
        DESCRIPTION    "."
        INDEX { ifIndex }
        ::= { tn1ety100PortConfigTable 1 }

    Tn1ety100PortConfigEntry ::=
        SEQUENCE {
            tn1ety100PortConfigFunction     INTEGER
        }
    tn1ety100PortConfigFunction OBJECT-TYPE
        SYNTAX         INTEGER {
                         network(1),
                         backplane(2)
                       }
        MAX-ACCESS     read-only
        STATUS         current
        DESCRIPTION    "Indicates the functional type of this 1ety100 port."
        ::= { tn1ety100PortConfigEntry 1 }

--    obsolete
--    tnD1ad400qPortConfigAttributeTotal OBJECT-TYPE ::= { tnOpticalPortConfig 489 }
--    tnD1ad400qPortConfigTable          OBJECT-TYPE ::= { tnOpticalPortConfig 490 }

-------------------------------------------------------------------------------
-- Omdcl Optical Port Config Scalar
-------------------------------------------------------------------------------
    tnOmdclPortConfigAttributeTotal OBJECT-TYPE
        SYNTAX         Integer32
        MAX-ACCESS     read-only
        STATUS         current
        DESCRIPTION    "."
        ::= { tnOpticalPortConfig 491 }

-------------------------------------------------------------------------------
-- Omdcl Optical Port Config Table
-------------------------------------------------------------------------------
    tnOmdclPortConfigTable OBJECT-TYPE
        SYNTAX         SEQUENCE OF TnOmdclPortConfigEntry
        MAX-ACCESS     not-accessible
        STATUS         current
        DESCRIPTION    "The ports on an Omdcl card."
        ::= { tnOpticalPortConfig 492 }

    tnOmdclPortConfigEntry OBJECT-TYPE
        SYNTAX         TnOmdclPortConfigEntry
        MAX-ACCESS     not-accessible
        STATUS         current
        DESCRIPTION    "."
        INDEX { ifIndex }
        ::= { tnOmdclPortConfigTable 1 }

    TnOmdclPortConfigEntry ::=
        SEQUENCE {
            tnOmdclPortConfigFunction                  INTEGER,
            tnOmdclPortConfigTargetLinePpcOut          Integer32,
            tnOmdclPortConfigTargetLinePpcOutL         Integer32,
            tnOmdclPortConfigOSCVoaAtten               Unsigned32,
            tnOmdclPortConfigSpanLossTh                Integer32,
            tnOmdclPortConfigAsellEnabled              TruthValue,
            tnOmdclPortConfigTargetPowerWidth          NokiaAmpPortTargetPowerWidth,
            tnOmdclPortConfigTargetPowerWidthL         NokiaAmpPortTargetPowerWidth,
            tnOmdclPortConfigAsellEnabledL             TruthValue,
            tnOmdclPortConfigIngressTargetPowerWidth   NokiaAmpPortTargetPowerWidth,
            tnOmdclPortConfigIngressTargetPowerWidthL  NokiaAmpPortTargetPowerWidth
        }

    tnOmdclPortConfigFunction OBJECT-TYPE
        SYNTAX         INTEGER {
                         lineIn(1),
                         lineOut(2),
                         sigcIn(3),
                         sigcOut(4),
                         siglIn(5),
                         siglOut(6),
                         oscsfp(7),
                         osc(8),
                         custlan(9),
                         osclan(10)
                       }
        MAX-ACCESS     read-only
        STATUS         current
        DESCRIPTION    "Indicates the functional type of this Omdcl port."
        ::= { tnOmdclPortConfigEntry 1 }

    tnOmdclPortConfigTargetLinePpcOut OBJECT-TYPE
        SYNTAX         Integer32
        UNITS          "mBm"
        MAX-ACCESS     read-create
        STATUS         current
        DESCRIPTION    "Target Power per Channel C band."
        DEFVAL         { -400 }
        ::= { tnOmdclPortConfigEntry 2 }

    tnOmdclPortConfigTargetLinePpcOutL OBJECT-TYPE
        SYNTAX         Integer32
        UNITS          "mBm"
        MAX-ACCESS     read-create
        STATUS         current
        DESCRIPTION    "Target Power per Channel L band."
        DEFVAL         { -400 }
        ::= { tnOmdclPortConfigEntry 3 }

    tnOmdclPortConfigOSCVoaAtten OBJECT-TYPE
        SYNTAX         Unsigned32
        UNITS          "mB"
        MAX-ACCESS     read-create
        STATUS         current
        DESCRIPTION    "OSC Drop VOA Set."
        DEFVAL         { 1500 }
        ::= { tnOmdclPortConfigEntry 4 }

    tnOmdclPortConfigSpanLossTh OBJECT-TYPE
        SYNTAX         Integer32
        UNITS          "mB"
        MAX-ACCESS     read-create
        STATUS         current
        DESCRIPTION    "Span loss threshold ."
        DEFVAL         { -9900 }
        ::= { tnOmdclPortConfigEntry 5 }

    tnOmdclPortConfigAsellEnabled OBJECT-TYPE
        SYNTAX         TruthValue
        MAX-ACCESS     read-create
        STATUS         current
        DESCRIPTION    "."
        DEFVAL         { false }
        ::= { tnOmdclPortConfigEntry 6 }

    tnOmdclPortConfigTargetPowerWidth OBJECT-TYPE
        SYNTAX         NokiaAmpPortTargetPowerWidth
        MAX-ACCESS     read-create
        STATUS         current
        DESCRIPTION    "."
        DEFVAL         { channelWidth50GHz }
        ::= { tnOmdclPortConfigEntry 7 }

    tnOmdclPortConfigTargetPowerWidthL OBJECT-TYPE
        SYNTAX         NokiaAmpPortTargetPowerWidth
        MAX-ACCESS     read-create
        STATUS         current
        DESCRIPTION    "."
        DEFVAL         { channelWidth50GHz }
        ::= { tnOmdclPortConfigEntry 8 }

    tnOmdclPortConfigAsellEnabledL OBJECT-TYPE
        SYNTAX         TruthValue
        MAX-ACCESS     read-create
        STATUS         current
        DESCRIPTION    "."
        DEFVAL         { false }
        ::= { tnOmdclPortConfigEntry 9 }

    tnOmdclPortConfigIngressTargetPowerWidth OBJECT-TYPE
        SYNTAX         NokiaAmpPortTargetPowerWidth
        MAX-ACCESS     read-create
        STATUS         current
        DESCRIPTION    "."
        DEFVAL         { channelWidth50GHz }
        ::= { tnOmdclPortConfigEntry 10 }

    tnOmdclPortConfigIngressTargetPowerWidthL OBJECT-TYPE
        SYNTAX         NokiaAmpPortTargetPowerWidth
        MAX-ACCESS     read-create
        STATUS         current
        DESCRIPTION    "."
        DEFVAL         { channelWidth50GHz }
        ::= { tnOmdclPortConfigEntry 11 }

--------------------------------------------------------------------------------
-- MCS16-15L Optical Port Config Scalar
--------------------------------------------------------------------------------
    tnMcs16x15lPortConfigAttributeTotal OBJECT-TYPE
        SYNTAX         Integer32
        MAX-ACCESS     read-only
        STATUS         current
        DESCRIPTION    "."
        ::= { tnOpticalPortConfig 493 }

--------------------------------------------------------------------------------
-- MCS16-15L Optical Port Config Table
--------------------------------------------------------------------------------
    tnMcs16x15lPortConfigTable OBJECT-TYPE
        SYNTAX         SEQUENCE OF TnMcs16x15lPortConfigEntry
        MAX-ACCESS     not-accessible
        STATUS         current
        DESCRIPTION    "The ports on a MCS16-15L optical card."
        ::= { tnOpticalPortConfig 494 }

    tnMcs16x15lPortConfigEntry OBJECT-TYPE
        SYNTAX         TnMcs16x15lPortConfigEntry
        MAX-ACCESS     not-accessible
        STATUS         current
        DESCRIPTION    "."
        INDEX { ifIndex }
        ::= { tnMcs16x15lPortConfigTable 1 }

    TnMcs16x15lPortConfigEntry ::=
        SEQUENCE {
            tnMcs16x15lPortConfigFunction   INTEGER
        }

    tnMcs16x15lPortConfigFunction OBJECT-TYPE
        SYNTAX         INTEGER {
                         signal(1),
                         ad(2),
                         mpoAar(3)
                       }
        MAX-ACCESS     read-only
        STATUS         current
        DESCRIPTION    "Indicates the functional type of this MCS16-15L port."
        ::= { tnMcs16x15lPortConfigEntry 1 }

-------------------------------------------------------------------------------
-- EILAL Optical Port Config Scalar
-------------------------------------------------------------------------------
    tnEilalPortConfigAttributeTotal OBJECT-TYPE
        SYNTAX         Integer32
        MAX-ACCESS     read-only
        STATUS         current
        DESCRIPTION    "."
        ::= { tnOpticalPortConfig 495 }

-------------------------------------------------------------------------------
-- EILAL Optical Port Config Table
-------------------------------------------------------------------------------
    tnEilalPortConfigTable OBJECT-TYPE
        SYNTAX         SEQUENCE OF TnEilalPortConfigEntry
        MAX-ACCESS     not-accessible
        STATUS         current
        DESCRIPTION    "The ports on a EILAL optical card."
        ::= { tnOpticalPortConfig 496 }

    tnEilalPortConfigEntry OBJECT-TYPE
        SYNTAX         TnEilalPortConfigEntry
        MAX-ACCESS     not-accessible
        STATUS         current
        DESCRIPTION    "."
        INDEX { ifIndex }
        ::= { tnEilalPortConfigTable 1 }

    TnEilalPortConfigEntry ::=
        SEQUENCE {
            tnEilalPortConfigFunction INTEGER
        }

    tnEilalPortConfigFunction OBJECT-TYPE
        SYNTAX         INTEGER {
                         lineIn(1),
                         otdrRx(2),
                         otdrTx(3),
                         lineOut(4),
                         oscSfp(5),
                         osc(6),
                         custLan(7),
                         inv(8),
                         oscLan(9)
                       }
        MAX-ACCESS     read-only
        STATUS         current
        DESCRIPTION    "Indicates the functional type of this EILAL port."
        ::= { tnEilalPortConfigEntry 1 }

--------------------------------------------------------------------------------
-- RA5PB Optical Port Config Scalar
--------------------------------------------------------------------------------
    tnRa5pbPortConfigAttributeTotal OBJECT-TYPE
        SYNTAX         Integer32
        MAX-ACCESS     read-only
        STATUS         current
        DESCRIPTION    "."
        ::= { tnOpticalPortConfig 497 }

--------------------------------------------------------------------------------
-- RA5PB Optical Port Config Table
--------------------------------------------------------------------------------
    tnRa5pbPortConfigTable OBJECT-TYPE
        SYNTAX         SEQUENCE OF TnRa5pbPortConfigEntry
        MAX-ACCESS     not-accessible
        STATUS         current
        DESCRIPTION    "The ports on a RA5PB optical card."
        ::= { tnOpticalPortConfig 498 }

    tnRa5pbPortConfigEntry OBJECT-TYPE
        SYNTAX         TnRa5pbPortConfigEntry
        MAX-ACCESS     not-accessible
        STATUS         current
        DESCRIPTION    "."
        INDEX { ifIndex }
        ::= { tnRa5pbPortConfigTable 1 }

    TnRa5pbPortConfigEntry ::=
        SEQUENCE {
            tnRa5pbPortConfigFunction INTEGER
        }

    tnRa5pbPortConfigFunction OBJECT-TYPE
        SYNTAX         INTEGER {
                         lineIn(1),
                         lineOut(2)
                       }
        MAX-ACCESS     read-only
        STATUS         current
        DESCRIPTION    "Indicates the functional type of this RA5PB port."
        ::= { tnRa5pbPortConfigEntry 1 }

--------------------------------------------------------------------------------
-- MLFSB Optical Port Config Scalar
--------------------------------------------------------------------------------
    tnMlfsbPortConfigAttributeTotal OBJECT-TYPE
        SYNTAX         Integer32
        MAX-ACCESS     read-only
        STATUS         current
        DESCRIPTION    "."
        ::= { tnOpticalPortConfig 499 }

--------------------------------------------------------------------------------
-- MLFSB Optical Port Config Table
--------------------------------------------------------------------------------
    tnMlfsbPortConfigTable OBJECT-TYPE
        SYNTAX         SEQUENCE OF TnMlfsbPortConfigEntry
        MAX-ACCESS     not-accessible
        STATUS         current
        DESCRIPTION    "The ports on a MLFSB optical card."
        ::= { tnOpticalPortConfig 500 }

    tnMlfsbPortConfigEntry OBJECT-TYPE
        SYNTAX         TnMlfsbPortConfigEntry
        MAX-ACCESS     not-accessible
        STATUS         current
        DESCRIPTION    "."
        INDEX { ifIndex }
        ::= { tnMlfsbPortConfigTable 1 }

    TnMlfsbPortConfigEntry ::=
        SEQUENCE {
            tnMlfsbPortConfigFunction     INTEGER
        }

    tnMlfsbPortConfigFunction OBJECT-TYPE
        SYNTAX         INTEGER {
                         mpoMx(1),
                         mpoLc(2)
                       }
        MAX-ACCESS     read-only
        STATUS         current
        DESCRIPTION    "Indicates the functional type of this MLFSB port."
        ::= { tnMlfsbPortConfigEntry 1 }

--------------------------------------------------------------------------------
-- 1830 Optical Port LPT Config Scalars
--------------------------------------------------------------------------------
    tnPortLptConfigAttributeTotal OBJECT-TYPE
        SYNTAX         Integer32
        MAX-ACCESS     read-only
        STATUS         current
        DESCRIPTION    "."
        ::= { tnOpticalPortConfig 501 }

--------------------------------------------------------------------------------
-- 1830 Optical Port LPT Config Table
--------------------------------------------------------------------------------
    tnPortLptConfigTable OBJECT-TYPE
        SYNTAX         SEQUENCE OF TnPortLptConfigEntry
        MAX-ACCESS     not-accessible
        STATUS         current
        DESCRIPTION    "The LPT configuration functon on a ports in a 1830 card."
        ::= { tnOpticalPortConfig 502 }

    tnPortLptConfigEntry OBJECT-TYPE
        SYNTAX         TnPortLptConfigEntry
        MAX-ACCESS     not-accessible
        STATUS         current
        DESCRIPTION    "."
        INDEX { ifIndex }
        ::= { tnPortLptConfigTable 1 }

    TnPortLptConfigEntry ::=
        SEQUENCE {
            tnPortLptConfigCons               INTEGER,
            tnPortLptConfigFlsDelayTime       Integer32,
            tnPortLptConfigTxDisDelayTime     Integer32,
            tnPortLptConfigExtensionTime      Integer32
        }

    tnPortLptConfigCons OBJECT-TYPE
        SYNTAX         INTEGER {
                         disable(1),
                         fls(2),
                         cpritxdis(3),
                         obsaitxdis(4)
                       }
        MAX-ACCESS     read-create
        STATUS         current
        DESCRIPTION    "Configure LPT Consequent Action on port basis at local
                        client port, when CSF/SSF is detected on network side.
                        This parameter applies only to the LPT CA enabled/disabled
                        by the user (i.e., aCPRITxDis, and aFLS), but does not
                        apply to the LPT CA non configurable by the user (i.e.,
                        aAllZeroBits, aLoPattern).  It is applied for cpri-obsai
                        port only."
        DEFVAL         { disable }
        ::= { tnPortLptConfigEntry 1 }

    tnPortLptConfigFlsDelayTime OBJECT-TYPE
        SYNTAX         Integer32 (0..300000)
        MAX-ACCESS     read-create
        STATUS         current
        DESCRIPTION    "The LPT SSF CA FLS delay time on port basis at local
                        LAN port.  Delay time on LAN port is used to postpone
                        the consequent actions on LAN port to take effect, in
                        order to avoid the conflicts with server protection,
                        valid for cpri-obsai only.  Range is 0 - 300000 ms, in
                        a unit of ms."
        DEFVAL         { 0 }
        ::= { tnPortLptConfigEntry 2 }

    tnPortLptConfigTxDisDelayTime OBJECT-TYPE
        SYNTAX         Integer32 (0..300000)
        MAX-ACCESS     read-create
        STATUS         current
        DESCRIPTION    "the LPT CA CPRITxDis delay time on port basis at local
                        LAN port.  Delay time on LAN port is used to postpone
                        the consequent actions on LAN port to take effect, in
                        order to avoid the conflicts with server protection,
                        valid for cpri-obsai only.  Range is 0 - 300000 ms, in
                        a unit of ms."
        DEFVAL         { 0 }
        ::= { tnPortLptConfigEntry 3 }

    tnPortLptConfigExtensionTime OBJECT-TYPE
        SYNTAX         Integer32 (0..300000)
        MAX-ACCESS     read-create
        STATUS         current
        DESCRIPTION    "The LPT SSF/CSF CA extension time on port basis at
                        local LAN port.  The consequent action is extended to
                        be at least extension time long enough to trigger the
                        reset or restart calibration at BBU/RU, valid for
                        cpri-obsai only.  Range is 0 - 300000 ms, in a unit
                        of ms."
        DEFVAL         { 0 }
        ::= { tnPortLptConfigEntry 4 }

--------------------------------------------------------------------------------
-- 1830 Optical Port Config Scalar
--------------------------------------------------------------------------------
    tnPortConfigAttributeTotal OBJECT-TYPE
        SYNTAX         Integer32
        MAX-ACCESS     read-only
        STATUS         current
        DESCRIPTION    "."
        ::= { tnOpticalPortConfig 503 }

--------------------------------------------------------------------------------
-- 1830 Optical Port Config Table
--------------------------------------------------------------------------------
    tnPortConfigTable OBJECT-TYPE
        SYNTAX         SEQUENCE OF TnPortConfigEntry
        MAX-ACCESS     not-accessible
        STATUS         current
        DESCRIPTION    "The ports on a 1830 card."
        ::= { tnOpticalPortConfig 504 }

    tnPortConfigEntry OBJECT-TYPE
        SYNTAX         TnPortConfigEntry
        MAX-ACCESS     not-accessible
        STATUS         current
        DESCRIPTION    "."
        INDEX { ifIndex }
        ::= { tnPortConfigTable 1 }

    TnPortConfigEntry ::=
        SEQUENCE {
            tnPortConfigFunction     INTEGER,
            tnPortConfigLosProp      INTEGER
        }

    tnPortConfigFunction OBJECT-TYPE
        SYNTAX         INTEGER {
                         network(1),
                         client(2),
                         ethman(3),
                         cit(4),
                         lan(5),
                         otc(6),
                         tod(7),
                         bits(8),
                         ppstest(9)
                       }
        MAX-ACCESS     read-only
        STATUS         current
        DESCRIPTION    "Indicates the functional type of the port for 1830 PSS NE."
        ::= { tnPortConfigEntry 1 }

    tnPortConfigLosProp OBJECT-TYPE
        SYNTAX         INTEGER {
                         laserOn(1),
                         laserOff(2)
                       }
        MAX-ACCESS     read-create
        STATUS         current
        DESCRIPTION    "The LOS propagation."
        DEFVAL         { laserOn }
        ::= { tnPortConfigEntry 2 }

--------------------------------------------------------------------------------
-- 18P400 Optical Port Config Scalar
--------------------------------------------------------------------------------
    tn18P400PortConfigAttributeTotal OBJECT-TYPE
        SYNTAX         Integer32
        MAX-ACCESS     read-only
        STATUS         current
        DESCRIPTION    "."
        ::= { tnOpticalPortConfig 505 }

--------------------------------------------------------------------------------
-- 18P400 Optical Port Config Table
--------------------------------------------------------------------------------
    tn18P400PortConfigTable OBJECT-TYPE
        SYNTAX         SEQUENCE OF Tn18P400PortConfigEntry
        MAX-ACCESS     not-accessible
        STATUS         current
        DESCRIPTION    "The ports on a 18P400 optical card."
        ::= { tnOpticalPortConfig 506 }

    tn18P400PortConfigEntry OBJECT-TYPE
        SYNTAX         Tn18P400PortConfigEntry
        MAX-ACCESS     not-accessible
        STATUS         current
        DESCRIPTION    "."
        INDEX { ifIndex }
        ::= { tn18P400PortConfigTable 1 }

    Tn18P400PortConfigEntry ::=
        SEQUENCE {
            tn18P400PortConfigFunction INTEGER
        }

    tn18P400PortConfigFunction OBJECT-TYPE
        SYNTAX         INTEGER {
                         client(1),
                         backplane(2)
                       }
        MAX-ACCESS     read-only
        STATUS         current
        DESCRIPTION    "Indicates the functional type of this 18P400 port."
        ::= { tn18P400PortConfigEntry 1 }

--------------------------------------------------------------------------------
-- 4UC1T Optical Port Config Scalar
--------------------------------------------------------------------------------
    tn4uc1tPortConfigAttributeTotal OBJECT-TYPE
        SYNTAX         Integer32
        MAX-ACCESS     read-only
        STATUS         current
        DESCRIPTION    "."
        ::= { tnOpticalPortConfig 507 }

--------------------------------------------------------------------------------
-- 4UC1T Optical Port Config Table
--------------------------------------------------------------------------------
    tn4uc1tPortConfigTable OBJECT-TYPE
        SYNTAX         SEQUENCE OF Tn4uc1tPortConfigEntry
        MAX-ACCESS     not-accessible
        STATUS         current
        DESCRIPTION    "The ports on a 4UC1T optical card."
        ::= { tnOpticalPortConfig 508 }

    tn4uc1tPortConfigEntry OBJECT-TYPE
        SYNTAX         Tn4uc1tPortConfigEntry
        MAX-ACCESS     not-accessible
        STATUS         current
        DESCRIPTION    "."
        INDEX { ifIndex }
        ::= { tn4uc1tPortConfigTable 1 }

    Tn4uc1tPortConfigEntry ::=
        SEQUENCE {
            tn4uc1tPortConfigFunction INTEGER
        }

    tn4uc1tPortConfigFunction OBJECT-TYPE
        SYNTAX         INTEGER {
                         network(1)
                       }
        MAX-ACCESS     read-only
        STATUS         current
        DESCRIPTION    "Indicates the functional type of this 4UC1T port."
        ::= { tn4uc1tPortConfigEntry 1 }

--------------------------------------------------------------------------------
-- ASG Optical Port Config Scalar
--------------------------------------------------------------------------------
    tnAsgPortConfigAttributeTotal OBJECT-TYPE
        SYNTAX         Integer32
        MAX-ACCESS     read-only
        STATUS         current
        DESCRIPTION    "."
        ::= { tnOpticalPortConfig 509 }

--------------------------------------------------------------------------------
-- ASG Optical Port Config Table
--------------------------------------------------------------------------------
    tnAsgPortConfigTable OBJECT-TYPE
        SYNTAX         SEQUENCE OF TnAsgPortConfigEntry
        MAX-ACCESS     not-accessible
        STATUS         current
        DESCRIPTION    "The ports on an ASG optical card."
        ::= { tnOpticalPortConfig 510 }

    tnAsgPortConfigEntry OBJECT-TYPE
        SYNTAX         TnAsgPortConfigEntry
        MAX-ACCESS     not-accessible
        STATUS         current
        DESCRIPTION    "."
        INDEX { ifIndex }
        ::= { tnAsgPortConfigTable 1 }

    TnAsgPortConfigEntry ::=
        SEQUENCE {
            tnAsgPortConfigFunction INTEGER
        }

    tnAsgPortConfigFunction OBJECT-TYPE
        SYNTAX         INTEGER {
                         lineIn(1),
                         otdrRx(2),
                         otdrTx(3),
                         lineOut(4),
                         oscSfp(5),
                         osc(6),
                         custLan(7),
                         inv(8)
                       }
        MAX-ACCESS     read-only
        STATUS         current
        DESCRIPTION    "Indicates the functional type of this ASG port."
        ::= { tnAsgPortConfigEntry 1 }

--------------------------------------------------------------------------------
-- 12P120S Optical Port Config Scalar
--------------------------------------------------------------------------------
    tn12p120sPortConfigAttributeTotal OBJECT-TYPE
        SYNTAX         Integer32
        MAX-ACCESS     read-only
        STATUS         current
        DESCRIPTION    "."
        ::= { tnOpticalPortConfig 511 }

--------------------------------------------------------------------------------
-- 12P120S Optical Port Config Table
--------------------------------------------------------------------------------
    tn12p120sPortConfigTable OBJECT-TYPE
        SYNTAX         SEQUENCE OF Tn12p120sPortConfigEntry
        MAX-ACCESS     not-accessible
        STATUS         current
        DESCRIPTION    "The ports on a 12P120S optical card."
        ::= { tnOpticalPortConfig 512 }

    tn12p120sPortConfigEntry OBJECT-TYPE
        SYNTAX         Tn12p120sPortConfigEntry
        MAX-ACCESS     not-accessible
        STATUS         current
        DESCRIPTION    "."
        INDEX { ifIndex }
        ::= { tn12p120sPortConfigTable 1 }

    Tn12p120sPortConfigEntry ::=
        SEQUENCE {
            tn12p120sPortConfigFunction  INTEGER
        }

    tn12p120sPortConfigFunction OBJECT-TYPE
        SYNTAX         INTEGER {
                         network(1),
                         client(2),
                         evoa(3),
                         backplane(4)
                       }
        MAX-ACCESS     read-only
        STATUS         current
        DESCRIPTION    "Indicates the functional type of this 12P120S port."
        ::= { tn12p120sPortConfigEntry 1 }

--------------------------------------------------------------------------------
-- 16P200 Optical Port Config Scalar
--------------------------------------------------------------------------------
    tn16p200PortConfigAttributeTotal OBJECT-TYPE
        SYNTAX         Integer32
        MAX-ACCESS     read-only
        STATUS         current
        DESCRIPTION    "."
        ::= { tnOpticalPortConfig 513 }

--------------------------------------------------------------------------------
-- 16P200 Optical Port Config Table
--------------------------------------------------------------------------------
    tn16p200PortConfigTable OBJECT-TYPE
        SYNTAX         SEQUENCE OF Tn16p200PortConfigEntry
        MAX-ACCESS     not-accessible
        STATUS         current
        DESCRIPTION    "The ports on a 16P200 optical card."
        ::= { tnOpticalPortConfig 514 }

    tn16p200PortConfigEntry OBJECT-TYPE
        SYNTAX         Tn16p200PortConfigEntry
        MAX-ACCESS     not-accessible
        STATUS         current
        DESCRIPTION    "."
        INDEX { ifIndex }
        ::= { tn16p200PortConfigTable 1 }

    Tn16p200PortConfigEntry ::=
        SEQUENCE {
            tn16p200PortConfigFunction  INTEGER
        }

    tn16p200PortConfigFunction OBJECT-TYPE
        SYNTAX         INTEGER {
                         network(1),
                         client(2)
                       }
        MAX-ACCESS     read-only
        STATUS         current
        DESCRIPTION    "Indicates the functional type of this 16P200 port."
        ::= { tn16p200PortConfigEntry 1 }

--------------------------------------------------------------------------------
-- IR9 Optical Port Config Scalar
--------------------------------------------------------------------------------
    tnIr9PortConfigAttributeTotal OBJECT-TYPE
        SYNTAX         Integer32
        MAX-ACCESS     read-only
        STATUS         current
        DESCRIPTION    "."
        ::= { tnOpticalPortConfig 515 }

--------------------------------------------------------------------------------
-- IR9 Optical Port Config Table
--------------------------------------------------------------------------------
    tnIr9PortConfigTable OBJECT-TYPE
        SYNTAX         SEQUENCE OF TnIr9PortConfigEntry
        MAX-ACCESS     not-accessible
        STATUS         current
        DESCRIPTION    "The ports on a IR9 optical card."
        ::= { tnOpticalPortConfig 516 }

    tnIr9PortConfigEntry OBJECT-TYPE
        SYNTAX         TnIr9PortConfigEntry
        MAX-ACCESS     not-accessible
        STATUS         current
        DESCRIPTION    "."
        INDEX { ifIndex }
        ::= { tnIr9PortConfigTable 1 }

    TnIr9PortConfigEntry ::=
        SEQUENCE {
            tnIr9PortConfigFunction INTEGER
        }

    tnIr9PortConfigFunction OBJECT-TYPE
        SYNTAX         INTEGER {
                         lineIn(1),
                         inv(2),
                         osc(3),
                         lineOut(4),
                         oscSfp(5),
                         adt(6),
                         otdrRx(7),
                         otdrTx(8),
                         custLan(9)
                       }
        MAX-ACCESS     read-only
        STATUS         current
        DESCRIPTION    "Indicates the functional type of this IR9 port."
        ::= { tnIr9PortConfigEntry 1 }

--------------------------------------------------------------------------------
-- MXN824 Optical Port Config Scalar
--------------------------------------------------------------------------------
    tnMxn824PortConfigAttributeTotal OBJECT-TYPE
        SYNTAX         Integer32
        MAX-ACCESS     read-only
        STATUS         current
        DESCRIPTION    "."
        ::= { tnOpticalPortConfig 517 }

--------------------------------------------------------------------------------
-- MXN824 Optical Port Config Table
--------------------------------------------------------------------------------
    tnMxn824PortConfigTable OBJECT-TYPE
        SYNTAX         SEQUENCE OF TnMxn824PortConfigEntry
        MAX-ACCESS     not-accessible
        STATUS         current
        DESCRIPTION    "The ports on a MXN824 optical card."
        ::= { tnOpticalPortConfig 518 }

    tnMxn824PortConfigEntry OBJECT-TYPE
        SYNTAX         TnMxn824PortConfigEntry
        MAX-ACCESS     not-accessible
        STATUS         current
        DESCRIPTION    "."
        INDEX { ifIndex }
        ::= { tnMxn824PortConfigTable 1 }

    TnMxn824PortConfigEntry ::=
        SEQUENCE {
            tnMxn824PortConfigFunction     INTEGER
        }

    tnMxn824PortConfigFunction OBJECT-TYPE
        SYNTAX         INTEGER {
                         sig(1),
                         ad(2),
                         lpbk(3),
                         tl(4),
                         fsm(5)
                       }
        MAX-ACCESS     read-only
        STATUS         current
        DESCRIPTION    "Indicates the functional type of this MXN824 port."
        ::= { tnMxn824PortConfigEntry 1 }

--------------------------------------------------------------------------------
-- ASC4 Optical Port Config Scalar
--------------------------------------------------------------------------------
    tnAsc4PortConfigAttributeTotal OBJECT-TYPE
        SYNTAX         Integer32
        MAX-ACCESS     read-only
        STATUS         current
        DESCRIPTION    "."
        ::= { tnOpticalPortConfig 519 }

--------------------------------------------------------------------------------
-- ASC4 Optical Port Config Table
--------------------------------------------------------------------------------
    tnAsc4PortConfigTable OBJECT-TYPE
        SYNTAX         SEQUENCE OF TnAsc4PortConfigEntry
        MAX-ACCESS     not-accessible
        STATUS         current
        DESCRIPTION    "The ports on a ASC4 optical card."
        ::= { tnOpticalPortConfig 520 }

    tnAsc4PortConfigEntry OBJECT-TYPE
        SYNTAX         TnAsc4PortConfigEntry
        MAX-ACCESS     not-accessible
        STATUS         current
        DESCRIPTION    "."
        INDEX { ifIndex }
        ::= { tnAsc4PortConfigTable 1 }

    TnAsc4PortConfigEntry ::=
        SEQUENCE {
            tnAsc4PortConfigFunction     INTEGER
        }

    tnAsc4PortConfigFunction OBJECT-TYPE
        SYNTAX         INTEGER {
                         sigAIn(1),
                         aOut(2),
                         sigAOut(3),
                         aIn(4),
                         sigBIn(5),
                         bOut(6),
                         sigBOut(7),
                         bIn(8),
                         sigCIn(9),
                         cOut(10),
                         sigCOut(11),
                         cIn(12),
                         sigDIn(13),
                         dOut(14),
                         sigDOut(15),
                         dIn(16)
                       }
        MAX-ACCESS     read-only
        STATUS         current
        DESCRIPTION    "Indicates the functional type of this ASC4 port."
        ::= { tnAsc4PortConfigEntry 1 }

--------------------------------------------------------------------------------
-- 5MX500 Optical Port Config Scalar
--------------------------------------------------------------------------------
    tn5mx500PortConfigAttributeTotal OBJECT-TYPE
        SYNTAX         Integer32
        MAX-ACCESS     read-only
        STATUS         current
        DESCRIPTION    "."
        ::= { tnOpticalPortConfig 521 }

--------------------------------------------------------------------------------
-- 5MX500 Optical Port Config Table
--------------------------------------------------------------------------------
    tn5mx500PortConfigTable OBJECT-TYPE
        SYNTAX         SEQUENCE OF Tn5mx500PortConfigEntry
        MAX-ACCESS     not-accessible
        STATUS         current
        DESCRIPTION    "The ports on a 5MX500 optical card."
        ::= { tnOpticalPortConfig 522 }

    tn5mx500PortConfigEntry OBJECT-TYPE
        SYNTAX         Tn5mx500PortConfigEntry
        MAX-ACCESS     not-accessible
        STATUS         current
        DESCRIPTION    "."
        INDEX { ifIndex }
        ::= { tn5mx500PortConfigTable 1 }

    Tn5mx500PortConfigEntry ::=
        SEQUENCE {
            tn5mx500PortConfigFunction     INTEGER
        }

    tn5mx500PortConfigFunction OBJECT-TYPE
        SYNTAX         INTEGER {
                         client(1)
                       }
        MAX-ACCESS     read-only
        STATUS         current
        DESCRIPTION    "Indicates the functional type of this 5MX500 port."
        ::= { tn5mx500PortConfigEntry 1 }

--------------------------------------------------------------------------------
-- 2UX500 Optical Port Config Scalar
--------------------------------------------------------------------------------
    tn2ux500PortConfigAttributeTotal OBJECT-TYPE
        SYNTAX         Integer32
        MAX-ACCESS     read-only
        STATUS         current
        DESCRIPTION    "."
        ::= { tnOpticalPortConfig 523 }

--------------------------------------------------------------------------------
-- 2UX500 Optical Port Config Table
--------------------------------------------------------------------------------
    tn2ux500PortConfigTable OBJECT-TYPE
        SYNTAX         SEQUENCE OF Tn2ux500PortConfigEntry
        MAX-ACCESS     not-accessible
        STATUS         current
        DESCRIPTION    "The ports on a 2UX500 optical card."
        ::= { tnOpticalPortConfig 524 }

    tn2ux500PortConfigEntry OBJECT-TYPE
        SYNTAX         Tn2ux500PortConfigEntry
        MAX-ACCESS     not-accessible
        STATUS         current
        DESCRIPTION    "."
        INDEX { ifIndex }
        ::= { tn2ux500PortConfigTable 1 }

    Tn2ux500PortConfigEntry ::=
        SEQUENCE {
            tn2ux500PortConfigFunction     INTEGER
        }

    tn2ux500PortConfigFunction OBJECT-TYPE
        SYNTAX         INTEGER {
                         line(1)
                       }
        MAX-ACCESS     read-only
        STATUS         current
        DESCRIPTION    "Indicates the functional type of this 2UX500 port."
        ::= { tn2ux500PortConfigEntry 1 }

--------------------------------------------------------------------------------
-- MXN Optical Port Config Scalar
--------------------------------------------------------------------------------
    tnMxnPortConfigAttributeTotal OBJECT-TYPE
        SYNTAX         Integer32
        MAX-ACCESS     read-only
        STATUS         current
        DESCRIPTION    "."
        ::= { tnOpticalPortConfig 525 }

--------------------------------------------------------------------------------
-- MXN Optical Port Config Table
--------------------------------------------------------------------------------
    tnMxnPortConfigTable OBJECT-TYPE
        SYNTAX         SEQUENCE OF TnMxnPortConfigEntry
        MAX-ACCESS     not-accessible
        STATUS         current
        DESCRIPTION    "The ports on a MXN optical card."
        ::= { tnOpticalPortConfig 526 }

    tnMxnPortConfigEntry OBJECT-TYPE
        SYNTAX         TnMxnPortConfigEntry
        MAX-ACCESS     not-accessible
        STATUS         current
        DESCRIPTION    "."
        INDEX { ifIndex }
        ::= { tnMxnPortConfigTable 1 }

    TnMxnPortConfigEntry ::=
        SEQUENCE {
            tnMxnPortConfigAlienWaveBank                 TruthValue,
            tnMxnPortConfigPlannedFrequencyIn            Integer32,
            tnMxnPortConfigPlannedFrequencyOut           Integer32
       }

    tnMxnPortConfigAlienWaveBank OBJECT-TYPE
        SYNTAX         TruthValue
        MAX-ACCESS     read-create
        STATUS         current
        DESCRIPTION    "Alien wave bank allowed."
        DEFVAL         { false }
        ::= { tnMxnPortConfigEntry 1 }

    tnMxnPortConfigPlannedFrequencyIn OBJECT-TYPE
        SYNTAX         Integer32
        UNITS          "MHz"
        MAX-ACCESS     read-create
        STATUS         current
        DESCRIPTION    "Planned Center Frequency In.
                        Value in Mhz, which follows additional calculation:
                        (<number>*10 + 100000)*1000
                        (i.e.) (9130.625*10+100000)*1000 = 191306250."
        DEFVAL         { 0 }
        ::= { tnMxnPortConfigEntry 2 }

    tnMxnPortConfigPlannedFrequencyOut OBJECT-TYPE
        SYNTAX         Integer32
        UNITS          "MHz"
        MAX-ACCESS     read-create
        STATUS         current
        DESCRIPTION    "Planned Center Frequency Out.
                        Value in Mhz, which follows additional calculation:
                        (<number>*10 + 100000)*1000
                        (i.e.) (9130.625*10+100000)*1000 = 191306250."
        DEFVAL         { 0 }
        ::= { tnMxnPortConfigEntry 3 }

--------------------------------------------------------------------------------
-- ASC Optical Port Config Scalar
--------------------------------------------------------------------------------
    tnAscPortConfigAttributeTotal OBJECT-TYPE
        SYNTAX         Integer32
        MAX-ACCESS     read-only
        STATUS         current
        DESCRIPTION    "."
        ::= { tnOpticalPortConfig 527 }

--------------------------------------------------------------------------------
-- ASC Optical Port Config Table
--------------------------------------------------------------------------------
    tnAscPortConfigTable OBJECT-TYPE
        SYNTAX         SEQUENCE OF TnAscPortConfigEntry
        MAX-ACCESS     not-accessible
        STATUS         current
        DESCRIPTION    "The ports on a ASC optical card."
        ::= { tnOpticalPortConfig 528 }

    tnAscPortConfigEntry OBJECT-TYPE
        SYNTAX         TnAscPortConfigEntry
        MAX-ACCESS     not-accessible
        STATUS         current
        DESCRIPTION    "."
        INDEX { ifIndex }
        ::= { tnAscPortConfigTable 1 }

    TnAscPortConfigEntry ::=
        SEQUENCE {
            tnAscPortConfigPowerGain      Unsigned32,
            tnAscPortConfigPowerGainL     Unsigned32,  -- deprecated
            tnAscPortConfigAmpEnable      TruthValue,
            tnAscPortConfigVoaSet         Unsigned32
        }

    tnAscPortConfigPowerGain OBJECT-TYPE
        SYNTAX         Unsigned32
        UNITS          "mB"
        MAX-ACCESS     read-create
        STATUS         current
        DESCRIPTION    "."
        ::= { tnAscPortConfigEntry 1 }

    tnAscPortConfigPowerGainL OBJECT-TYPE
        SYNTAX         Unsigned32
        UNITS          "mB"
        MAX-ACCESS     read-create
        STATUS         deprecated
        DESCRIPTION    "."
        ::= { tnAscPortConfigEntry 2 }

    tnAscPortConfigAmpEnable OBJECT-TYPE
        SYNTAX         TruthValue
        MAX-ACCESS     read-create
        STATUS         current
        DESCRIPTION    "."
        ::= { tnAscPortConfigEntry 3 }

    tnAscPortConfigVoaSet OBJECT-TYPE
        SYNTAX         Unsigned32
        UNITS          "mB"
        MAX-ACCESS     read-create
        STATUS         current
        DESCRIPTION    "."
        ::= { tnAscPortConfigEntry 4 }

--------------------------------------------------------------------------------
-- OPSUM Optical Port Config Scalar
--------------------------------------------------------------------------------
    tnOpsumPortConfigAttributeTotal OBJECT-TYPE
        SYNTAX         Integer32
        MAX-ACCESS     read-only
        STATUS         current
        DESCRIPTION    "."
        ::= { tnOpticalPortConfig 529 }

--------------------------------------------------------------------------------
-- OPSUM Optical Port Config Table
--------------------------------------------------------------------------------
    tnOpsumPortConfigTable OBJECT-TYPE
        SYNTAX         SEQUENCE OF TnOpsumPortConfigEntry
        MAX-ACCESS     not-accessible
        STATUS         current
        DESCRIPTION    "The ports on an Opsum card."
        ::= { tnOpticalPortConfig 530 }

    tnOpsumPortConfigEntry OBJECT-TYPE
        SYNTAX         TnOpsumPortConfigEntry
        MAX-ACCESS     not-accessible
        STATUS         current
        DESCRIPTION    "."
        INDEX { ifIndex }
        ::= { tnOpsumPortConfigTable 1 }

    TnOpsumPortConfigEntry ::=
        SEQUENCE {
            tnOpsumPortConfigFunction     INTEGER
        }

    tnOpsumPortConfigFunction OBJECT-TYPE
        SYNTAX         INTEGER {
                         signal(1),
                         workingProtected(2)
                       }
        MAX-ACCESS     read-only
        STATUS         current
        DESCRIPTION    "Indicates the functional type of this Opsum port."
        ::= { tnOpsumPortConfigEntry 1 }

--------------------------------------------------------------------------------
-- MXN1624 Optical Port Config Scalar
--------------------------------------------------------------------------------
    tnMxn1624PortConfigAttributeTotal OBJECT-TYPE
        SYNTAX         Integer32
        MAX-ACCESS     read-only
        STATUS         current
        DESCRIPTION    "."
        ::= { tnOpticalPortConfig 531 }

--------------------------------------------------------------------------------
-- MXN1624 Optical Port Config Table
--------------------------------------------------------------------------------
    tnMxn1624PortConfigTable OBJECT-TYPE
        SYNTAX         SEQUENCE OF TnMxn1624PortConfigEntry
        MAX-ACCESS     not-accessible
        STATUS         current
        DESCRIPTION    "The ports on a MXN1624 optical card."
        ::= { tnOpticalPortConfig 532 }

    tnMxn1624PortConfigEntry OBJECT-TYPE
        SYNTAX         TnMxn1624PortConfigEntry
        MAX-ACCESS     not-accessible
        STATUS         current
        DESCRIPTION    "."
        INDEX { ifIndex }
        ::= { tnMxn1624PortConfigTable 1 }

    TnMxn1624PortConfigEntry ::=
        SEQUENCE {
            tnMxn1624PortConfigFunction     INTEGER
        }

    tnMxn1624PortConfigFunction OBJECT-TYPE
        SYNTAX         INTEGER {
                         sig(1),
                         ad(2),
                         lpbk(3),
                         tl(4),
                         fsm(5)
                       }
        MAX-ACCESS     read-only
        STATUS         current
        DESCRIPTION    "Indicates the functional type of this MXN1624 port."
        ::= { tnMxn1624PortConfigEntry 1 }

--------------------------------------------------------------------------------
-- IR4 Optical Port Config Scalar
--------------------------------------------------------------------------------
    tnIr4PortConfigAttributeTotal OBJECT-TYPE
        SYNTAX         Integer32
        MAX-ACCESS     read-only
        STATUS         current
        DESCRIPTION    "."
        ::= { tnOpticalPortConfig 533 }

--------------------------------------------------------------------------------
-- IR4 Optical Port Config Table
--------------------------------------------------------------------------------
    tnIr4PortConfigTable OBJECT-TYPE
        SYNTAX         SEQUENCE OF TnIr4PortConfigEntry
        MAX-ACCESS     not-accessible
        STATUS         current
        DESCRIPTION    "The ports on a IR4 optical card."
        ::= { tnOpticalPortConfig 534 }

    tnIr4PortConfigEntry OBJECT-TYPE
        SYNTAX         TnIr4PortConfigEntry
        MAX-ACCESS     not-accessible
        STATUS         current
        DESCRIPTION    "."
        INDEX { ifIndex }
        ::= { tnIr4PortConfigTable 1 }

    TnIr4PortConfigEntry ::=
        SEQUENCE {
            tnIr4PortConfigFunction     INTEGER
        }

    tnIr4PortConfigFunction OBJECT-TYPE
        SYNTAX         INTEGER {
                         lineIn(1),
                         inv(2),
                         osc(3),
                         lineOut(4),
                         oscSfp(5),
                         adt(6),
                         otdrRx(7),
                         otdrTx(8),
                         custLan(9)
                       }
        MAX-ACCESS     read-only
        STATUS         current
        DESCRIPTION    "Indicates the functional type of this IR4 port."
        ::= { tnIr4PortConfigEntry 1 }

--------------------------------------------------------------------------------
-- ASC2 Optical Port Config Scalar
--------------------------------------------------------------------------------
    tnAsc2PortConfigAttributeTotal OBJECT-TYPE
        SYNTAX         Integer32
        MAX-ACCESS     read-only
        STATUS         current
        DESCRIPTION    "."
        ::= { tnOpticalPortConfig 535 }

--------------------------------------------------------------------------------
-- ASC2 Optical Port Config Table
--------------------------------------------------------------------------------
    tnAsc2PortConfigTable OBJECT-TYPE
        SYNTAX         SEQUENCE OF TnAsc2PortConfigEntry
        MAX-ACCESS     not-accessible
        STATUS         current
        DESCRIPTION    "The ports on an ASC2 optical card."
        ::= { tnOpticalPortConfig 536 }

    tnAsc2PortConfigEntry OBJECT-TYPE
        SYNTAX         TnAsc2PortConfigEntry
        MAX-ACCESS     not-accessible
        STATUS         current
        DESCRIPTION    "."
        INDEX { ifIndex }
        ::= { tnAsc2PortConfigTable 1 }

    TnAsc2PortConfigEntry ::=
        SEQUENCE {
            tnAsc2PortConfigFunction     INTEGER
        }

    tnAsc2PortConfigFunction OBJECT-TYPE
        SYNTAX         INTEGER {
                         sigAIn(1),
                         aOut(2),
                         sigAOut(3),
                         aIn(4),
                         sigBIn(5),
                         bOut(6),
                         sigBOut(7),
                         bIn(8),
                         sigCIn(9),
                         cOut(10),
                         sigCOut(11),
                         cIn(12),
                         sigDIn(13),
                         dOut(14),
                         sigDOut(15),
                         dIn(16),
                         sigEIn(17),
                         eOut(18),
                         sigEOut(19),
                         eIn(20),
                         sigFIn(21),
                         fOut(22),
                         sigFOut(23),
                         fIn(24)
                       }
        MAX-ACCESS     read-only
        STATUS         current
        DESCRIPTION    "Indicates the functional type of this ASC2 port."
        ::= { tnAsc2PortConfigEntry 1 }

--------------------------------------------------------------------------------
-- Firmware Port Module Scalar
--------------------------------------------------------------------------------
    tnFwPortModuleAttributeTotal OBJECT-TYPE
        SYNTAX         Integer32
        MAX-ACCESS     read-only
        STATUS         current
        DESCRIPTION    "."
        ::= { tnOpticalPortConfig 537 }

--------------------------------------------------------------------------------
--  Firmware Port Module Table
--------------------------------------------------------------------------------
    tnFwPortModuleTable OBJECT-TYPE
        SYNTAX         SEQUENCE OF TnFwPortModuleEntry
        MAX-ACCESS     not-accessible
        STATUS         current
        DESCRIPTION    "."
        ::= { tnOpticalPortConfig 538 }

    tnFwPortModuleEntry OBJECT-TYPE
        SYNTAX         TnFwPortModuleEntry
        MAX-ACCESS     not-accessible
        STATUS         current
        DESCRIPTION    "."
        INDEX { tnFwPortModuleType }
        ::= { tnFwPortModuleTable 1 }

    TnFwPortModuleEntry ::= SEQUENCE {
        tnFwPortModuleType     Unsigned32,
        tnFwPortModule         INTEGER
    }

    tnFwPortModuleType OBJECT-TYPE
        SYNTAX         Unsigned32
        MAX-ACCESS     not-accessible
        STATUS         current
        DESCRIPTION    "The module type is defined as:
                          C2DCO4  - 1
                          BMDCO6  - 2
                          C2DCO4O - 3
                          BMDCO6L - 4
                          BMDCO6E - 5."
        ::= { tnFwPortModuleEntry 1 }

    tnFwPortModule OBJECT-TYPE
        SYNTAX         INTEGER {
                         hitlessAuto(1),
                         auto(2),
                         deferred(3)
                       }
        MAX-ACCESS     read-create
        STATUS         current
        DESCRIPTION    "."
        ::= { tnFwPortModuleEntry 2 }

--------------------------------------------------------------------------------
-- SFD48 Optical Port Config Scalar
--------------------------------------------------------------------------------
    tnSfd48PortConfigAttributeTotal OBJECT-TYPE
        SYNTAX         Integer32
        MAX-ACCESS     read-only
        STATUS         current
        DESCRIPTION    "."
        ::= { tnOpticalPortConfig 539 }

--------------------------------------------------------------------------------
-- SFD48 Optical Port Config Table
--------------------------------------------------------------------------------
    tnSfd48PortConfigTable OBJECT-TYPE
        SYNTAX         SEQUENCE OF TnSfd48PortConfigEntry
        MAX-ACCESS     not-accessible
        STATUS         current
        DESCRIPTION    "The ports on a SFD48 optical card."
        ::= { tnOpticalPortConfig 540 }

    tnSfd48PortConfigEntry OBJECT-TYPE
        SYNTAX         TnSfd48PortConfigEntry
        MAX-ACCESS     not-accessible
        STATUS         current
        DESCRIPTION    "."
        INDEX { ifIndex }
        ::= { tnSfd48PortConfigTable 1 }

    TnSfd48PortConfigEntry ::=
        SEQUENCE {
            tnSfd48PortConfigFunction     INTEGER
        }

    tnSfd48PortConfigFunction OBJECT-TYPE
        SYNTAX         INTEGER {
                         channel(1),
                         mux(2)
                       }
        MAX-ACCESS     read-only
        STATUS         current
        DESCRIPTION    "Indicates the functional type of this SFD48 port."
        ::= { tnSfd48PortConfigEntry 1 }

--------------------------------------------------------------------------------
-- SFD64 Optical Port Config Scalar
--------------------------------------------------------------------------------
    tnSfd64PortConfigAttributeTotal OBJECT-TYPE
        SYNTAX         Integer32
        MAX-ACCESS     read-only
        STATUS         current
        DESCRIPTION    "."
        ::= { tnOpticalPortConfig 541 }

--------------------------------------------------------------------------------
-- SFD64 Optical Port Config Table
--------------------------------------------------------------------------------
    tnSfd64PortConfigTable OBJECT-TYPE
        SYNTAX         SEQUENCE OF TnSfd64PortConfigEntry
        MAX-ACCESS     not-accessible
        STATUS         current
        DESCRIPTION    "The ports on a SFD64 optical card."
        ::= { tnOpticalPortConfig 542 }

    tnSfd64PortConfigEntry OBJECT-TYPE
        SYNTAX         TnSfd64PortConfigEntry
        MAX-ACCESS     not-accessible
        STATUS         current
        DESCRIPTION    "."
        INDEX { ifIndex }
        ::= { tnSfd64PortConfigTable 1 }

    TnSfd64PortConfigEntry ::=
        SEQUENCE {
            tnSfd64PortConfigFunction     INTEGER
        }

    tnSfd64PortConfigFunction OBJECT-TYPE
        SYNTAX         INTEGER {
                         channel(1),
                         mux(2)
                       }
        MAX-ACCESS     read-only
        STATUS         current
        DESCRIPTION    "Indicates the functional type of this SFD64 port."
        ::= { tnSfd64PortConfigEntry 1 }

--------------------------------------------------------------------------------
-- IR32AW Optical Port Config Scalar
--------------------------------------------------------------------------------
    tnIr32AWPortConfigAttributeTotal OBJECT-TYPE
        SYNTAX         Integer32
        MAX-ACCESS     read-only
        STATUS         current
        DESCRIPTION    "."
        ::= { tnOpticalPortConfig 543 }

--------------------------------------------------------------------------------
-- IR32AW Optical Port Config Table
--------------------------------------------------------------------------------
    tnIr32AWPortConfigTable OBJECT-TYPE
        SYNTAX         SEQUENCE OF TnIr32AWPortConfigEntry
        MAX-ACCESS     not-accessible
        STATUS         current
        DESCRIPTION    "The ports on a IR32AW optical card."
        ::= { tnOpticalPortConfig 544 }

    tnIr32AWPortConfigEntry OBJECT-TYPE
        SYNTAX         TnIr32AWPortConfigEntry
        MAX-ACCESS     not-accessible
        STATUS         current
        DESCRIPTION    "."
        INDEX { ifIndex }
        ::= { tnIr32AWPortConfigTable 1 }

    TnIr32AWPortConfigEntry ::=
        SEQUENCE {
            tnIr32AWPortConfigFunction INTEGER
        }
    tnIr32AWPortConfigFunction OBJECT-TYPE
        SYNTAX         INTEGER {
                         lineIn(1),
                         inv(2),
                         osc(3),
                         lineOut(4),
                         oscSfp(5),
                         adt(6),
                         lineLoading(7),
                         otdr(8),
                         custLan(9),
                         testLaser(10),
                         mpoFs(11),
                         oscLan(12)
                       }
        MAX-ACCESS     read-only
        STATUS         current
        DESCRIPTION    "Indicates the functional type of this IR32AW port."
        ::= { tnIr32AWPortConfigEntry 1 }

-------------------------------------------------------------------------------
-- EILAAW Optical Port Config Scalar
-------------------------------------------------------------------------------
    tnEilaAWPortConfigAttributeTotal OBJECT-TYPE
        SYNTAX         Integer32
        MAX-ACCESS     read-only
        STATUS         current
        DESCRIPTION    "."
        ::= { tnOpticalPortConfig 545 }

-------------------------------------------------------------------------------
-- EILAAW Optical Port Config Table
-------------------------------------------------------------------------------
    tnEilaAWPortConfigTable OBJECT-TYPE
        SYNTAX         SEQUENCE OF TnEilaAWPortConfigEntry
        MAX-ACCESS     not-accessible
        STATUS         current
        DESCRIPTION    "The ports on a EILAAW optical card."
        ::= { tnOpticalPortConfig 546 }

    tnEilaAWPortConfigEntry OBJECT-TYPE
        SYNTAX         TnEilaAWPortConfigEntry
        MAX-ACCESS     not-accessible
        STATUS         current
        DESCRIPTION    "."
        INDEX { ifIndex }
        ::= { tnEilaAWPortConfigTable 1 }

    TnEilaAWPortConfigEntry ::=
        SEQUENCE {
            tnEilaAWPortConfigFunction INTEGER
        }

    tnEilaAWPortConfigFunction OBJECT-TYPE
        SYNTAX         INTEGER {
                         lineIn(1),
                         otdr(2),
                         lineOut(3),
                         oscSfp(4),
                         osc(5),
                         custLan(6),
                         inv(7),
                         oscLan(8)
                       }
        MAX-ACCESS     read-only
        STATUS         current
        DESCRIPTION    "Indicates the functional type of this EILAAW port."
        ::= { tnEilaAWPortConfigEntry 1 }

-------------------------------------------------------------------------------
-- 18CE300 Optical Port Config Scalar
-------------------------------------------------------------------------------
    tn18ce300PortConfigAttributeTotal OBJECT-TYPE
        SYNTAX         Integer32
        MAX-ACCESS     read-only
        STATUS         current
        DESCRIPTION    "."
        ::= { tnOpticalPortConfig 547 }

-------------------------------------------------------------------------------
-- 18CE300 Optical Port Config Table
-------------------------------------------------------------------------------
    tn18ce300PortConfigTable OBJECT-TYPE
        SYNTAX         SEQUENCE OF Tn18ce300PortConfigEntry
        MAX-ACCESS     not-accessible
        STATUS         current
        DESCRIPTION    "The ports on a 18CE300 optical card."
        ::= { tnOpticalPortConfig 548 }

    tn18ce300PortConfigEntry OBJECT-TYPE
        SYNTAX         Tn18ce300PortConfigEntry
        MAX-ACCESS     not-accessible
        STATUS         current
        DESCRIPTION    "."
        INDEX { ifIndex }
        ::= { tn18ce300PortConfigTable 1 }

    Tn18ce300PortConfigEntry ::=
        SEQUENCE {
            tn18ce300PortConfigFunction INTEGER
        }

    tn18ce300PortConfigFunction OBJECT-TYPE
        SYNTAX         INTEGER {
                         network(1),
                         client(2),
                         backplane(3),
                         ethman(4)
                       }
        MAX-ACCESS     read-only
        STATUS         current
        DESCRIPTION    "Indicates the functional type of this 18CE300 port."
        ::= { tn18ce300PortConfigEntry 1 }

-------------------------------------------------------------------------------
-- GNSS Module Config Scalar
-------------------------------------------------------------------------------
    tnGnssModuleAttributeTotal OBJECT-TYPE
        SYNTAX         Integer32
        MAX-ACCESS     read-only
        STATUS         current
        DESCRIPTION    "."
        ::= { tnOpticalPortConfig 549 }

--------------------------------------------------------------------------------
-- GNSS Module Table
--------------------------------------------------------------------------------
    tnGnssModuleTable OBJECT-TYPE
        SYNTAX         SEQUENCE OF TnGnssModuleEntry
        MAX-ACCESS     not-accessible
        STATUS         current
        DESCRIPTION    "Common attributes of GNSS module."
        ::= { tnOpticalPortConfig 550 }

    tnGnssModuleEntry OBJECT-TYPE
        SYNTAX         TnGnssModuleEntry
        MAX-ACCESS     not-accessible
        STATUS         current
        DESCRIPTION    "."
        INDEX { ifIndex }
        ::= { tnGnssModuleTable 1 }

    TnGnssModuleEntry ::=
        SEQUENCE {
            tnGnssModuleAdminState                      INTEGER,
            tnGnssModuleOperState                       INTEGER,
            tnGnssModuleReset                           INTEGER,
            tnGnssModuleMode                            BITS,
            tnGnssModuleAugmentationMode                BITS,
            tnGnssModuleElevationMask                   Unsigned32,
            tnGnssModuleSNRMask                         Unsigned32,
            tnGnssModuleTimeAdvance                     Unsigned32,
            tnGnssModuleAntennaDelayValue               INTEGER,
            tnGnssModuleForcedAntennaConnected          TruthValue,
            tnGnssModulePtpPTPClockPriority1            Unsigned32,
            tnGnssModulePtpPTPClockPriority2            Unsigned32,
            tnGnssModulePtpPTPClockDomainNumber         Unsigned32,
            tnGnssModulePtpPTPPortTxDestMacAddress      INTEGER,
            tnGnssModulePtpPortAsymmetryCorrection      INTEGER,
            tnGnssModuleSyncEMode                       INTEGER,
            tnGnssModuleProvisionedRxSsmQL              INTEGER,
            tnGnssModuleTxSsm                           INTEGER,
            tnGnssModuleSignalType                      INTEGER,
            tnGnssModuleGnssStatusTracking              INTEGER,
            tnGnssModuleGnssStatusLocationMode          INTEGER,
            tnGnssModuleCoordinateLatitude              OCTET STRING,
            tnGnssModuleCoordinateLongitude             OCTET STRING,
            tnGnssModuleCoordinateAltitude              Integer32,
            tnGnssModuleHorizontalAccuracy              Integer32,
            tnGnssModuleVerticalAccuracy                Integer32,
            tnGnssModuleTimeDOP                         Integer32,
            tnGnssModuleHorizontalDOP                   Integer32,
            tnGnssModuleVerticalDOP                     Integer32,
            tnGnssModuleSatelliteStatus                 OCTET STRING,
            tnGnssModulePTPClockProfile                 INTEGER,
            tnGnssModulePTPClockType                    INTEGER,
            tnGnssModulePTPClockGmClockIdentity         NokiaPtpClockIdentifier,
            tnGnssModulePTPClockClockClass              Unsigned32,
            tnGnssModulePTPClockClockRecoveryState      INTEGER,
            tnGnssModulePTPClockPhaseRecoveryState      INTEGER,
            tnGnssModulePTPClockTimeSource              INTEGER,
            tnGnssModulePTPClockFreqTraceabilityStatus  TruthValue,
            tnGnssModulePTPClockTimeTraceabilityStatus  TruthValue,
            tnGnssModulePTPPortmAnnounceMsgRate         INTEGER,
            tnGnssModulePTPPortSyncMessageRate          INTEGER,
            tnGnssModulePTPPortmDelayReqRespMsgRate     INTEGER,
            tnGnssModuleMessageMode                     INTEGER,
            tnGnssModuleClockStatusFrequency            INTEGER,
            tnGnssModuleAlmProfName                     OCTET STRING
        }

    tnGnssModuleAdminState OBJECT-TYPE
        SYNTAX         INTEGER {
                         up(1),
                         down(2)
                       }
        MAX-ACCESS     read-create
        STATUS         current
        DESCRIPTION    "GNSS Module AdminState."
        ::= { tnGnssModuleEntry 1 }

    tnGnssModuleOperState OBJECT-TYPE
        SYNTAX         INTEGER {
                         up(1),
                         down(2)
                       }
        MAX-ACCESS     read-only
        STATUS         current
        DESCRIPTION    "GNSS Module OperState."
        ::= { tnGnssModuleEntry 2 }

    tnGnssModuleReset OBJECT-TYPE
        SYNTAX         INTEGER {
                         warm(1)
                       }
        MAX-ACCESS     read-create
        STATUS         current
        DESCRIPTION    "GNSS Module reset."
        ::= { tnGnssModuleEntry 3 }

    tnGnssModuleMode OBJECT-TYPE
        SYNTAX         BITS {
                         gps(0),
                         glonass(1),
                         beidou(2)
                       }
        MAX-ACCESS     read-create
        STATUS         current
        DESCRIPTION    "GNSS Module receiver mode:
                          gps(0x80),
                          glonass(0x40),
                          beidou(0x20),
                          gps_glonass(0xC0),
                          gps_beidou(0xA0)."
        ::= { tnGnssModuleEntry 4 }

    tnGnssModuleAugmentationMode OBJECT-TYPE
        SYNTAX         BITS {
                         sbas(4),
                         qzss(5)
                       }
        MAX-ACCESS     read-create
        STATUS         current
        DESCRIPTION    "GNSS Module receiver augmentation mode:
                          none(0x00),
                          sbas(0x08),
                          qzss(0x04),
                          sbas_qzss(0x0C)."
        ::= { tnGnssModuleEntry 5 }

    tnGnssModuleElevationMask OBJECT-TYPE
        SYNTAX         Unsigned32 (1..90)
        MAX-ACCESS     read-create
        STATUS         current
        DESCRIPTION    "The minimum elevation mask for the GNSS receiver of
                        the external GNSS-GM module, the unit is degree."
        ::= { tnGnssModuleEntry 6 }

    tnGnssModuleSNRMask OBJECT-TYPE
        SYNTAX         Unsigned32 (1..60)
        MAX-ACCESS     read-create
        STATUS         current
        DESCRIPTION    "The minimum SNR (Signal-to-noise) mask for the GNSS
                        receiver of the external GNSS-GM module, the unit is
                        dBHz."
        ::= { tnGnssModuleEntry 7 }

    tnGnssModuleTimeAdvance OBJECT-TYPE
        SYNTAX         Unsigned32 (0..200)
        MAX-ACCESS     read-create
        STATUS         current
        DESCRIPTION    "GNSS Module time advance value (ns)."
        ::= { tnGnssModuleEntry 8 }

    tnGnssModuleAntennaDelayValue OBJECT-TYPE
        SYNTAX         INTEGER (0..9999)
        MAX-ACCESS     read-create
        STATUS         current
        DESCRIPTION    "The RF antenna cable delay for the GNSS receiver of
                        the external GNSS-GM module, the unit is ns."
        ::= { tnGnssModuleEntry 9 }

    tnGnssModuleForcedAntennaConnected OBJECT-TYPE
        SYNTAX         TruthValue
        MAX-ACCESS     read-create
        STATUS         current
        DESCRIPTION    "The antenna state for the GNSS receiver of the
                        external GNSS-GM module."
        ::= { tnGnssModuleEntry 10 }

    tnGnssModulePtpPTPClockPriority1 OBJECT-TYPE
        SYNTAX         Unsigned32 (0..255)
        MAX-ACCESS     read-only
        STATUS         current
        DESCRIPTION    "The priority1 attribute for the T-GM clock of the
                        external GNSS-GM module."
        ::= { tnGnssModuleEntry 11 }

    tnGnssModulePtpPTPClockPriority2 OBJECT-TYPE
        SYNTAX         Unsigned32 (0..255)
        MAX-ACCESS     read-create
        STATUS         current
        DESCRIPTION    "The priority2 attribute for the T-GM clock of the
                        external GNSS-GM module."
        ::= { tnGnssModuleEntry 12 }

    tnGnssModulePtpPTPClockDomainNumber OBJECT-TYPE
        SYNTAX         Unsigned32 (24..43)
        MAX-ACCESS     read-create
        STATUS         current
        DESCRIPTION    "The domain number attribute for the T-GM clock of
                        the external GNSS-GM module."
        ::= { tnGnssModuleEntry 13 }

    tnGnssModulePtpPTPPortTxDestMacAddress OBJECT-TYPE
        SYNTAX         INTEGER {
                         forwardable(1),
                         nonForwardable(2)
                       }
        MAX-ACCESS     read-create
        STATUS         current
        DESCRIPTION    "The multicast destination MAC address for the PTP port
                        of the T-GM clock of the exter-nal GNSS-GM module."
        ::= { tnGnssModuleEntry 14 }

    tnGnssModulePtpPortAsymmetryCorrection OBJECT-TYPE
        SYNTAX         INTEGER (-100000000..100000000)
        MAX-ACCESS     read-create
        STATUS         current
        DESCRIPTION    "The asymmetry correction value for the PTP port of
                        the T-GM of the external GNSS-GM module."
        ::= { tnGnssModuleEntry 15 }

    tnGnssModuleSyncEMode OBJECT-TYPE
        SYNTAX         INTEGER {
                         slave(1),
                         master(2)
                       }
        MAX-ACCESS     read-create
        STATUS         current
        DESCRIPTION    "GNSS Module SyncE mode (master or slave)."
        ::= { tnGnssModuleEntry 16 }

    tnGnssModuleProvisionedRxSsmQL OBJECT-TYPE
        SYNTAX         INTEGER {
                         dnu(1),  -- SDH DNU/SONET DUS
                         auto(2),
                         prc(3)   -- SDH PRC/SONET PRS
                       }
        MAX-ACCESS     read-create
        STATUS         current
        DESCRIPTION    "The provisioned incoming QL for the SyncE clock of
                        the external GNSS-GM module.
                        SDH Mode:
                            1: DNU
                            2: auto
                            3: PRC
                        SONET Mode:
                            1: DUS
                            2: auto
                            3: PRS."
        ::= { tnGnssModuleEntry 17 }

    tnGnssModuleTxSsm OBJECT-TYPE
        SYNTAX         INTEGER {
                         enabled(1),
                         disabled(2)
                       }
        MAX-ACCESS     read-only
        STATUS         current
        DESCRIPTION    "GNSS Module TX SMM enable/disable."
        ::= { tnGnssModuleEntry 18 }

    tnGnssModuleSignalType OBJECT-TYPE
        SYNTAX         INTEGER {
                         pps1(1),
                         m2(2),
                         m10(3)
                       }
        MAX-ACCESS     read-create
        STATUS         current
        DESCRIPTION    "The signal type of the 1PSS/CLK output port of
                        the external GNSS-GM module."
        ::= { tnGnssModuleEntry 19 }

    tnGnssModuleGnssStatusTracking OBJECT-TYPE
        SYNTAX         INTEGER {
                         freerun(1),
                         warmup(2),
                         tracking(3),
                         transition(4),
                         holdover(5),
                         locked(6)
                       }
        MAX-ACCESS     read-only
        STATUS         current
        DESCRIPTION    "GNSS module gnssstatus Tracking Mode,
                        and syncstatus clock status phase."
        ::= { tnGnssModuleEntry 20 }

    tnGnssModuleGnssStatusLocationMode OBJECT-TYPE
        SYNTAX         INTEGER {
                         notApplicable(0),
                         navigation(1),
                         surveyIn(2),
                         fixed(3)
                       }
        MAX-ACCESS     read-only
        STATUS         current
        DESCRIPTION    "GNSS module gnssstatus Location Mode."
        ::= { tnGnssModuleEntry 21 }

    tnGnssModuleCoordinateLatitude OBJECT-TYPE
        SYNTAX         OCTET STRING (SIZE(0..32))
        MAX-ACCESS     read-only
        STATUS         current
        DESCRIPTION    "GNSS module Receiver Port coordinate latitude."
        ::= { tnGnssModuleEntry 22 }

    tnGnssModuleCoordinateLongitude OBJECT-TYPE
        SYNTAX         OCTET STRING (SIZE(0..32))
        MAX-ACCESS     read-only
        STATUS         current
        DESCRIPTION    "GNSS module Receiver Port coordinate longitude."
        ::= { tnGnssModuleEntry 23 }

    tnGnssModuleCoordinateAltitude OBJECT-TYPE
        SYNTAX         Integer32
        MAX-ACCESS     read-only
        STATUS         current
        DESCRIPTION    "GNSS module Receiver Port coordinate altitude
                        in meters."
        ::= { tnGnssModuleEntry 24 }

    tnGnssModuleHorizontalAccuracy OBJECT-TYPE
        SYNTAX         Integer32
        MAX-ACCESS     read-only
        STATUS         current
        DESCRIPTION    "GNSS module horizontal accuracy (in millimeters) of
                        the position fix determined by the GNSS receiver."
        ::= { tnGnssModuleEntry 25 }

    tnGnssModuleVerticalAccuracy OBJECT-TYPE
        SYNTAX         Integer32
        MAX-ACCESS     read-only
        STATUS         current
        DESCRIPTION    "GNSS module vertical accuracy (in millimeters) of
                        the position fix determined by the GNSS receiver."
        ::= { tnGnssModuleEntry 26 }

    tnGnssModuleTimeDOP OBJECT-TYPE
        SYNTAX         Integer32
        MAX-ACCESS     read-only
        STATUS         current
        DESCRIPTION    "GNSS module the dimensionless TDOP value calculated
                        by the GNSS Receiver. The value is expressed in
                        hundredth of the TDOP definition. For instance,
                        a value of 153 means that TDOP calculated by GNSS
                        Receiver is 1.53. When the value cannot be evaluated
                        by the GNSS Receiver, the value is shown with the
                        minimum range value 0."
        ::= { tnGnssModuleEntry 27 }

    tnGnssModuleHorizontalDOP OBJECT-TYPE
        SYNTAX         Integer32
        MAX-ACCESS     read-only
        STATUS         current
        DESCRIPTION    "GNSS module the dimensionless HDOP value calculated
                        by the GNSS Receiver while GNSS Receiver Survey
                        Pogress is not complete yet or the receiver is in
                        navigation mode. The value is expressed in hundredth
                        of the HDOP definition. For instance, a value of 153
                        means that HDOP calculated by GNSS Receiver is 1.53.
                        When the value cannot be evaluated by the GNSS Receiver
                        or when Survey Progress is complete, the value is shown
                        with the minimum range value 0."
        ::= { tnGnssModuleEntry 28 }

    tnGnssModuleVerticalDOP OBJECT-TYPE
        SYNTAX         Integer32
        MAX-ACCESS     read-only
        STATUS         current
        DESCRIPTION    "GNSS module the dimensionless VDOP value calculated
                        by the GNSS Receiver while GNSS Receiver Survey
                        Pogress is not complete yet or the receiver is in
                        navigation mode. The value is expressed in hundredth
                        of the VDOP definition. For instance, a value of 153
                        means that VDOP calculated by GNSS Receiver is 1.53.
                        When the value cannot be evaluated by the GNSS Receiver
                        or when Survey Progress is complete, the value is shown
                        with the minimum range value 0."
        ::= { tnGnssModuleEntry 29 }

    tnGnssModuleSatelliteStatus OBJECT-TYPE
        SYNTAX         OCTET STRING (SIZE(0..512))
        MAX-ACCESS     read-only
        STATUS         current
        DESCRIPTION    "GNSS module gnss status Satellite Status:

                        | byte 1  | byte 2  | byte 3  | ....... | byte 15 | byte 16 |
                        | byte 17 | byte 18 | byte 19 | ....... | byte 31 | byte 32 |

                        size of 1 SatelliteStatus structure = 16 bytes,
                        defined as below:

                        struct SatelliteStatus
                        {
                          // byte 1~2
                          U16 SVType;   // f3SatelliteSVType
                                        //   gps(0x80)
                                        //   glonass(0x40)
                                        //   beidou(0x20)
                                        //   galileo(0x10)

                          // byte 3~4
                          U16 SV;       // f3SatelliteSV
                                        // Unsigned32 (1..255)

                          // byte 5~8
                          U32 SNR;      // f3SatelliteCNO
                                        // Unsigned32

                          // byte 9
                          U8 Health;    // TruthValue
                                        //   true(1) =f3SatelliteHealth ok(2)
                                        //   false(2)=f3SatelliteHealth other

                          // byte 10
                          U8 InUse;     // TruthValue
                                        //   true(1)
                                        //   false(2)

                          // byte 11~12
                          U16 Azimuth;  // f3SatelliteAzimuth
                                        // Unsigned32 (0..360)

                          // byte 13
                          U8 Elevation; // f3SatelliteElevation
                                        // Unsigned32 (0..90)

                          // byte 14~16
                          U8 pad_byte_1;// reserved
                          U8 pad_byte_2;// reserved
                          U8 pad_byte_3;// reserved
                        };

                        byte 1 ~ 16 for SatelliteStatus #1,
                        byte 17 ~ 32 for SatelliteStatus #2,
                        ...
                        byte 497 ~ 512 for SatelliteStatus #32."
        ::= { tnGnssModuleEntry 30 }

    tnGnssModulePTPClockProfile OBJECT-TYPE
        SYNTAX         INTEGER {
                         g82751(1)
                       }
        MAX-ACCESS     read-only
        STATUS         current
        DESCRIPTION    "GNSS module PTPClock profile."
        ::= { tnGnssModuleEntry 31 }

    tnGnssModulePTPClockType OBJECT-TYPE
        SYNTAX         INTEGER {
                         tGgm(1),
                         tTsc(2),
                         idle(3),
                         tBc(4),
                         gm(5)
                       }
        MAX-ACCESS     read-only
        STATUS         current
        DESCRIPTION    "GNSS module PTPClock type."
        ::= { tnGnssModuleEntry 32 }

    tnGnssModulePTPClockGmClockIdentity OBJECT-TYPE
        SYNTAX         NokiaPtpClockIdentifier
        MAX-ACCESS     read-only
        STATUS         current
        DESCRIPTION    "GNSS module PTPClock Identity."
        ::= { tnGnssModuleEntry 33 }

    tnGnssModulePTPClockClockClass OBJECT-TYPE
        SYNTAX         Unsigned32
        MAX-ACCESS     read-only
        STATUS         current
        DESCRIPTION    "GNSS module PTPClock class."
        ::= { tnGnssModuleEntry 34 }

    tnGnssModulePTPClockClockRecoveryState OBJECT-TYPE
        SYNTAX         INTEGER {
                         notApplicable(0),
                         start(1),
                         normal(2),
                         freerun(3),
                         holdover(4),
                         acquisition(5),
                         transient(6),
                         none(7),
                         holdoverOutOfSpec(8),
                         holdoverInSpe(9)
                       }
        MAX-ACCESS     read-only
        STATUS         current
        DESCRIPTION    "GNSS module PTPClock recovery state."
        ::= { tnGnssModuleEntry 35 }

    tnGnssModulePTPClockPhaseRecoveryState OBJECT-TYPE
        SYNTAX         INTEGER {
                         notApplicable(0),
                         freerun(1),
                         holdover(2),
                         normal(3),
                         start(4),
                         acquisition(5),
                         transient(6),
                         none(7),
                         holdoverOutOfSpec(8),
                         holdoverInSpe(9)
                       }
        MAX-ACCESS     read-only
        STATUS         current
        DESCRIPTION    "GNSS module PTPClock recovery state."
        ::= { tnGnssModuleEntry 36 }

    tnGnssModulePTPClockTimeSource OBJECT-TYPE
        SYNTAX         INTEGER {
                         atomicClock(1),
                         gps(2),
                         terrestrialRadio(3),
                         ptp(4),
                         ntp(5),
                         handSet(6),
                         other(7),
                         internalOscillator(8)
                       }
        MAX-ACCESS     read-only
        STATUS         current
        DESCRIPTION    "GNSS module PTPClock time source."
        ::= { tnGnssModuleEntry 37 }

    tnGnssModulePTPClockFreqTraceabilityStatus OBJECT-TYPE
        SYNTAX         TruthValue
        MAX-ACCESS     read-only
        STATUS         current
        DESCRIPTION    "GNSS module PTPClock Frequency traceability status."
        ::= { tnGnssModuleEntry 38 }

    tnGnssModulePTPClockTimeTraceabilityStatus OBJECT-TYPE
        SYNTAX         TruthValue
        MAX-ACCESS     read-only
        STATUS         current
        DESCRIPTION    "GNSS module PTPClock Time traceability status."
        ::= { tnGnssModuleEntry 39 }

    tnGnssModulePTPPortmAnnounceMsgRate OBJECT-TYPE
        SYNTAX         INTEGER {
                         notApplicable(0),
                         pkt1per16secs(1),
                         pkt1per8secs(2),
                         pkt1per4secs(3),
                         pkt1per2secs(4),
                         pkt1per1sec(5),
                         pkts2per1sec(6),
                         pkts4per1sec(7),
                         pkts8per1sec(8),
                         none(9)
                       }
        MAX-ACCESS     read-only
        STATUS         current
        DESCRIPTION    "GNSS module PTPPort Announce Message Rate."
        ::= { tnGnssModuleEntry 40 }

    tnGnssModulePTPPortSyncMessageRate OBJECT-TYPE
        SYNTAX         INTEGER {
                         notApplicable(0),
                         pkt1persec(1),
                         pkts2persec(2),
                         pkts4persec(3),
                         pkts8persec(4),
                         pkts16persec(5),
                         pkts32persec(6),
                         pkts64persec(7),
                         pkts128persec(8),
                         none(9)
                       }
        MAX-ACCESS     read-only
        STATUS         current
        DESCRIPTION    "GNSS module PTPPort Sync Message Rate."
        ::= { tnGnssModuleEntry 41 }

    tnGnssModulePTPPortmDelayReqRespMsgRate OBJECT-TYPE
        SYNTAX         INTEGER {
                         notApplicable(0),
                         pkt1persec(1),
                         pkts2persec(2),
                         pkts4persec(3),
                         pkts8persec(4),
                         pkts16persec(5),
                         pkts32persec(6),
                         pkts64persec(7),
                         pkts128persec(8),
                         none(9),
                         na(10),
                         pkts0persec(11)
                       }
        MAX-ACCESS     read-only
        STATUS         current
        DESCRIPTION    "GNSS module PTPPort Delay Response Message Rate."
        ::= { tnGnssModuleEntry 42 }

    tnGnssModuleMessageMode OBJECT-TYPE
        SYNTAX         INTEGER {
                         unknown(1),
                         oneStep(2),
                         twoStep(3)
                       }
        MAX-ACCESS     read-only
        STATUS         current
        DESCRIPTION    "GNSS module PTPPort the Master Clock Type."
        ::= { tnGnssModuleEntry 43 }

    tnGnssModuleClockStatusFrequency OBJECT-TYPE
        SYNTAX         INTEGER {
                         notAvailable(1),
                         freerun(2),
                         holdover(3),
                         tracking(4),
                         lossoflock(5),
                         locked(6),
                         bypass(7)
                       }
        MAX-ACCESS     read-only
        STATUS         current
        DESCRIPTION    "GNSS module syncstatus clock status frequency."
        ::= { tnGnssModuleEntry 44 }

    tnGnssModuleAlmProfName OBJECT-TYPE
        SYNTAX         OCTET STRING (SIZE(1..40))
        MAX-ACCESS     read-create
        STATUS         current
        DESCRIPTION    "."
        ::= { tnGnssModuleEntry 45 }

--------------------------------------------------------------------------------
-- OPSUML Optical Port Config Scalar
--------------------------------------------------------------------------------
    tnOpsumlPortConfigAttributeTotal OBJECT-TYPE
        SYNTAX         Integer32
        MAX-ACCESS     read-only
        STATUS         current
        DESCRIPTION    "."
        ::= { tnOpticalPortConfig 551 }

--------------------------------------------------------------------------------
-- OPSUML Optical Port Config Table
--------------------------------------------------------------------------------
    tnOpsumlPortConfigTable OBJECT-TYPE
        SYNTAX         SEQUENCE OF TnOpsumPortConfigEntry
        MAX-ACCESS     not-accessible
        STATUS         current
        DESCRIPTION    "The ports on an Opsuml card."
        ::= { tnOpticalPortConfig 552 }

    tnOpsumlPortConfigEntry OBJECT-TYPE
        SYNTAX         TnOpsumlPortConfigEntry
        MAX-ACCESS     not-accessible
        STATUS         current
        DESCRIPTION    "."
        INDEX { ifIndex }
        ::= { tnOpsumlPortConfigTable 1 }

    TnOpsumlPortConfigEntry ::=
        SEQUENCE {
            tnOpsumlPortConfigFunction     INTEGER
        }

    tnOpsumlPortConfigFunction OBJECT-TYPE
        SYNTAX         INTEGER {
                         signal(1),
                         workingProtected(2)
                       }
        MAX-ACCESS     read-only
        STATUS         current
        DESCRIPTION    "Indicates the functional type of this Opsuml port."
        ::= { tnOpsumlPortConfigEntry 1 }

--------------------------------------------------------------------------------
-- Optical Port Information
--------------------------------------------------------------------------------

--------------------------------------------------------------------------------
-- SDH Optical Port Info Scalar
--------------------------------------------------------------------------------
    tnSdhPortInfoAttributeTotal OBJECT-TYPE
        SYNTAX         Integer32
        MAX-ACCESS     read-only
        STATUS         current
        DESCRIPTION    "."
        ::= { tnOpticalPortInfo 1 }

--------------------------------------------------------------------------------
-- SDH Optical Port Info Table
--------------------------------------------------------------------------------
    tnSdhPortInfoTable OBJECT-TYPE
        SYNTAX         SEQUENCE OF TnSdhPortInfoEntry
        MAX-ACCESS     not-accessible
        STATUS         current
        DESCRIPTION    "The ports on SDH supported cards."
        ::= { tnOpticalPortInfo 2 }

    tnSdhPortInfoEntry OBJECT-TYPE
        SYNTAX         TnSdhPortInfoEntry
        MAX-ACCESS     not-accessible
        STATUS         current
        DESCRIPTION    "."
        INDEX { ifIndex }
        ::= { tnSdhPortInfoTable 1 }

    TnSdhPortInfoEntry ::=
        SEQUENCE {
            tnSdhPortRxSectionTrace       SnmpAdminString,
--            obsolete
--            tnSdhPortTxSynchStatusMessage TropicSonetS1,
            tnSdhPortTiming               INTEGER,
--            obsolete
--            tnSdhPortRxSynchStatusMessage TropicSonetS1,
            tnSdhPortRxSectionTraceValid  TruthValue,
            tnSdhPortTxSynchronizeStatusMessage TropicSdhS1,
            tnSdhPortRxSynchronizeStatusMessage TropicSdhS1
        }

    tnSdhPortRxSectionTrace OBJECT-TYPE
        SYNTAX         SnmpAdminString (SIZE(0..255))
        MAX-ACCESS     read-only
        STATUS         current
        DESCRIPTION    "."
        ::= { tnSdhPortInfoEntry 1 }

--    obsolete
--    tnSdhPortTxSynchStatusMessage OBJECT-TYPE ::= { tnSdhPortInfoEntry 2 }

    tnSdhPortTiming OBJECT-TYPE
        SYNTAX         INTEGER {
                         unknown(1),
                         external(2),
                         line(3),
                         through(4),
                         loop(5),
                         local(6)
                       }
        MAX-ACCESS     read-only
        STATUS         current
        DESCRIPTION    "."
        DEFVAL         { unknown }
        ::= { tnSdhPortInfoEntry 3 }

--    obsolete
--    tnSdhPortRxSynchStatusMessage OBJECT-TYPE ::= { tnSdhPortInfoEntry 4 }

    tnSdhPortRxSectionTraceValid OBJECT-TYPE
        SYNTAX         TruthValue
        MAX-ACCESS     read-only
        STATUS         current
        DESCRIPTION    "."
        DEFVAL         { false }
        ::= { tnSdhPortInfoEntry 5 }

    tnSdhPortTxSynchronizeStatusMessage OBJECT-TYPE
        SYNTAX         TropicSdhS1
        MAX-ACCESS     read-only
        STATUS         current
        DESCRIPTION    "Current range: 0 to 15."
        DEFVAL         { unknown }
        ::= { tnSdhPortInfoEntry 6 }

    tnSdhPortRxSynchronizeStatusMessage OBJECT-TYPE
        SYNTAX         TropicSdhS1
        MAX-ACCESS     read-only
        STATUS         current
        DESCRIPTION    "Current range:  0 to 255."
        DEFVAL         { unknown }
        ::= { tnSdhPortInfoEntry 7 }

--    obsolete
--    tnOC48STM16PortInfoAttributeTotal             OBJECT-TYPE ::= { tnOpticalPortInfo 3 }
--    tnOC48STM16PortInfoTable                      OBJECT-TYPE ::= { tnOpticalPortInfo 4 }
--    tnOC192STM64PortInfoAttributeTotal            OBJECT-TYPE ::= { tnOpticalPortInfo 5 }
--    tnOC192STM64PortInfoTable                     OBJECT-TYPE ::= { tnOpticalPortInfo 6 }
--    tnQuadOC48STM16MuxPortInfoAttributeTotal      OBJECT-TYPE ::= { tnOpticalPortInfo 7 }
--    tnQuadOC48STM16MuxPortInfoTable               OBJECT-TYPE ::= { tnOpticalPortInfo 8 }
--    tnQuadOC3or12STM1or4MuxPortInfoAttributeTotal OBJECT-TYPE ::= { tnOpticalPortInfo 9 }
--    tnQuadOC3or12STM1or4MuxPortInfoTable          OBJECT-TYPE ::= { tnOpticalPortInfo 10 }
--    tnBandFilterPortInfoAttributeTotal            OBJECT-TYPE ::= { tnOpticalPortInfo 11 }
--    tnBandFilterPortInfoTable                     OBJECT-TYPE ::= { tnOpticalPortInfo 12 }

--------------------------------------------------------------------------------
-- OSC Optical Port Info Scalar
--------------------------------------------------------------------------------
    tnOscPortInfoAttributeTotal OBJECT-TYPE
        SYNTAX         Integer32
        MAX-ACCESS     read-only
        STATUS         current
        DESCRIPTION    "."
        ::= { tnOpticalPortInfo 13 }

--------------------------------------------------------------------------------
-- OSC Optical Port Info Table
--------------------------------------------------------------------------------
    tnOscPortInfoTable OBJECT-TYPE
        SYNTAX         SEQUENCE OF TnOscPortInfoEntry
        MAX-ACCESS     not-accessible
        STATUS         current
        DESCRIPTION    "The ports on an OSC optical card."
        ::= { tnOpticalPortInfo 14 }

    tnOscPortInfoEntry OBJECT-TYPE
        SYNTAX         TnOscPortInfoEntry
        MAX-ACCESS     not-accessible
        STATUS         current
        DESCRIPTION    "."
        INDEX { ifIndex }
        ::= { tnOscPortInfoTable 1 }

    TnOscPortInfoEntry ::=
        SEQUENCE {
            tnOscPortInfoFunction         INTEGER,
            tnOscPortTotalNwPowerIn       Integer32,
            tnOscPortTotalNwPowerOut      Integer32,
            tnOscPortPhyDeviceLinkStatus  INTEGER,
            tnOscPortPhyDeviceIdNo        Unsigned32,
            tnOscPortPhyDeviceMfgModelNo  Unsigned32,
            tnOscPortPhyDeviceMfgRevNo    Unsigned32
        }

    tnOscPortInfoFunction OBJECT-TYPE
        SYNTAX         INTEGER {
                         signal(1),
                         line(2),
                         inv(3),
                         osc(4),
                         oscSfp(5)
                       }
        MAX-ACCESS     read-only
        STATUS         current
        DESCRIPTION    "Indicates the functional type of this OSC port."
        ::= { tnOscPortInfoEntry 1 }

    tnOscPortTotalNwPowerIn OBJECT-TYPE
        SYNTAX         Integer32
        UNITS          "mBm"
        MAX-ACCESS     read-only
        STATUS         current
        DESCRIPTION    "The following description applies to the wdm
                        port of the OSC card:

                        The total ingress power of the optical signal."
        DEFVAL         { -9900 }
        ::= { tnOscPortInfoEntry 2 }

    tnOscPortTotalNwPowerOut OBJECT-TYPE
        SYNTAX         Integer32
        UNITS          "mBm"
        MAX-ACCESS     read-only
        STATUS         current
        DESCRIPTION    "The following description applies to the wdm
                        port of the OSC card:

                        The total egress power of the optical signal."
        ::= { tnOscPortInfoEntry 3 }

    tnOscPortPhyDeviceLinkStatus OBJECT-TYPE
        SYNTAX         INTEGER {
                         up(1),
                         down(2)
                       }
        MAX-ACCESS     read-only
        STATUS         current
        DESCRIPTION    "The following description applies to the wdm
                        port of the OSC card:

                        PHY chip link status."
        ::= { tnOscPortInfoEntry 4 }

    tnOscPortPhyDeviceIdNo OBJECT-TYPE
        SYNTAX         Unsigned32
        MAX-ACCESS     read-only
        STATUS         current
        DESCRIPTION    "The following description applies to the wdm
                        port of the OSC card:

                        PHY chip ID."
        ::= { tnOscPortInfoEntry 5 }

    tnOscPortPhyDeviceMfgModelNo OBJECT-TYPE
        SYNTAX         Unsigned32
        MAX-ACCESS     read-only
        STATUS         current
        DESCRIPTION    "The following description applies to the wdm
                        port of the OSC card:

                        PHY chip manufacturing model number."
        ::= { tnOscPortInfoEntry 6 }

    tnOscPortPhyDeviceMfgRevNo OBJECT-TYPE
        SYNTAX         Unsigned32
        MAX-ACCESS     read-only
        STATUS         current
        DESCRIPTION    "The following description applies to the wdm
                        port of the OSC card:

                        PHY chip manufacturing revision number."
        ::= { tnOscPortInfoEntry 7 }

--    obsolete
--    tnChFilterPortInfoAttributeTotal    OBJECT-TYPE ::= { tnOpticalPortInfo 15 }
--    tnChFilterPortInfoTable             OBJECT-TYPE ::= { tnOpticalPortInfo 16 }
--    tnChAddDropPortInfoAttributeTotal   OBJECT-TYPE ::= { tnOpticalPortInfo 17 }
--    tnChAddDropPortInfoTable            OBJECT-TYPE ::= { tnOpticalPortInfo 18 }
--    tnBbaHgPortInfoAttributeTotal       OBJECT-TYPE ::= { tnOpticalPortInfo 19 }
--    tnBbaHgPortInfoTable                OBJECT-TYPE ::= { tnOpticalPortInfo 20 }
--    tnBbaLgPortInfoAttributeTotal       OBJECT-TYPE ::= { tnOpticalPortInfo 21 }
--    tnBbaLgPortInfoTable                OBJECT-TYPE ::= { tnOpticalPortInfo 22 }
--    tnPpsPortInfoAttributeTotal         OBJECT-TYPE ::= { tnOpticalPortInfo 23 }
--    tnPpsPortInfoTable                  OBJECT-TYPE ::= { tnOpticalPortInfo 24 }
--    tnDualGigEMuxPortInfoAttributeTotal OBJECT-TYPE ::= { tnOpticalPortInfo 25 }
--    tnDualGigEMuxPortInfoTable          OBJECT-TYPE ::= { tnOpticalPortInfo 26 }
--    tnRoadmPortInfoAttributeTotal       OBJECT-TYPE ::= { tnOpticalPortInfo 27 }
--    tnRoadmPortInfoTable                OBJECT-TYPE ::= { tnOpticalPortInfo 28 }
--    tn10GigELANPortInfoAttributeTotal   OBJECT-TYPE ::= { tnOpticalPortInfo 29 }
--    tn10GigELANPortInfoTable            OBJECT-TYPE ::= { tnOpticalPortInfo 30 }

--------------------------------------------------------------------------------
-- Dispersion Compensation Module Optical Port Info Scalar
--------------------------------------------------------------------------------
    tnDcmPortInfoAttributeTotal OBJECT-TYPE
        SYNTAX         Integer32
        MAX-ACCESS     read-only
        STATUS         current
        DESCRIPTION    "."
        ::= { tnOpticalPortInfo 31 }

--------------------------------------------------------------------------------
-- Dispersion Compensation Module Optical Port Info Table
--------------------------------------------------------------------------------
    tnDcmPortInfoTable OBJECT-TYPE
        SYNTAX         SEQUENCE OF TnDcmPortInfoEntry
        MAX-ACCESS     not-accessible
        STATUS         current
        DESCRIPTION    "The ports on a DCM optical card."
        ::= { tnOpticalPortInfo 32 }

    tnDcmPortInfoEntry OBJECT-TYPE
        SYNTAX         TnDcmPortInfoEntry
        MAX-ACCESS     not-accessible
        STATUS         current
        DESCRIPTION    "."
        INDEX { ifIndex }
        ::= { tnDcmPortInfoTable 1 }

    TnDcmPortInfoEntry ::=
        SEQUENCE {
            tnDcmPortInfoFunction           INTEGER,
            tnDcmPortInfoIroadmConnAddress  InterfaceIndexOrZero
        }

    tnDcmPortInfoFunction OBJECT-TYPE
        SYNTAX         INTEGER {
                         dcmOutThruIn(1),
                         thruOutDcmIn(2),
                         dcmInOut(3)
                       }
        MAX-ACCESS     read-only
        STATUS         current
        DESCRIPTION    "Indicates the functional type of this Dispersion
                        Compensation Module port."
        ::= { tnDcmPortInfoEntry 1 }

    tnDcmPortInfoIroadmConnAddress OBJECT-TYPE
        SYNTAX         InterfaceIndexOrZero
        MAX-ACCESS     read-only
        STATUS         current
        DESCRIPTION    "."
        ::= { tnDcmPortInfoEntry 2 }

--    obsolete
--    tnDecaGigEMuxPortInfoAttributeTotal OBJECT-TYPE ::= { tnOpticalPortInfo 33 }
--    tnDecaGigEMuxPortInfoTable          OBJECT-TYPE ::= { tnOpticalPortInfo 34 }

--------------------------------------------------------------------------------
-- SONET Optical Port Info Scalar
--------------------------------------------------------------------------------
    tnSonetPortInfoAttributeTotal OBJECT-TYPE
        SYNTAX         Integer32
        MAX-ACCESS     read-only
        STATUS         current
        DESCRIPTION    "."
        ::= { tnOpticalPortInfo 35 }

--------------------------------------------------------------------------------
-- SONET Optical Port Info Table
--------------------------------------------------------------------------------
    tnSonetPortInfoTable OBJECT-TYPE
        SYNTAX         SEQUENCE OF TnSonetPortInfoEntry
        MAX-ACCESS     not-accessible
        STATUS         current
        DESCRIPTION    "The ports on SONET supported cards."
        ::= { tnOpticalPortInfo 36 }

    tnSonetPortInfoEntry OBJECT-TYPE
        SYNTAX         TnSonetPortInfoEntry
        MAX-ACCESS     not-accessible
        STATUS         current
        DESCRIPTION    "."
        INDEX { ifIndex }
        ::= { tnSonetPortInfoTable 1 }

    TnSonetPortInfoEntry ::=
        SEQUENCE {
            tnSonetPortRxSectionTrace       SnmpAdminString,
            tnSonetPortTxSynchStatusMessage TropicSonetS1,
            tnSonetPortTiming               INTEGER,
            tnSonetPortRxSynchStatusMessage TropicSonetS1,
            tnSonetPortRxSectionTraceValid  TruthValue
        }

    tnSonetPortRxSectionTrace OBJECT-TYPE
        SYNTAX         SnmpAdminString (SIZE(0..255))
        MAX-ACCESS     read-only
        STATUS         current
        DESCRIPTION    "."
        ::= { tnSonetPortInfoEntry 1 }

    tnSonetPortTxSynchStatusMessage OBJECT-TYPE
        SYNTAX         TropicSonetS1
        MAX-ACCESS     read-only
        STATUS         current
        DESCRIPTION    "."
        ::= { tnSonetPortInfoEntry 2 }

    tnSonetPortTiming OBJECT-TYPE
        SYNTAX         INTEGER {
                         unknown(1),
                         external(2),
                         line(3),
                         through(4),
                         loop(5),
                         local(6)
                       }
        MAX-ACCESS     read-only
        STATUS         current
        DESCRIPTION    "."
        ::= { tnSonetPortInfoEntry 3 }

    tnSonetPortRxSynchStatusMessage OBJECT-TYPE
        SYNTAX         TropicSonetS1
        MAX-ACCESS     read-only
        STATUS         current
        DESCRIPTION    "."
        ::= { tnSonetPortInfoEntry 4 }

    tnSonetPortRxSectionTraceValid OBJECT-TYPE
        SYNTAX         TruthValue
        MAX-ACCESS     read-only
        STATUS         current
        DESCRIPTION    "."
        ::= { tnSonetPortInfoEntry 5 }

--    obsolete
--    tnExternalDcuPortInfoAttributeTotal OBJECT-TYPE ::= { tnOpticalPortInfo 37 }
--    tnExternalDcuPortInfoTable          OBJECT-TYPE ::= { tnOpticalPortInfo 38 }

--------------------------------------------------------------------------------
-- Digital Wrapper Optical Port Info Scalar
--------------------------------------------------------------------------------
    tnDigitalWrapperPortInfoAttributeTotal OBJECT-TYPE
        SYNTAX         Integer32
        MAX-ACCESS     read-only
        STATUS         current
        DESCRIPTION    "."
        ::= { tnOpticalPortInfo 39 }

--------------------------------------------------------------------------------
-- Digital Wrapper Optical Port Info Table
--------------------------------------------------------------------------------
    tnDigitalWrapperPortInfoTable OBJECT-TYPE
        SYNTAX         SEQUENCE OF TnDigitalWrapperPortInfoEntry
        MAX-ACCESS     not-accessible
        STATUS         current
        DESCRIPTION    "The ports on Digital Wrapper supported cards."
        ::= { tnOpticalPortInfo 40 }

    tnDigitalWrapperPortInfoEntry OBJECT-TYPE
        SYNTAX         TnDigitalWrapperPortInfoEntry
        MAX-ACCESS     not-accessible
        STATUS         current
        DESCRIPTION    "."
        INDEX { ifIndex }
        ::= { tnDigitalWrapperPortInfoTable 1 }

    TnDigitalWrapperPortInfoEntry ::=
        SEQUENCE {
            tnDwPortRxPMTTI                SnmpAdminString,
            tnDwPortRxPMExpectedTTI        SnmpAdminString,
            tnDwPortTxPMTTI                SnmpAdminString
        }

    tnDwPortRxPMTTI OBJECT-TYPE
        SYNTAX         SnmpAdminString (SIZE(0..255))
        MAX-ACCESS     read-only
        STATUS         current
        DESCRIPTION    "."
        ::= { tnDigitalWrapperPortInfoEntry 1 }

    tnDwPortRxPMExpectedTTI OBJECT-TYPE
        SYNTAX         SnmpAdminString (SIZE(0..255))
        MAX-ACCESS     read-only
        STATUS         current
        DESCRIPTION    "."
        ::= { tnDigitalWrapperPortInfoEntry 2 }

    tnDwPortTxPMTTI OBJECT-TYPE
        SYNTAX         SnmpAdminString (SIZE(0..255))
        MAX-ACCESS     read-only
        STATUS         current
        DESCRIPTION    "."
        ::= { tnDigitalWrapperPortInfoEntry 3 }

--    obsolete
--    tnMsaHgPortInfoAttributeTotal OBJECT-TYPE ::= { tnOpticalPortInfo 41 }
--    tnMsaHgPortInfoTable          OBJECT-TYPE ::= { tnOpticalPortInfo 42 }
--    tnWssX9PortInfoAttributeTotal OBJECT-TYPE ::= { tnOpticalPortInfo 43 }
--    tnWssX9PortInfoTable          OBJECT-TYPE ::= { tnOpticalPortInfo 44 }

--------------------------------------------------------------------------------
-- SFP Port Info Scalar
--------------------------------------------------------------------------------
    tnSfpPortInfoAttributeTotal OBJECT-TYPE
        SYNTAX         Integer32
        MAX-ACCESS     read-only
        STATUS         current
        DESCRIPTION    "."
        ::= { tnOpticalPortInfo 45 }

--------------------------------------------------------------------------------
-- SFP Port Info Table
--------------------------------------------------------------------------------
    tnSfpPortInfoTable OBJECT-TYPE
        SYNTAX         SEQUENCE OF TnSfpPortInfoEntry
        MAX-ACCESS     not-accessible
        STATUS         current
        DESCRIPTION    "The SFP supported ports."
        ::= { tnOpticalPortInfo 46 }

    tnSfpPortInfoEntry OBJECT-TYPE
        SYNTAX         TnSfpPortInfoEntry
        MAX-ACCESS     not-accessible
        STATUS         current
        DESCRIPTION    "."
        INDEX { ifIndex }
        ::= { tnSfpPortInfoTable 1 }

    TnSfpPortInfoEntry ::=
        SEQUENCE {
            tnSfpPortModulePresentType             Unsigned32,
            tnSfpPortModuleVendorSerNo             SnmpAdminString,
            tnSfpPortModuleState                   TnSfpModuleState,
            tnSfpPortModuleVendor                  SnmpAdminString,
            tnSfpPortTxDisable                     TruthValue,
            tnSfpPortWavelength                    Unsigned32,
            tnSfpPortModuleType                    SnmpAdminString,
            tnSfpPortCLEI                          SnmpAdminString,
            tnSfpPortUnitPartNum                   SnmpAdminString,
            tnSfpPortSWPartNum                     SnmpAdminString,
            tnSfpPortFactoryID                     SnmpAdminString,
            tnSfpPortDate                          SnmpAdminString,
            tnSfpPortExtraData                     SnmpAdminString,
            tnSfpPortMaximumCaseTemperature        Integer32,
            tnSfpPortInterchangeabilityMarking     SnmpAdminString,
            tnSfpPortAcronymCode                   SnmpAdminString,
            tnSfpPortPowerClass                    SnmpAdminString,
            tnSfpPortFirmwareVersion               SnmpAdminString,
            tnSfpPortMaximumPowerConsumption       Integer32
        }

    tnSfpPortModulePresentType OBJECT-TYPE
        SYNTAX         Unsigned32
        MAX-ACCESS     read-only
        STATUS         current
        DESCRIPTION    "XFP/SFP module present type."
        ::= { tnSfpPortInfoEntry 1 }

    tnSfpPortModuleVendorSerNo OBJECT-TYPE
        SYNTAX         SnmpAdminString (SIZE(0..18))
        MAX-ACCESS     read-only
        STATUS         current
        DESCRIPTION    "XFP/SFP module vendor serial number."
        ::= { tnSfpPortInfoEntry 2 }

    tnSfpPortModuleState OBJECT-TYPE
        SYNTAX         TnSfpModuleState
        MAX-ACCESS     read-only
        STATUS         current
        DESCRIPTION    "XFP/SFP module state."
        ::= { tnSfpPortInfoEntry 3 }

    tnSfpPortModuleVendor OBJECT-TYPE
        SYNTAX         SnmpAdminString (SIZE(0..16))
        MAX-ACCESS     read-only
        STATUS         current
        DESCRIPTION    "XFP/SFP module vendor."
        ::= { tnSfpPortInfoEntry 4 }

    tnSfpPortTxDisable OBJECT-TYPE
        SYNTAX         TruthValue
        MAX-ACCESS     read-only
        STATUS         current
        DESCRIPTION    "XFP/SFP TX disable."
        ::= { tnSfpPortInfoEntry 5 }

    tnSfpPortWavelength OBJECT-TYPE
        SYNTAX         Unsigned32
        MAX-ACCESS     read-only
        STATUS         current
        DESCRIPTION    "XFP/SFP wavelength."
        ::= { tnSfpPortInfoEntry 6 }

    tnSfpPortModuleType OBJECT-TYPE
        SYNTAX         SnmpAdminString
        MAX-ACCESS     read-only
        STATUS         current
        DESCRIPTION    "XFP/SFP module type."
        ::= { tnSfpPortInfoEntry 7 }

    tnSfpPortCLEI OBJECT-TYPE
        SYNTAX         SnmpAdminString
        MAX-ACCESS     read-only
        STATUS         current
        DESCRIPTION    "XFP/SFP CLEI."
        ::= { tnSfpPortInfoEntry 8 }

    tnSfpPortUnitPartNum OBJECT-TYPE
        SYNTAX         SnmpAdminString
        MAX-ACCESS     read-only
        STATUS         current
        DESCRIPTION    "XFP/SFP unit part number."
        ::= { tnSfpPortInfoEntry 9 }

    tnSfpPortSWPartNum OBJECT-TYPE
        SYNTAX         SnmpAdminString
        MAX-ACCESS     read-only
        STATUS         current
        DESCRIPTION    "XFP/SFP software part number."
        ::= { tnSfpPortInfoEntry 10 }

    tnSfpPortFactoryID OBJECT-TYPE
        SYNTAX         SnmpAdminString
        MAX-ACCESS     read-only
        STATUS         current
        DESCRIPTION    "XFP/SFP factory ID."
        ::= { tnSfpPortInfoEntry 11 }

    tnSfpPortDate OBJECT-TYPE
        SYNTAX         SnmpAdminString
        MAX-ACCESS     read-only
        STATUS         current
        DESCRIPTION    "XFP/SFP date."
        ::= { tnSfpPortInfoEntry 12 }

    tnSfpPortExtraData OBJECT-TYPE
        SYNTAX         SnmpAdminString
        MAX-ACCESS     read-only
        STATUS         current
        DESCRIPTION    "XFP/SFP extra data."
        ::= { tnSfpPortInfoEntry 13 }

    tnSfpPortMaximumCaseTemperature OBJECT-TYPE
        SYNTAX         Integer32
        MAX-ACCESS     read-only
        STATUS         current
        DESCRIPTION    "XFP/SFP maximum case temperature."
        ::= { tnSfpPortInfoEntry 14 }

    tnSfpPortInterchangeabilityMarking OBJECT-TYPE
        SYNTAX         SnmpAdminString (SIZE(0..6))
        MAX-ACCESS     read-only
        STATUS         current
        DESCRIPTION    "XFP/SFP interchangeability marking."
        ::= { tnSfpPortInfoEntry 15 }

    tnSfpPortAcronymCode OBJECT-TYPE
        SYNTAX         SnmpAdminString (SIZE(0..12))
        MAX-ACCESS     read-only
        STATUS         current
        DESCRIPTION    "XFP/SFP acronym code."
        ::= { tnSfpPortInfoEntry 16 }

    tnSfpPortPowerClass OBJECT-TYPE
        SYNTAX         SnmpAdminString (SIZE(0..7))
        MAX-ACCESS     read-only
        STATUS         current
        DESCRIPTION    "Sfp Power class."
        ::= { tnSfpPortInfoEntry 17 }

    tnSfpPortFirmwareVersion OBJECT-TYPE
        SYNTAX         SnmpAdminString (SIZE(0..4))
        MAX-ACCESS     read-only
        STATUS         current
        DESCRIPTION    "Sfp Firmware version."
        ::= { tnSfpPortInfoEntry 18 }

    tnSfpPortMaximumPowerConsumption OBJECT-TYPE
        SYNTAX         Integer32
        UNITS          "mW"
        MAX-ACCESS     read-only
        STATUS         current
        DESCRIPTION    "module maximum power consumption."
        ::= { tnSfpPortInfoEntry 19 }

--    obsolete
--    tn1xMR2dot5GPortInfoAttributeTotal OBJECT-TYPE ::= { tnOpticalPortInfo 47 }
--    tn1xMR2dot5GPortInfoTable          OBJECT-TYPE ::= { tnOpticalPortInfo 48 }

--------------------------------------------------------------------------------
-- Network Port Info Scalar
--------------------------------------------------------------------------------
    tnNetworkPortInfoAttributeTotal OBJECT-TYPE
        SYNTAX         Integer32
        MAX-ACCESS     read-only
        STATUS         current
        DESCRIPTION    "."
        ::= { tnOpticalPortInfo 49 }

--------------------------------------------------------------------------------
-- Network Port Info Table
--------------------------------------------------------------------------------
    tnNetworkPortInfoTable OBJECT-TYPE
        SYNTAX         SEQUENCE OF TnNetworkPortInfoEntry
        MAX-ACCESS     not-accessible
        STATUS         current
        DESCRIPTION    "The network ports on optical transponder cards."
        ::= { tnOpticalPortInfo 50 }

    tnNetworkPortInfoEntry OBJECT-TYPE
        SYNTAX         TnNetworkPortInfoEntry
        MAX-ACCESS     not-accessible
        STATUS         current
        DESCRIPTION    "."
        INDEX { ifIndex }
        ::= { tnNetworkPortInfoTable 1 }

    TnNetworkPortInfoEntry ::=
        SEQUENCE {
--            obsolete
--            tnNwPortOchRxStatus    TnOchStatus,
--            tnNwPortOchTxStatus    TnOchStatus,
            tnNwPortPresentChannel Unsigned32
        }

--    obsolete
--    tnNwPortOchRxStatus OBJECT-TYPE ::= { tnNetworkPortInfoEntry 1 }
--    tnNwPortOchTxStatus OBJECT-TYPE ::= { tnNetworkPortInfoEntry 2 }

    tnNwPortPresentChannel OBJECT-TYPE
        SYNTAX         Unsigned32
        MAX-ACCESS     read-only
        STATUS         current
        DESCRIPTION    "The present ITU channel."
        ::= { tnNetworkPortInfoEntry 3 }

--------------------------------------------------------------------------------
-- OPSA Optical Port Info Scalar
--------------------------------------------------------------------------------
    tnOpsaPortInfoAttributeTotal OBJECT-TYPE
        SYNTAX         Integer32
        MAX-ACCESS     read-only
        STATUS         current
        DESCRIPTION    "."
        ::= { tnOpticalPortInfo 51 }

--------------------------------------------------------------------------------
-- OPSA Optical Port Info Table
--------------------------------------------------------------------------------
    tnOpsaPortInfoTable OBJECT-TYPE
        SYNTAX         SEQUENCE OF TnOpsaPortInfoEntry
        MAX-ACCESS     not-accessible
        STATUS         current
        DESCRIPTION    "The ports on an OPSA optical card."
        ::= { tnOpticalPortInfo 52 }

    tnOpsaPortInfoEntry OBJECT-TYPE
        SYNTAX         TnOpsaPortInfoEntry
        MAX-ACCESS     not-accessible
        STATUS         current
        DESCRIPTION    "."
        INDEX { ifIndex }
        ::= { tnOpsaPortInfoTable 1 }

    TnOpsaPortInfoEntry ::=
        SEQUENCE {
            tnOpsaPortInfoFunction               INTEGER,
            tnOpsaPortReceivedPower              Integer32,  -- deprecated
            tnOpsaPortPresentTransmitAttenuation Integer32   -- deprecated
        }

    tnOpsaPortInfoFunction OBJECT-TYPE
        SYNTAX         INTEGER {
                         signal(1),
                         workingProtected(2)
                       }
        MAX-ACCESS     read-only
        STATUS         current
        DESCRIPTION    "Indicates the functional type of this OPSA port."
        ::= { tnOpsaPortInfoEntry 1 }

    tnOpsaPortReceivedPower OBJECT-TYPE
        SYNTAX         Integer32
        UNITS          "mBm"
        MAX-ACCESS     read-only
        STATUS         deprecated
        DESCRIPTION    "The received power in mBm.  This is accessible
                        from ports 2 and 3 (working or protected)
                        exclusively."
        ::= { tnOpsaPortInfoEntry 2 }

    tnOpsaPortPresentTransmitAttenuation OBJECT-TYPE
        SYNTAX         Integer32
        UNITS          "mB"
        MAX-ACCESS     read-only
        STATUS         deprecated
        DESCRIPTION    "The present attenuation of the attenuator -
                        applies to the network ports of the OPSA card
                        with attenuators."
        ::= { tnOpsaPortInfoEntry 3 }

--------------------------------------------------------------------------------
-- 11STMM10 Optical Port Info Scalar
--------------------------------------------------------------------------------
    tn11stmm10PortInfoAttributeTotal OBJECT-TYPE
        SYNTAX         Integer32
        MAX-ACCESS     read-only
        STATUS         current
        DESCRIPTION    "."
        ::= { tnOpticalPortInfo 53 }

--------------------------------------------------------------------------------
-- 11STMM10 Optical Port Info Table
--------------------------------------------------------------------------------
    tn11stmm10PortInfoTable OBJECT-TYPE
        SYNTAX         SEQUENCE OF Tn11stmm10PortInfoEntry
        MAX-ACCESS     not-accessible
        STATUS         current
        DESCRIPTION    "The ports on a 11STMM10 optical card."
        ::= { tnOpticalPortInfo 54 }

    tn11stmm10PortInfoEntry OBJECT-TYPE
        SYNTAX         Tn11stmm10PortInfoEntry
        MAX-ACCESS     not-accessible
        STATUS         current
        DESCRIPTION    "."
        INDEX { ifIndex }
        ::= { tn11stmm10PortInfoTable 1 }

    Tn11stmm10PortInfoEntry ::=
        SEQUENCE {
            tn11stmm10PortInfoFunction INTEGER
        }

    tn11stmm10PortInfoFunction OBJECT-TYPE
        SYNTAX         INTEGER {
                         network(1),
                         client(2)
                       }
        MAX-ACCESS     read-only
        STATUS         current
        DESCRIPTION    "Indicates the functional type of this 11STMM10 port."
        ::= { tn11stmm10PortInfoEntry 1 }

--------------------------------------------------------------------------------
-- 11STAR1 Optical Port Info Scalar
--------------------------------------------------------------------------------
    tn11star1PortInfoAttributeTotal OBJECT-TYPE
        SYNTAX         Integer32
        MAX-ACCESS     read-only
        STATUS         current
        DESCRIPTION    "."
        ::= { tnOpticalPortInfo 55 }

--------------------------------------------------------------------------------
-- 11STAR1 Optical Port Info Table
--------------------------------------------------------------------------------
    tn11star1PortInfoTable OBJECT-TYPE
        SYNTAX         SEQUENCE OF Tn11star1PortInfoEntry
        MAX-ACCESS     not-accessible
        STATUS         current
        DESCRIPTION    "The ports on a 11STAR1 optical card."
        ::= { tnOpticalPortInfo 56 }

    tn11star1PortInfoEntry OBJECT-TYPE
        SYNTAX         Tn11star1PortInfoEntry
        MAX-ACCESS     not-accessible
        STATUS         current
        DESCRIPTION    "."
        INDEX { ifIndex }
        ::= { tn11star1PortInfoTable 1 }

    Tn11star1PortInfoEntry ::=
        SEQUENCE {
            tn11star1PortInfoFunction INTEGER
        }

    tn11star1PortInfoFunction OBJECT-TYPE
        SYNTAX         INTEGER {
                         network(1),
                         client(2)
                       }
        MAX-ACCESS     read-only
        STATUS         current
        DESCRIPTION    "Indicates the functional type of this 11STAR1 port."
        ::= { tn11star1PortInfoEntry 1 }

--------------------------------------------------------------------------------
-- AHPHG Optical Port Info Scalar
--------------------------------------------------------------------------------
    tnAhphgPortInfoAttributeTotal OBJECT-TYPE
        SYNTAX         Integer32
        MAX-ACCESS     read-only
        STATUS         current
        DESCRIPTION    "."
        ::= { tnOpticalPortInfo 57 }

--------------------------------------------------------------------------------
-- AHPHG Optical Port Info Table
--------------------------------------------------------------------------------
    tnAhphgPortInfoTable OBJECT-TYPE
        SYNTAX         SEQUENCE OF TnAhphgPortInfoEntry
        MAX-ACCESS     not-accessible
        STATUS         current
        DESCRIPTION    "The ports on an AHPHG optical card."
        ::= { tnOpticalPortInfo 58 }

    tnAhphgPortInfoEntry OBJECT-TYPE
        SYNTAX         TnAhphgPortInfoEntry
        MAX-ACCESS     not-accessible
        STATUS         current
        DESCRIPTION    "."
        INDEX { ifIndex }
        ::= { tnAhphgPortInfoTable 1 }

    TnAhphgPortInfoEntry ::=
        SEQUENCE {
            tnAhphgPortInfoFunction INTEGER
        }

    tnAhphgPortInfoFunction OBJECT-TYPE
        SYNTAX         INTEGER {
                         line(1),
                         signal(2),
                         dcm(3),
                         inv(4),
                         osc(5),
                         custLan(6)
                       }
        MAX-ACCESS     read-only
        STATUS         current
        DESCRIPTION    "Indicates the functional type of this AHPHG port."
        ::= { tnAhphgPortInfoEntry 1 }

--------------------------------------------------------------------------------
-- ALPHG Optical Port Info Scalar
--------------------------------------------------------------------------------
    tnAlphgPortInfoAttributeTotal OBJECT-TYPE
        SYNTAX         Integer32
        MAX-ACCESS     read-only
        STATUS         current
        DESCRIPTION    "."
        ::= { tnOpticalPortInfo 59 }

--------------------------------------------------------------------------------
-- ALPHG Optical Port Info Table
--------------------------------------------------------------------------------
    tnAlphgPortInfoTable OBJECT-TYPE
        SYNTAX         SEQUENCE OF TnAlphgPortInfoEntry
        MAX-ACCESS     not-accessible
        STATUS         current
        DESCRIPTION    "The ports on an ALPHG optical card."
        ::= { tnOpticalPortInfo 60 }

    tnAlphgPortInfoEntry OBJECT-TYPE
        SYNTAX         TnAlphgPortInfoEntry
        MAX-ACCESS     not-accessible
        STATUS         current
        DESCRIPTION    "."
        INDEX { ifIndex }
        ::= { tnAlphgPortInfoTable 1 }

    TnAlphgPortInfoEntry ::=
        SEQUENCE {
            tnAlphgPortInfoFunction INTEGER
        }

    tnAlphgPortInfoFunction OBJECT-TYPE
        SYNTAX         INTEGER {
                         line(1),
                         signal(2),
                         dcm(3),
                         inv(4),
                         osc(5),
                         custLan(6)
                       }
        MAX-ACCESS     read-only
        STATUS         current
        DESCRIPTION    "Indicates the functional type of this ALPHG port."
        ::= { tnAlphgPortInfoEntry 1 }

--------------------------------------------------------------------------------
-- CWR8 Optical Port Info Scalar
--------------------------------------------------------------------------------
    tnCwr8PortInfoAttributeTotal OBJECT-TYPE
        SYNTAX         Integer32
        MAX-ACCESS     read-only
        STATUS         current
        DESCRIPTION    "."
        ::= { tnOpticalPortInfo 61 }

--------------------------------------------------------------------------------
-- CWR8 Optical Port Info Table
--------------------------------------------------------------------------------
    tnCwr8PortInfoTable OBJECT-TYPE
        SYNTAX         SEQUENCE OF TnCwr8PortInfoEntry
        MAX-ACCESS     not-accessible
        STATUS         current
        DESCRIPTION    "The ports on a CWR8 optical card."
        ::= { tnOpticalPortInfo 62 }

    tnCwr8PortInfoEntry OBJECT-TYPE
        SYNTAX         TnCwr8PortInfoEntry
        MAX-ACCESS     not-accessible
        STATUS         current
        DESCRIPTION    "."
        INDEX { ifIndex }
        ::= { tnCwr8PortInfoTable 1 }

    TnCwr8PortInfoEntry ::=
        SEQUENCE {
            tnCwr8PortInfoFunction           INTEGER,
--            obsolete
--            tnCwr8PortTotalNwPowerIn         Integer32,
--            tnCwr8PortTotalNwPowerOut        Integer32,
            tnCwr8PortRelativeAttenuationMin Unsigned32,
            tnCwr8PortAverageAttenuationOut  Unsigned32
        }

    tnCwr8PortInfoFunction OBJECT-TYPE
        SYNTAX         INTEGER {
                         signal(1),
                         test(2),
                         thru(3),
                         colorless(4),
                         omd(5),
                         inv(6)
                       }
        MAX-ACCESS     read-only
        STATUS         current
        DESCRIPTION    "Indicates the functional type of this CWR8 port."
        ::= { tnCwr8PortInfoEntry 1 }

--    obsolete
--    tnCwr8PortTotalNwPowerIn  OBJECT-TYPE ::= { tnCwr8PortInfoEntry 2 }
--    tnCwr8PortTotalNwPowerOut OBJECT-TYPE ::= { tnCwr8PortInfoEntry 3 }

    tnCwr8PortRelativeAttenuationMin OBJECT-TYPE
        SYNTAX         Unsigned32
        UNITS          "mB"
        MAX-ACCESS     read-only
        STATUS         current
        DESCRIPTION    "The following description applies to the Thru
                        port of the CWR8 card:

                        The minimum attenuation on the blocker across
                        all of the channels."
        ::= { tnCwr8PortInfoEntry 4 }

    tnCwr8PortAverageAttenuationOut OBJECT-TYPE
        SYNTAX         Unsigned32
        UNITS          "mB"
        MAX-ACCESS     read-only
        STATUS         current
        DESCRIPTION    "The following description applies to the Thru
                        port of the CWR8 card:

                        The average attenuation on the blocker across
                        all of the channels."
        ::= { tnCwr8PortInfoEntry 5 }

--------------------------------------------------------------------------------
-- 11STGE12 Optical Port Info Scalar
--------------------------------------------------------------------------------
    tn11stge12PortInfoAttributeTotal OBJECT-TYPE
        SYNTAX         Integer32
        MAX-ACCESS     read-only
        STATUS         current
        DESCRIPTION    "."
        ::= { tnOpticalPortInfo 63 }

--------------------------------------------------------------------------------
-- 11STGE12 Optical Port Info Table
--------------------------------------------------------------------------------
    tn11stge12PortInfoTable OBJECT-TYPE
        SYNTAX         SEQUENCE OF Tn11stge12PortInfoEntry
        MAX-ACCESS     not-accessible
        STATUS         current
        DESCRIPTION    "The ports on a 11STGE12 optical card."
        ::= { tnOpticalPortInfo 64 }

    tn11stge12PortInfoEntry OBJECT-TYPE
        SYNTAX         Tn11stge12PortInfoEntry
        MAX-ACCESS     not-accessible
        STATUS         current
        DESCRIPTION    "."
        INDEX { ifIndex }
        ::= { tn11stge12PortInfoTable 1 }

    Tn11stge12PortInfoEntry ::=
        SEQUENCE {
            tn11stge12PortInfoFunction INTEGER
        }

    tn11stge12PortInfoFunction OBJECT-TYPE
        SYNTAX         INTEGER {
                         network(1),
                         client(2)
                       }
        MAX-ACCESS     read-only
        STATUS         current
        DESCRIPTION    "Indicates the functional type of this 11STGE12 port."
        ::= { tn11stge12PortInfoEntry 1 }

--------------------------------------------------------------------------------
-- 11DPGE12 Optical Port Info Scalar
--------------------------------------------------------------------------------
    tn11dpge12PortInfoAttributeTotal OBJECT-TYPE
        SYNTAX         Integer32
        MAX-ACCESS     read-only
        STATUS         current
        DESCRIPTION    "."
        ::= { tnOpticalPortInfo 65 }

--------------------------------------------------------------------------------
-- 11DPGE12 Optical Port Info Table
--------------------------------------------------------------------------------
    tn11dpge12PortInfoTable OBJECT-TYPE
        SYNTAX         SEQUENCE OF Tn11dpge12PortInfoEntry
        MAX-ACCESS     not-accessible
        STATUS         current
        DESCRIPTION    "The ports on a 11DPGE12 optical card."
        ::= { tnOpticalPortInfo 66 }

    tn11dpge12PortInfoEntry OBJECT-TYPE
        SYNTAX         Tn11dpge12PortInfoEntry
        MAX-ACCESS     not-accessible
        STATUS         current
        DESCRIPTION    "."
        INDEX { ifIndex }
        ::= { tn11dpge12PortInfoTable 1 }

    Tn11dpge12PortInfoEntry ::=
        SEQUENCE {
            tn11dpge12PortInfoFunction           INTEGER,
            tn11dpge12PortAvailableBandwidth     Unsigned32,
            tn11dpge12PortTotalVTS               Unsigned32,
            tn11dpge12PortIngAvailableBandwidth  Unsigned32,
            tn11dpge12PortEgrAvailableBandwidth  Unsigned32
        }

    tn11dpge12PortInfoFunction OBJECT-TYPE
        SYNTAX         INTEGER {
                         network(1),
                         client(2),
                         evoa(3),
                         backplane(4)
                       }
        MAX-ACCESS     read-only
        STATUS         current
        DESCRIPTION    "Indicates the functional type of this 11DPGE12 port."
        ::= { tn11dpge12PortInfoEntry 1 }

    tn11dpge12PortAvailableBandwidth OBJECT-TYPE
        SYNTAX         Unsigned32
        MAX-ACCESS     read-only
        STATUS         current
        DESCRIPTION    "Available bandwidth for 11DPGE12 ports."
        ::= { tn11dpge12PortInfoEntry 2 }

    tn11dpge12PortTotalVTS OBJECT-TYPE
        SYNTAX         Unsigned32
        MAX-ACCESS     read-only
        STATUS         current
        DESCRIPTION    "Total VTS for 11DPGE12 ports."
        ::= { tn11dpge12PortInfoEntry 3 }

    tn11dpge12PortIngAvailableBandwidth OBJECT-TYPE
        SYNTAX         Unsigned32
        MAX-ACCESS     read-only
        STATUS         current
        DESCRIPTION    "Available bandwidth for Ingress 11DPGE12 ports."
        ::= { tn11dpge12PortInfoEntry 4 }

    tn11dpge12PortEgrAvailableBandwidth OBJECT-TYPE
        SYNTAX         Unsigned32
        MAX-ACCESS     read-only
        STATUS         current
        DESCRIPTION    "Available bandwidth for Egress 11DPGE12 ports."
        ::= { tn11dpge12PortInfoEntry 5 }

--    obsolete
--    tnDwdmGpPhyPortInfoTable OBJECT-TYPE ::= { tnOpticalPortInfo 67 }

--------------------------------------------------------------------------------
-- DWDM Common Line Port Info Table
--------------------------------------------------------------------------------
    tnDwdmCmnLinePortInfoTable OBJECT-TYPE
        SYNTAX         SEQUENCE OF TnDwdmCmnLinePortInfoEntry
        MAX-ACCESS     not-accessible
        STATUS         current
        DESCRIPTION    "Common attributes against DWDM line ports."
        ::= { tnOpticalPortInfo 68 }

    tnDwdmCmnLinePortInfoEntry OBJECT-TYPE
        SYNTAX         TnDwdmCmnLinePortInfoEntry
        MAX-ACCESS     not-accessible
        STATUS         current
        DESCRIPTION    "."
        INDEX { ifIndex }
        ::= { tnDwdmCmnLinePortInfoTable 1 }

    TnDwdmCmnLinePortInfoEntry ::=
        SEQUENCE {
            tnDwdmCmnLinePortOtu2IncomingTti                  OCTET STRING,
            tnDwdmCmnLinePortOtu2TtiStatus                    AluWdmTtiStatus,
            tnDwdmCmnLinePortOdu2IncomingTti                  OCTET STRING,
            tnDwdmCmnLinePortOdu2TtiStatus                    AluWdmTtiStatus,
--            obsolete
--            tnDwdmCmnLinePortAvailableBandwidth             Unsigned32,
            tnDwdmCmnLinePortOtu2PreFec                       Counter64,
            tnDwdmCmnLinePortOtu2PostFec                      Counter64,
            tnDwdmCmnLinePortOdu2IncFwFTFLTypeID              OCTET STRING,
            tnDwdmCmnLinePortOdu2IncFwFTFLOperID              OCTET STRING,
            tnDwdmCmnLinePortOdu2IncBwFTFLTypeID              OCTET STRING,
            tnDwdmCmnLinePortOdu2IncBwFTFLOperID              OCTET STRING,
            tnDwdmCmnLinePortOdu2IncResRow2                   OCTET STRING,
            tnDwdmCmnLinePortOdu2IncResRow4                   OCTET STRING,
            tnDwdmCmnLinePortOdu2IncExp                       OCTET STRING,
            tnDwdmCmnLinePortOtu2IncRes                       OCTET STRING,
            tnDwdmCmnLinePortDMInfoCurrentStatus              AluWdmDMInfoCurrentStatus,
            tnDwdmCmnLinePortDMInfoCurrentValue               Unsigned32,
            tnDwdmCmnLinePortOtsigId                          Integer32,
            tnDwdmCmnLinePortOtsigModuleCapabilityFileName    SnmpAdminString,
            tnDwdmCmnLinePortDisruptionTime                   Unsigned32
        }

    tnDwdmCmnLinePortOtu2IncomingTti OBJECT-TYPE
        SYNTAX         OCTET STRING
        MAX-ACCESS     read-only
        STATUS         current
        DESCRIPTION    "OTU2 incoming TTI."
        ::= { tnDwdmCmnLinePortInfoEntry 1 }

    tnDwdmCmnLinePortOtu2TtiStatus OBJECT-TYPE
        SYNTAX         AluWdmTtiStatus
        MAX-ACCESS     read-only
        STATUS         current
        DESCRIPTION    "OTU2 TTI status."
        ::= { tnDwdmCmnLinePortInfoEntry 2 }

    tnDwdmCmnLinePortOdu2IncomingTti OBJECT-TYPE
        SYNTAX         OCTET STRING
        MAX-ACCESS     read-only
        STATUS         current
        DESCRIPTION    "ODU2 incoming TTI."
        ::= { tnDwdmCmnLinePortInfoEntry 3 }

    tnDwdmCmnLinePortOdu2TtiStatus OBJECT-TYPE
        SYNTAX         AluWdmTtiStatus
        MAX-ACCESS     read-only
        STATUS         current
        DESCRIPTION    "ODU2 TTI status."
        ::= { tnDwdmCmnLinePortInfoEntry 4 }

--    obsolete
--    tnDwdmCmnLinePortAvailableBandwidth OBJECT-TYPE ::= { tnDwdmCmnLinePortInfoEntry 5 }

    tnDwdmCmnLinePortOtu2PreFec OBJECT-TYPE
        SYNTAX         Counter64
        MAX-ACCESS     read-only
        STATUS         current
        DESCRIPTION    "Real time error bit rate of pre-FEC (Forward
                        Error Correction)."
        ::= { tnDwdmCmnLinePortInfoEntry 6 }

    tnDwdmCmnLinePortOtu2PostFec OBJECT-TYPE
        SYNTAX         Counter64
        MAX-ACCESS     read-only
        STATUS         current
        DESCRIPTION    "Real time error bit rate of post-FEC (Forward
                        Error Correction)."
        ::= { tnDwdmCmnLinePortInfoEntry 7 }

    tnDwdmCmnLinePortOdu2IncFwFTFLTypeID OBJECT-TYPE
        SYNTAX         OCTET STRING
        MAX-ACCESS     read-only
        STATUS         current
        DESCRIPTION    "ODU2 Incoming Forward FTFL Type ID"
        ::= { tnDwdmCmnLinePortInfoEntry 8 }

    tnDwdmCmnLinePortOdu2IncFwFTFLOperID OBJECT-TYPE
        SYNTAX         OCTET STRING
        MAX-ACCESS     read-only
        STATUS         current
        DESCRIPTION    "ODU2 Incoming Forward FTFL Operator ID."
        ::= { tnDwdmCmnLinePortInfoEntry 9 }

    tnDwdmCmnLinePortOdu2IncBwFTFLTypeID OBJECT-TYPE
        SYNTAX         OCTET STRING
        MAX-ACCESS     read-only
        STATUS         current
        DESCRIPTION    "ODU2 Incoming Backward FTFL Type ID."
        ::= { tnDwdmCmnLinePortInfoEntry 10 }

    tnDwdmCmnLinePortOdu2IncBwFTFLOperID OBJECT-TYPE
        SYNTAX         OCTET STRING
        MAX-ACCESS     read-only
        STATUS         current
        DESCRIPTION    "ODU2 Incoming Backward FTFL Operator ID."
        ::= { tnDwdmCmnLinePortInfoEntry 11 }

    tnDwdmCmnLinePortOdu2IncResRow2 OBJECT-TYPE
        SYNTAX         OCTET STRING
        MAX-ACCESS     read-only
        STATUS         current
        DESCRIPTION    "ODU2 Incoming Res Row2."
        ::= { tnDwdmCmnLinePortInfoEntry 12 }

    tnDwdmCmnLinePortOdu2IncResRow4 OBJECT-TYPE
        SYNTAX         OCTET STRING
        MAX-ACCESS     read-only
        STATUS         current
        DESCRIPTION    "ODU2 Incoming Res Row4."
        ::= { tnDwdmCmnLinePortInfoEntry 13 }

    tnDwdmCmnLinePortOdu2IncExp OBJECT-TYPE
        SYNTAX         OCTET STRING
        MAX-ACCESS     read-only
        STATUS         current
        DESCRIPTION    "ODU2 Incoming Exp."
        ::= { tnDwdmCmnLinePortInfoEntry 14 }

    tnDwdmCmnLinePortOtu2IncRes OBJECT-TYPE
        SYNTAX         OCTET STRING
        MAX-ACCESS     read-only
        STATUS         current
        DESCRIPTION    "OTU2 Incoming Res."
        ::= { tnDwdmCmnLinePortInfoEntry 15 }

    tnDwdmCmnLinePortDMInfoCurrentStatus OBJECT-TYPE
        SYNTAX         AluWdmDMInfoCurrentStatus
        MAX-ACCESS     read-only
        STATUS         current
        DESCRIPTION    "Indicates whether this DM test is valid."
        ::= { tnDwdmCmnLinePortInfoEntry 16 }

    tnDwdmCmnLinePortDMInfoCurrentValue OBJECT-TYPE
        SYNTAX         Unsigned32
        MAX-ACCESS     read-only
        STATUS         current
        DESCRIPTION    "Reports the DM value in 10**(-7) seconds in the
                        current Interval."
        ::= { tnDwdmCmnLinePortInfoEntry 17 }

    tnDwdmCmnLinePortOtsigId OBJECT-TYPE
        SYNTAX         Integer32 (0..255)
        MAX-ACCESS     read-only
        STATUS         current
        DESCRIPTION    "Line Port OtsigId."
        DEFVAL         { 0 }
        ::= { tnDwdmCmnLinePortInfoEntry 18 }

    tnDwdmCmnLinePortOtsigModuleCapabilityFileName OBJECT-TYPE
        SYNTAX         SnmpAdminString (SIZE(0..128))
        MAX-ACCESS     read-only
        STATUS         current
        DESCRIPTION    "File name associated with this port's module capabilities."
        ::= { tnDwdmCmnLinePortInfoEntry 19 }

    tnDwdmCmnLinePortDisruptionTime OBJECT-TYPE
        SYNTAX         Unsigned32
        MAX-ACCESS     read-only
        STATUS         current
        DESCRIPTION    "The disruption time reports the last
                        DSP covergence in microseconds"
        ::= { tnDwdmCmnLinePortInfoEntry 20 }

--------------------------------------------------------------------------------
-- DWDM Common Client Port Info Table
--------------------------------------------------------------------------------
    tnDwdmCmnClientPortInfoTable OBJECT-TYPE
        SYNTAX         SEQUENCE OF TnDwdmCmnClientPortInfoEntry
        MAX-ACCESS     not-accessible
        STATUS         current
        DESCRIPTION    "Common attributes against DWDM client ports."
        ::= { tnOpticalPortInfo 69 }

    tnDwdmCmnClientPortInfoEntry OBJECT-TYPE
        SYNTAX         TnDwdmCmnClientPortInfoEntry
        MAX-ACCESS     not-accessible
        STATUS         current
        DESCRIPTION    "."
        INDEX { ifIndex }
        ::= { tnDwdmCmnClientPortInfoTable 1 }

    TnDwdmCmnClientPortInfoEntry ::=
        SEQUENCE {
            tnDwdmCmnClientPortOtu2IncomingTti       OCTET STRING,
            tnDwdmCmnClientPortOtu2TtiStatus         AluWdmTtiStatus,
            tnDwdmCmnClientPortOdu2IncomingTti       OCTET STRING,
            tnDwdmCmnClientPortOdu2TtiStatus         AluWdmTtiStatus,
--            obsolete
--            tnDwdmCmnClientPortAvailableBandwidth    Unsigned32,
            tnDwdmCmnClientPortBroadcastPortMap      OCTET STRING,
            tnDwdmCmnClientPortOtu2PreFec            Counter64,
            tnDwdmCmnClientPortOtu2PostFec           Counter64,
            tnDwdmCmnClientPortOdu2IncFwFTFLTypeID   OCTET STRING,
            tnDwdmCmnClientPortOdu2IncFwFTFLOperID   OCTET STRING,
            tnDwdmCmnClientPortOdu2IncBwFTFLTypeID   OCTET STRING,
            tnDwdmCmnClientPortOdu2IncBwFTFLOperID   OCTET STRING,
            tnDwdmCmnClientPortOdu2IncResRow2        OCTET STRING,
            tnDwdmCmnClientPortOdu2IncResRow4        OCTET STRING,
            tnDwdmCmnClientPortOdu2IncExp            OCTET STRING,
            tnDwdmCmnClientPortOtu2IncRes            OCTET STRING,
            tnDwdmCmnClientPortEthPrefec             Counter64,
            tnDwdmCmnClientPortEthPostfec            Counter64
        }

    tnDwdmCmnClientPortOtu2IncomingTti OBJECT-TYPE
        SYNTAX         OCTET STRING
        MAX-ACCESS     read-only
        STATUS         current
        DESCRIPTION    "OTU2 incoming TTI."
        ::= { tnDwdmCmnClientPortInfoEntry 1 }

    tnDwdmCmnClientPortOtu2TtiStatus OBJECT-TYPE
        SYNTAX         AluWdmTtiStatus
        MAX-ACCESS     read-only
        STATUS         current
        DESCRIPTION    "OTU2 TTI status."
        ::= { tnDwdmCmnClientPortInfoEntry 2 }

    tnDwdmCmnClientPortOdu2IncomingTti OBJECT-TYPE
        SYNTAX         OCTET STRING
        MAX-ACCESS     read-only
        STATUS         current
        DESCRIPTION    "ODU2 incoming TTI."
        ::= { tnDwdmCmnClientPortInfoEntry 3 }

    tnDwdmCmnClientPortOdu2TtiStatus OBJECT-TYPE
        SYNTAX         AluWdmTtiStatus
        MAX-ACCESS     read-only
        STATUS         current
        DESCRIPTION    "ODU2 TTI status."
        ::= { tnDwdmCmnClientPortInfoEntry 4 }

--    obsolete
--    tnDwdmCmnClientPortAvailableBandwidth OBJECT-TYPE ::= { tnDwdmCmnClientPortInfoEntry 5 }

    tnDwdmCmnClientPortBroadcastPortMap OBJECT-TYPE
        SYNTAX         OCTET STRING (SIZE(0..255))
        MAX-ACCESS     read-only
        STATUS         current
        DESCRIPTION    "Client Broadcast port map."
        ::= { tnDwdmCmnClientPortInfoEntry 6 }

    tnDwdmCmnClientPortOtu2PreFec OBJECT-TYPE
        SYNTAX         Counter64
        MAX-ACCESS     read-only
        STATUS         current
        DESCRIPTION    "Real time error bit rate of pre-FEC (Forward
                        Error Correction)."
        ::= { tnDwdmCmnClientPortInfoEntry 7 }

    tnDwdmCmnClientPortOtu2PostFec OBJECT-TYPE
        SYNTAX         Counter64
        MAX-ACCESS     read-only
        STATUS         current
        DESCRIPTION    "Real time error bit rate of post-FEC (Forward
                        Error Correction)."
        ::= { tnDwdmCmnClientPortInfoEntry 8 }

    tnDwdmCmnClientPortOdu2IncFwFTFLTypeID OBJECT-TYPE
        SYNTAX         OCTET STRING
        MAX-ACCESS     read-only
        STATUS         current
        DESCRIPTION    "ODU2 Incoming Forward FTFL Type ID."
        ::= { tnDwdmCmnClientPortInfoEntry 9 }

    tnDwdmCmnClientPortOdu2IncFwFTFLOperID OBJECT-TYPE
        SYNTAX         OCTET STRING
        MAX-ACCESS     read-only
        STATUS         current
        DESCRIPTION    "ODU2 Incoming Forward FTFL Operator ID."
        ::= { tnDwdmCmnClientPortInfoEntry 10 }

    tnDwdmCmnClientPortOdu2IncBwFTFLTypeID OBJECT-TYPE
        SYNTAX         OCTET STRING
        MAX-ACCESS     read-only
        STATUS         current
        DESCRIPTION    "ODU2 Incoming Backward FTFL Type ID."
        ::= { tnDwdmCmnClientPortInfoEntry 11 }

    tnDwdmCmnClientPortOdu2IncBwFTFLOperID OBJECT-TYPE
        SYNTAX         OCTET STRING
        MAX-ACCESS     read-only
        STATUS         current
        DESCRIPTION    "ODU2 Incoming Backward FTFL Operator ID."
        ::= { tnDwdmCmnClientPortInfoEntry 12 }

    tnDwdmCmnClientPortOdu2IncResRow2 OBJECT-TYPE
        SYNTAX         OCTET STRING
        MAX-ACCESS     read-only
        STATUS         current
        DESCRIPTION    "ODU2 Incoming Res Row2."
        ::= { tnDwdmCmnClientPortInfoEntry 13 }

    tnDwdmCmnClientPortOdu2IncResRow4 OBJECT-TYPE
        SYNTAX         OCTET STRING
        MAX-ACCESS     read-only
        STATUS         current
        DESCRIPTION    "ODU2 Incoming Res Row4."
        ::= { tnDwdmCmnClientPortInfoEntry 14 }

    tnDwdmCmnClientPortOdu2IncExp OBJECT-TYPE
        SYNTAX         OCTET STRING
        MAX-ACCESS     read-only
        STATUS         current
        DESCRIPTION    "ODU2 Incoming Exp."
        ::= { tnDwdmCmnClientPortInfoEntry 15 }

    tnDwdmCmnClientPortOtu2IncRes OBJECT-TYPE
        SYNTAX         OCTET STRING
        MAX-ACCESS     read-only
        STATUS         current
        DESCRIPTION    "OTU2 Incoming Res."
        ::= { tnDwdmCmnClientPortInfoEntry 16 }

    tnDwdmCmnClientPortEthPrefec OBJECT-TYPE
        SYNTAX         Counter64
        MAX-ACCESS     read-only
        STATUS         current
        DESCRIPTION    "Real time error bit rate of pre-FEC."
        ::= { tnDwdmCmnClientPortInfoEntry 17 }

    tnDwdmCmnClientPortEthPostfec OBJECT-TYPE
        SYNTAX         Counter64
        MAX-ACCESS     read-only
        STATUS         current
        DESCRIPTION    "Real time error bit rate of post-FEC."
        ::= { tnDwdmCmnClientPortInfoEntry 18 }

--------------------------------------------------------------------------------
-- RSMON Ingress Port Info Table
--------------------------------------------------------------------------------
    tnRsmonIngrPortInfoTable OBJECT-TYPE
        SYNTAX         SEQUENCE OF TnRsmonIngrPortInfoEntry
        MAX-ACCESS     not-accessible
        STATUS         current
        DESCRIPTION    "Common attributes against RSMON Ingress
                        supported ports."
        ::= { tnOpticalPortInfo 70 }

    tnRsmonIngrPortInfoEntry OBJECT-TYPE
        SYNTAX         TnRsmonIngrPortInfoEntry
        MAX-ACCESS     not-accessible
        STATUS         current
        DESCRIPTION    "."
        INDEX { ifIndex }
        ::= { tnRsmonIngrPortInfoTable 1 }

    TnRsmonIngrPortInfoEntry ::=
        SEQUENCE {
            tnRsmonIngrPortIncomingTti OCTET STRING,
            tnRsmonIngrPortTtiStatus   INTEGER
        }

    tnRsmonIngrPortIncomingTti OBJECT-TYPE
        SYNTAX         OCTET STRING
        MAX-ACCESS     read-only
        STATUS         current
        DESCRIPTION    "RSMON incoming TTI."
        ::= { tnRsmonIngrPortInfoEntry 1 }

    tnRsmonIngrPortTtiStatus OBJECT-TYPE
        SYNTAX         INTEGER {
                         unavailable(1),
                         normal(2),
                         mismatch(3),
                         unspecified(4)
                       }
        MAX-ACCESS     read-only
        STATUS         current
        DESCRIPTION    "RSMON TTI status."
        ::= { tnRsmonIngrPortInfoEntry 2 }

--------------------------------------------------------------------------------
-- OT Port Info Table
--------------------------------------------------------------------------------
    tnOtPortInfoTable OBJECT-TYPE
        SYNTAX         SEQUENCE OF TnOtPortInfoEntry
        MAX-ACCESS     not-accessible
        STATUS         current
        DESCRIPTION    "The ports on an OT card."
        ::= { tnOpticalPortInfo 71 }

    tnOtPortInfoEntry OBJECT-TYPE
        SYNTAX         TnOtPortInfoEntry
        MAX-ACCESS     not-accessible
        STATUS         current
        DESCRIPTION    "."
        INDEX { ifIndex }
        ::= { tnOtPortInfoTable 1 }

    TnOtPortInfoEntry ::=
        SEQUENCE {
            tnOtPortRxPower                Integer32,
            tnOtPortTxPower                Integer32,
            tnOtPortBias                   Integer32,
            tnOtPortTemperature            Integer32,
            tnOtPortTxPowerLaser           Integer32,
            tnOtPortRxLanePowers           SnmpAdminString,
            tnOtPortTxLanePowers           SnmpAdminString,
            tnOtPortRxLaneBslPowers        SnmpAdminString,
            tnOtPortTxLaneBslPowers        SnmpAdminString,
            tnOtPortQsfpCurrentBias        SnmpAdminString,
            tnOtPortQsfpVoltage            SnmpAdminString,
            tnOtPortSupplyVoltage          Integer32,
            tnOtPortSupplyCurrent          Integer32,
            tnOtPortSupplyPower            Integer32,
            tnOtPortTxLaserAge             Integer32,
            tnOtPortLaserTemp              Integer32,
            tnOtPortRxQmargin30s           Integer32,
            tnOtPortRxQmargin5s            Integer32,
            tnOtPortRxQfactor30s           Integer32,
            tnOtPortRxQfactor5s            Integer32,
            tnOtPortNEQfactor1s            Integer32,
            tnOtPortFEQfactor1s            Integer32,
            tnOtPortTuningSynchroStateRx   INTEGER,
            tnOtPortTuningSynchroStateTx   INTEGER
        }

    tnOtPortRxPower OBJECT-TYPE
        SYNTAX         Integer32
        UNITS          "mBm"
        MAX-ACCESS     read-only
        STATUS         current
        DESCRIPTION    "OT RX power."
        ::= { tnOtPortInfoEntry 1 }

    tnOtPortTxPower OBJECT-TYPE
        SYNTAX         Integer32
        UNITS          "mBm"
        MAX-ACCESS     read-only
        STATUS         current
        DESCRIPTION    "The transmit power after the VOA."
        ::= { tnOtPortInfoEntry 2 }

    tnOtPortBias OBJECT-TYPE
        SYNTAX         Integer32
        UNITS          "mA"
        MAX-ACCESS     read-only
        STATUS         current
        DESCRIPTION    "OT Bias."
        ::= { tnOtPortInfoEntry 3 }

    tnOtPortTemperature OBJECT-TYPE
        SYNTAX         Integer32
        UNITS          "Celsius"
        MAX-ACCESS     read-only
        STATUS         current
        DESCRIPTION    "OT Temperature."
        ::= { tnOtPortInfoEntry 4 }

    tnOtPortTxPowerLaser OBJECT-TYPE
        SYNTAX         Integer32
        UNITS          "mBm"
        MAX-ACCESS     read-only
        STATUS         current
        DESCRIPTION    "The transmit power after the MSA transponder and
                        before the VOA."
        ::= { tnOtPortInfoEntry 5 }

    tnOtPortRxLanePowers OBJECT-TYPE
        SYNTAX         SnmpAdminString (SIZE(0..400))
        MAX-ACCESS     read-only
        STATUS         current
        DESCRIPTION    "Displays CFP receive lane powers for the number
                        of lanes supported by a CFP type.  Receive lane
                        powers will not be displayed for the following
                        conditions:
                          - A CFP does not provide lane powers
                          - A CFP is not equipped (not present)
                          - A port is not provisioned.
                        For a CFP with 4 lanes, here is a sample output:
                          'RxPwr Lane 1  : -40.00 dBm
                           RxPwr Lane 2  : -40.00 dBm
                           RxPwr Lane 3  : -40.00 dBm
                           RxPwr Lane 4  : -40.00 dBm'
                        including the new line characters."
        ::= { tnOtPortInfoEntry 6 }

    tnOtPortTxLanePowers OBJECT-TYPE
        SYNTAX         SnmpAdminString (SIZE(0..400))
        MAX-ACCESS     read-only
        STATUS         current
        DESCRIPTION    "Displays CFP transmit lane powers for the number
                        of lanes supported by a CFP type.  Transmit lane
                        powers will not be displayed for the following
                        conditions:
                          - A CFP does not provide lane powers
                          - A CFP is not equipped (not present)
                          - A port is not provisioned.
                        For a CFP with 4 lanes, here is a sample output:
                          'TxPwr Lane 1  : -40.00 dBm
                           TxPwr Lane 2  : -40.00 dBm
                           TxPwr Lane 3  : -40.00 dBm
                           TxPwr Lane 4  : -40.00 dBm'
                        including the new line characters."
        ::= { tnOtPortInfoEntry 7 }

    tnOtPortRxLaneBslPowers OBJECT-TYPE
        SYNTAX         SnmpAdminString (SIZE(0..400))
        MAX-ACCESS     read-only
        STATUS         current
        DESCRIPTION    "Displays CFP receive lane Baseline powers
                        for the number of lanes supported by a CFP
                        type.  Receive lane powers will not be
                        displayed for the following conditions:
                          - A CFP does not provide lane powers
                          - A CFP is not equipped (not present)
                          - A port is not provisioned.
                          - A CFP port Total RX power is not Baselined
                        For a CFP with 4 lanes, here is a sample output:
                          'RxPwr Lane 1  : -8.00 dBm
                           RxPwr Lane 2  : -8.10 dBm
                           RxPwr Lane 3  : -7.80 dBm
                           RxPwr Lane 4  : -8.30 dBm'
                        including the new line characters."
        ::= { tnOtPortInfoEntry 8 }

    tnOtPortTxLaneBslPowers OBJECT-TYPE
        SYNTAX         SnmpAdminString (SIZE(0..400))
        MAX-ACCESS     read-only
        STATUS         current
        DESCRIPTION    "Displays CFP transmit lane Baseline powers
                        for the number of lanes supported by a CFP
                        type.  Receive lane powers will not be
                        displayed for the following conditions:
                          - A CFP does not provide lane powers
                          - A CFP is not equipped (not present)
                          - A port is not provisioned.
                          - A CFP port Total RX power is not Baselined
                        For a CFP with 4 lanes, here is a sample output:
                          'TxPwr Lane 1  : -8.00 dBm
                           TxPwr Lane 2  : -8.10 dBm
                           TxPwr Lane 3  : -7.80 dBm
                           TxPwr Lane 4  : -8.30 dBm'
                        including the new line characters."
        ::= { tnOtPortInfoEntry 9 }

    tnOtPortQsfpCurrentBias OBJECT-TYPE
        SYNTAX         SnmpAdminString (SIZE(0..400))
        MAX-ACCESS     read-only
        STATUS         current
        DESCRIPTION    "."
        ::= { tnOtPortInfoEntry 10 }

    tnOtPortQsfpVoltage OBJECT-TYPE
        SYNTAX         SnmpAdminString (SIZE(0..400))
        MAX-ACCESS     read-only
        STATUS         current
        DESCRIPTION    "."
        ::= { tnOtPortInfoEntry 11 }

    tnOtPortSupplyVoltage OBJECT-TYPE
        SYNTAX         Integer32
        UNITS          "mV"
        MAX-ACCESS     read-only
        STATUS         current
        DESCRIPTION    "OT Voltage."
        ::= { tnOtPortInfoEntry 12 }

    tnOtPortSupplyCurrent OBJECT-TYPE
        SYNTAX         Integer32
        UNITS          "mA"
        MAX-ACCESS     read-only
        STATUS         current
        DESCRIPTION    "OT Current."
        ::= { tnOtPortInfoEntry 13 }

    tnOtPortSupplyPower OBJECT-TYPE
        SYNTAX         Integer32
        UNITS          "mW"
        MAX-ACCESS     read-only
        STATUS         current
        DESCRIPTION    "OT Power."
        ::= { tnOtPortInfoEntry 14 }

    tnOtPortTxLaserAge OBJECT-TYPE
        SYNTAX         Integer32
        MAX-ACCESS     read-only
        STATUS         current
        DESCRIPTION    "OT Tx Laser Age."
        ::= { tnOtPortInfoEntry 15 }

    tnOtPortLaserTemp OBJECT-TYPE
        SYNTAX         Integer32
        UNITS          "Celsius"
        MAX-ACCESS     read-only
        STATUS         current
        DESCRIPTION    "OT Laser Temperature."
        ::= { tnOtPortInfoEntry 16 }

    tnOtPortRxQmargin30s OBJECT-TYPE
        SYNTAX         Integer32
        MAX-ACCESS     read-only
        STATUS         current
        DESCRIPTION    "."
        ::= { tnOtPortInfoEntry 17 }

    tnOtPortRxQmargin5s OBJECT-TYPE
        SYNTAX         Integer32
        MAX-ACCESS     read-only
        STATUS         current
        DESCRIPTION    "."
        ::= { tnOtPortInfoEntry 18 }

    tnOtPortRxQfactor30s OBJECT-TYPE
        SYNTAX         Integer32
        MAX-ACCESS     read-only
        STATUS         current
        DESCRIPTION    "."
        ::= { tnOtPortInfoEntry 19 }

    tnOtPortRxQfactor5s OBJECT-TYPE
        SYNTAX         Integer32
        MAX-ACCESS     read-only
        STATUS         current
        DESCRIPTION    "."
        ::= { tnOtPortInfoEntry 20 }

    tnOtPortNEQfactor1s OBJECT-TYPE
        SYNTAX         Integer32
        MAX-ACCESS     read-only
        STATUS         current
        DESCRIPTION    "."
        ::= { tnOtPortInfoEntry 21 }

    tnOtPortFEQfactor1s OBJECT-TYPE
        SYNTAX         Integer32
        MAX-ACCESS     read-only
        STATUS         current
        DESCRIPTION    "."
        ::= { tnOtPortInfoEntry 22 }

    tnOtPortTuningSynchroStateRx OBJECT-TYPE
        SYNTAX         INTEGER {
                         noSignal(1),
                         idle(2),
                         fwdRdy(3),
                         bwdRdy(4),
                         fwdRdyAck(5),
                         bwdRdyAck(6)
                       }
        MAX-ACCESS     read-only
        STATUS         current
        DESCRIPTION    "."
        ::= { tnOtPortInfoEntry 23 }

    tnOtPortTuningSynchroStateTx OBJECT-TYPE
        SYNTAX         INTEGER {
                         idle(1),
                         fwdRdy(2),
                         bwdRdy(3),
                         fwdRdyAck(4),
                         bwdRdyAck(5)
                       }
        MAX-ACCESS     read-only
        STATUS         current
        DESCRIPTION    "."
        ::= { tnOtPortInfoEntry 24 }

--------------------------------------------------------------------------------
-- Wave Key Optical Port Info Table
--------------------------------------------------------------------------------
    tnWaveKeyPortInfoTable OBJECT-TYPE
        SYNTAX         SEQUENCE OF TnWaveKeyPortInfoEntry
        MAX-ACCESS     not-accessible
        STATUS         current
        DESCRIPTION    "This table is a compilation of attributes
                        associated with the ports on a Wave Key
                        decode supported optical card."
        ::= { tnOpticalPortInfo 72 }

    tnWaveKeyPortInfoEntry OBJECT-TYPE
        SYNTAX         TnWaveKeyPortInfoEntry
        MAX-ACCESS     not-accessible
        STATUS         current
        DESCRIPTION    "."
        INDEX { ifIndex }
        ::= { tnWaveKeyPortInfoTable 1 }

    TnWaveKeyPortInfoEntry ::=
        SEQUENCE {
            tnWaveKeyPortNwPowerIn                    Integer32,
            tnWaveKeyPortNwPowerOut                   Integer32,
--            obsolete
--            tnWavekeyPortWTDecoderUsageStatusIn       AluWdmWTDecoderUsageType,
--            tnWavekeyPortWTDecoderUsageStatusOut      AluWdmWTDecoderUsageType,
            tnWaveKeyPortWTDecoderMeasurementTypeIn   AluWdmWTDecoderMeasurementType,
            tnWaveKeyPortWTDecoderMeasurementTypeOut  AluWdmWTDecoderMeasurementType,
            tnWaveKeyPortNwPowerInL                   Integer32,
            tnWaveKeyPortNwPowerOutL                  Integer32,
            tnWaveKeyPortWTDecoderMeasurementTypeInL  AluWdmWTDecoderMeasurementType,
            tnWaveKeyPortWTDecoderMeasurementTypeOutL AluWdmWTDecoderMeasurementType
        }

    tnWaveKeyPortNwPowerIn OBJECT-TYPE
        SYNTAX         Integer32
        UNITS          "mBm"
        MAX-ACCESS     read-only
        STATUS         current
        DESCRIPTION    "The total ingress power of the optical signal.
                        Current Ranges:

                        ASWG:   -9900, -3600 to 1700
                        A4PSWG: -9900, -3600 to 1700."
        ::= { tnWaveKeyPortInfoEntry 1 }

    tnWaveKeyPortNwPowerOut OBJECT-TYPE
        SYNTAX         Integer32
        UNITS          "mBm"
        MAX-ACCESS     read-only
        STATUS         current
        DESCRIPTION    "The total egress power of the optical signal.
                        Current Ranges:

                        ASWG:   -9900, -1100 to 2550
                        A4PSWG: -9900, -1100 to 2550."
        ::= { tnWaveKeyPortInfoEntry 2 }

--    obsolete
--    tnWavekeyPortWTDecoderUsageStatusIn  OBJECT-TYPE ::= { tnWaveKeyPortInfoEntry 3 }
--    tnWavekeyPortWTDecoderUsageStatusOut OBJECT-TYPE ::= { tnWaveKeyPortInfoEntry 4 }

    tnWaveKeyPortWTDecoderMeasurementTypeIn OBJECT-TYPE
        SYNTAX         AluWdmWTDecoderMeasurementType
        MAX-ACCESS     read-only
        STATUS         current
        DESCRIPTION    "The measurement source for the WTD in the
                        ingress direction."
        DEFVAL         { unavailable }
        ::= { tnWaveKeyPortInfoEntry 5 }

    tnWaveKeyPortWTDecoderMeasurementTypeOut OBJECT-TYPE
        SYNTAX         AluWdmWTDecoderMeasurementType
        MAX-ACCESS     read-only
        STATUS         current
        DESCRIPTION    "The measurement source for the WTD in the
                        egress direction."
        DEFVAL         { unavailable }
        ::= { tnWaveKeyPortInfoEntry 6 }

    tnWaveKeyPortNwPowerInL OBJECT-TYPE
        SYNTAX         Integer32
        UNITS          "mBm"
        MAX-ACCESS     read-only
        STATUS         current
        DESCRIPTION    "The total ingress power of the optical signal for L band."
        ::= { tnWaveKeyPortInfoEntry 7 }

    tnWaveKeyPortNwPowerOutL OBJECT-TYPE
        SYNTAX         Integer32
        UNITS          "mBm"
        MAX-ACCESS     read-only
        STATUS         current
        DESCRIPTION    "The total egress power of the optical signal for L band."
        ::= { tnWaveKeyPortInfoEntry 8 }

    tnWaveKeyPortWTDecoderMeasurementTypeInL OBJECT-TYPE
        SYNTAX         AluWdmWTDecoderMeasurementType
        MAX-ACCESS     read-only
        STATUS         current
        DESCRIPTION    "The measurement source for the WTD in the ingress direction
                        for L band."
        DEFVAL         { unavailable }
        ::= { tnWaveKeyPortInfoEntry 9 }

    tnWaveKeyPortWTDecoderMeasurementTypeOutL OBJECT-TYPE
        SYNTAX         AluWdmWTDecoderMeasurementType
        MAX-ACCESS     read-only
        STATUS         current
        DESCRIPTION    "The measurement source for the WTD in the egress direction
                        for L band."
        DEFVAL         { unavailable }
        ::= { tnWaveKeyPortInfoEntry 10 }

--------------------------------------------------------------------------------
-- OMD Common Port Info Table
--------------------------------------------------------------------------------
    tnOmdPortInfoTable OBJECT-TYPE
        SYNTAX         SEQUENCE OF TnOmdPortInfoEntry
        MAX-ACCESS     not-accessible
        STATUS         current
        DESCRIPTION    "Common attributes against OMD ports for SFC and
                        SFD packs."
        ::= { tnOpticalPortInfo 73 }

    tnOmdPortInfoEntry OBJECT-TYPE
        SYNTAX         TnOmdPortInfoEntry
        MAX-ACCESS     not-accessible
        STATUS         current
        DESCRIPTION    "."
        INDEX { ifIndex }
        ::= { tnOmdPortInfoTable 1 }

    TnOmdPortInfoEntry ::=
        SEQUENCE {
            tnOmdPortReceivedPower     Integer32,
            tnOmdPortTransmittedPower  Integer32
        }

    tnOmdPortReceivedPower OBJECT-TYPE
        SYNTAX         Integer32
        UNITS          "mBm"
        MAX-ACCESS     read-only
        STATUS         current
        DESCRIPTION    "The measured power at the SIG_IN of the OMD port."
        DEFVAL         { 0 }
        ::= { tnOmdPortInfoEntry 1 }

    tnOmdPortTransmittedPower OBJECT-TYPE
        SYNTAX         Integer32
        UNITS          "mBm"
        MAX-ACCESS     read-only
        STATUS         current
        DESCRIPTION    "The measured power at the SIG_OUT of the OMD port."
        DEFVAL         { 0 }
        ::= { tnOmdPortInfoEntry 2 }

--------------------------------------------------------------------------------
-- 4DPA4 Optical Port Info Scalar
--------------------------------------------------------------------------------
    tn4dpa4PortInfoAttributeTotal OBJECT-TYPE
        SYNTAX         Integer32
        MAX-ACCESS     read-only
        STATUS         current
        DESCRIPTION    "."
        ::= { tnOpticalPortInfo 74 }

--------------------------------------------------------------------------------
-- 4DPA4 Optical Port Info Table
--------------------------------------------------------------------------------
    tn4dpa4PortInfoTable OBJECT-TYPE
        SYNTAX         SEQUENCE OF Tn4dpa4PortInfoEntry
        MAX-ACCESS     not-accessible
        STATUS         current
        DESCRIPTION    "The ports on a 4DPA4 optical card."
        ::= { tnOpticalPortInfo 75 }

    tn4dpa4PortInfoEntry OBJECT-TYPE
        SYNTAX         Tn4dpa4PortInfoEntry
        MAX-ACCESS     not-accessible
        STATUS         current
        DESCRIPTION    "."
        INDEX { ifIndex }
        ::= { tn4dpa4PortInfoTable 1 }

    Tn4dpa4PortInfoEntry ::=
        SEQUENCE {
            tn4dpa4PortInfoFunction INTEGER
        }

    tn4dpa4PortInfoFunction OBJECT-TYPE
        SYNTAX         INTEGER {
                         network(1),
                         client(2),
                         evoa(3)
                       }
        MAX-ACCESS     read-only
        STATUS         current
        DESCRIPTION    "Indicates the functional type of this 4DPA4 port."
        ::= { tn4dpa4PortInfoEntry 1 }

--------------------------------------------------------------------------------
-- CWR8-88 Optical Port Info Scalar
--------------------------------------------------------------------------------
    tnCwr8c88PortInfoAttributeTotal OBJECT-TYPE
        SYNTAX         Integer32
        MAX-ACCESS     read-only
        STATUS         current
        DESCRIPTION    "."
        ::= { tnOpticalPortInfo 76 }

--------------------------------------------------------------------------------
-- CWR8-88 Optical Port Info Table
--------------------------------------------------------------------------------
    tnCwr8c88PortInfoTable OBJECT-TYPE
        SYNTAX         SEQUENCE OF TnCwr8c88PortInfoEntry
        MAX-ACCESS     not-accessible
        STATUS         current
        DESCRIPTION    "The ports on a CWR8-88 optical card."
        ::= { tnOpticalPortInfo 77 }

    tnCwr8c88PortInfoEntry OBJECT-TYPE
        SYNTAX         TnCwr8c88PortInfoEntry
        MAX-ACCESS     not-accessible
        STATUS         current
        DESCRIPTION    "."
        INDEX { ifIndex }
        ::= { tnCwr8c88PortInfoTable 1 }

    TnCwr8c88PortInfoEntry ::=
        SEQUENCE {
            tnCwr8c88PortInfoFunction           INTEGER,
            tnCwr8c88PortRelativeAttenuationMin Unsigned32,
            tnCwr8c88PortAverageAttenuationOut  Unsigned32
        }

    tnCwr8c88PortInfoFunction OBJECT-TYPE
        SYNTAX         INTEGER {
                         signal(1),
                         test(2),
                         thru(3),
                         colorless(4),
                         omd(5),
                         inv(6)
                       }
        MAX-ACCESS     read-only
        STATUS         current
        DESCRIPTION    "Indicates the functional type of this CWR8-88 port."
        ::= { tnCwr8c88PortInfoEntry 1 }

    tnCwr8c88PortRelativeAttenuationMin OBJECT-TYPE
        SYNTAX         Unsigned32
        UNITS          "mB"
        MAX-ACCESS     read-only
        STATUS         current
        DESCRIPTION    "The following description applies to the Thru
                        port of the CWR8-88 card:

                        The minimum attenuation on the blocker across
                        all of the channels."
        DEFVAL         { 0 }
        ::= { tnCwr8c88PortInfoEntry 2 }

    tnCwr8c88PortAverageAttenuationOut OBJECT-TYPE
        SYNTAX         Unsigned32
        UNITS          "mB"
        MAX-ACCESS     read-only
        STATUS         current
        DESCRIPTION    "The following description applies to the Thru
                        port of the CWR8-88 card:

                        The average attenuation on the blocker across
                        all of the channels."
        DEFVAL         { 0 }
        ::= { tnCwr8c88PortInfoEntry 3 }

--------------------------------------------------------------------------------
-- AHPLG Optical Port Info Scalar
--------------------------------------------------------------------------------
    tnAhplgPortInfoAttributeTotal OBJECT-TYPE
        SYNTAX         Integer32
        MAX-ACCESS     read-only
        STATUS         current
        DESCRIPTION    "."
        ::= { tnOpticalPortInfo 78 }

--------------------------------------------------------------------------------
-- AHPLG Optical Port Info Table
--------------------------------------------------------------------------------
    tnAhplgPortInfoTable OBJECT-TYPE
        SYNTAX         SEQUENCE OF TnAhplgPortInfoEntry
        MAX-ACCESS     not-accessible
        STATUS         current
        DESCRIPTION    "The ports on an AHPLG optical card."
        ::= { tnOpticalPortInfo 79 }

    tnAhplgPortInfoEntry OBJECT-TYPE
        SYNTAX         TnAhplgPortInfoEntry
        MAX-ACCESS     not-accessible
        STATUS         current
        DESCRIPTION    "."
        INDEX { ifIndex }
        ::= { tnAhplgPortInfoTable 1 }

    TnAhplgPortInfoEntry ::=
        SEQUENCE {
            tnAhplgPortInfoFunction INTEGER
        }

    tnAhplgPortInfoFunction OBJECT-TYPE
        SYNTAX         INTEGER {
                         line(1),
                         signal(2),
                         dcm(3),
                         inv(4),
                         osc(5),
                         custLan(6)
                       }
        MAX-ACCESS     read-only
        STATUS         current
        DESCRIPTION    "Indicates the functional type of this AHPLG port."
        ::= { tnAhplgPortInfoEntry 1 }

--------------------------------------------------------------------------------
-- Line Port Timeslot Info Table
--------------------------------------------------------------------------------
    tnTimeSlotLinePortInfoTable OBJECT-TYPE
        SYNTAX         SEQUENCE OF TnTimeSlotLinePortInfoEntry
        MAX-ACCESS     not-accessible
        STATUS         current
        DESCRIPTION    "The line port timeslots on an optical card."
        ::= { tnOpticalPortInfo 80 }

    tnTimeSlotLinePortInfoEntry OBJECT-TYPE
        SYNTAX         TnTimeSlotLinePortInfoEntry
        MAX-ACCESS     not-accessible
        STATUS         current
        DESCRIPTION    "."
        INDEX { ifIndex,
                tnTimeSlot }
        ::= { tnTimeSlotLinePortInfoTable 1 }

    TnTimeSlotLinePortInfoEntry ::=
        SEQUENCE {
            tnTimeSlot                               Unsigned32,
            tnTimeSlotLinePortFarEndIfType           AluWdmTnIfType,
            tnTimeSlotLinePortFarEndInterfaceIndex   InterfaceIndexOrZero,
            tnTimeSlotLinePortNearEndIfType          AluWdmTnIfType,
            tnTimeSlotLinePortNearEndInterfaceIndex  InterfaceIndexOrZero
        }

    tnTimeSlot OBJECT-TYPE
        SYNTAX         Unsigned32
        MAX-ACCESS     not-accessible
        STATUS         current
        DESCRIPTION    "Timeslot index."
        ::= { tnTimeSlotLinePortInfoEntry 1 }

    tnTimeSlotLinePortFarEndIfType OBJECT-TYPE
        SYNTAX         AluWdmTnIfType
        MAX-ACCESS     read-only
        STATUS         current
        DESCRIPTION    "Far end line port interface type."
        ::= { tnTimeSlotLinePortInfoEntry 2 }

    tnTimeSlotLinePortFarEndInterfaceIndex OBJECT-TYPE
        SYNTAX         InterfaceIndexOrZero
        MAX-ACCESS     read-only
        STATUS         current
        DESCRIPTION    "Far end line port interface index."
        ::= { tnTimeSlotLinePortInfoEntry 3 }

    tnTimeSlotLinePortNearEndIfType OBJECT-TYPE
        SYNTAX         AluWdmTnIfType
        MAX-ACCESS     read-only
        STATUS         current
        DESCRIPTION    "Near end line port interface type."
        ::= { tnTimeSlotLinePortInfoEntry 4 }

    tnTimeSlotLinePortNearEndInterfaceIndex OBJECT-TYPE
        SYNTAX         InterfaceIndexOrZero
        MAX-ACCESS     read-only
        STATUS         current
        DESCRIPTION    "Near end line port interface index."
        ::= { tnTimeSlotLinePortInfoEntry 5 }

--------------------------------------------------------------------------------
-- DWDM Common OTU1/ODU1 Line Port Info Table
--------------------------------------------------------------------------------
    tnDwdmCmnOtu1Odu1LinePortInfoTable OBJECT-TYPE
        SYNTAX         SEQUENCE OF TnDwdmCmnOtu1Odu1LinePortInfoEntry
        MAX-ACCESS     not-accessible
        STATUS         current
        DESCRIPTION    "Common attributes against DWDM line ports."
        ::= { tnOpticalPortInfo 81 }

    tnDwdmCmnOtu1Odu1LinePortInfoEntry OBJECT-TYPE
        SYNTAX         TnDwdmCmnOtu1Odu1LinePortInfoEntry
        MAX-ACCESS     not-accessible
        STATUS         current
        DESCRIPTION    "."
        INDEX { ifIndex }
        ::= { tnDwdmCmnOtu1Odu1LinePortInfoTable 1 }

    TnDwdmCmnOtu1Odu1LinePortInfoEntry ::=
        SEQUENCE {
            tnDwdmCmnLinePortOtu1IncomingTti OCTET STRING,
            tnDwdmCmnLinePortOtu1TtiStatus   AluWdmTtiStatus,
            tnDwdmCmnLinePortOdu1IncomingTti OCTET STRING,
            tnDwdmCmnLinePortOdu1TtiStatus   AluWdmTtiStatus
        }

    tnDwdmCmnLinePortOtu1IncomingTti OBJECT-TYPE
        SYNTAX         OCTET STRING
        MAX-ACCESS     read-only
        STATUS         current
        DESCRIPTION    "OTU1 incoming TTI."
        DEFVAL         { "" }
        ::= { tnDwdmCmnOtu1Odu1LinePortInfoEntry 1 }

    tnDwdmCmnLinePortOtu1TtiStatus OBJECT-TYPE
        SYNTAX         AluWdmTtiStatus
        MAX-ACCESS     read-only
        STATUS         current
        DESCRIPTION    "OTU1 TTI status."
        DEFVAL         { unspecified }
        ::= { tnDwdmCmnOtu1Odu1LinePortInfoEntry 2 }

    tnDwdmCmnLinePortOdu1IncomingTti OBJECT-TYPE
        SYNTAX         OCTET STRING
        MAX-ACCESS     read-only
        STATUS         current
        DESCRIPTION    "ODU1 incoming TTI."
        DEFVAL         { "" }
        ::= { tnDwdmCmnOtu1Odu1LinePortInfoEntry 3 }

    tnDwdmCmnLinePortOdu1TtiStatus OBJECT-TYPE
        SYNTAX         AluWdmTtiStatus
        MAX-ACCESS     read-only
        STATUS         current
        DESCRIPTION    "ODU1 TTI status."
        DEFVAL         { unspecified }
        ::= { tnDwdmCmnOtu1Odu1LinePortInfoEntry 4 }

--------------------------------------------------------------------------------
-- DWDM Common OTU1/ODU1 Client Port Info Table
--------------------------------------------------------------------------------
    tnDwdmCmnOtu1Odu1ClientPortInfoTable OBJECT-TYPE
        SYNTAX         SEQUENCE OF TnDwdmCmnOtu1Odu1ClientPortInfoEntry
        MAX-ACCESS     not-accessible
        STATUS         current
        DESCRIPTION    "Common attributes against DWDM client ports."
        ::= { tnOpticalPortInfo 82 }

    tnDwdmCmnOtu1Odu1ClientPortInfoEntry OBJECT-TYPE
        SYNTAX         TnDwdmCmnOtu1Odu1ClientPortInfoEntry
        MAX-ACCESS     not-accessible
        STATUS         current
        DESCRIPTION    "."
        INDEX { ifIndex }
        ::= { tnDwdmCmnOtu1Odu1ClientPortInfoTable 1 }

    TnDwdmCmnOtu1Odu1ClientPortInfoEntry ::=
        SEQUENCE {
            tnDwdmCmnClientPortOtu1IncomingTti OCTET STRING,
            tnDwdmCmnClientPortOtu1TtiStatus   AluWdmTtiStatus,
            tnDwdmCmnClientPortOdu1IncomingTti OCTET STRING,
            tnDwdmCmnClientPortOdu1TtiStatus   AluWdmTtiStatus,
            tnDwdmCmnClientPortOtu1PreFec      Counter64,
            tnDwdmCmnClientPortOtu1PostFec     Counter64
        }

    tnDwdmCmnClientPortOtu1IncomingTti OBJECT-TYPE
        SYNTAX         OCTET STRING
        MAX-ACCESS     read-only
        STATUS         current
        DESCRIPTION    "OTU1 incoming TTI."
        DEFVAL         { "" }
        ::= { tnDwdmCmnOtu1Odu1ClientPortInfoEntry 1 }

    tnDwdmCmnClientPortOtu1TtiStatus OBJECT-TYPE
        SYNTAX         AluWdmTtiStatus
        MAX-ACCESS     read-only
        STATUS         current
        DESCRIPTION    "OTU1 TTI status."
        DEFVAL         { unspecified }
        ::= { tnDwdmCmnOtu1Odu1ClientPortInfoEntry 2 }

    tnDwdmCmnClientPortOdu1IncomingTti OBJECT-TYPE
        SYNTAX         OCTET STRING
        MAX-ACCESS     read-only
        STATUS         current
        DESCRIPTION    "ODU1 incoming TTI."
        DEFVAL         { "" }
        ::= { tnDwdmCmnOtu1Odu1ClientPortInfoEntry 3 }

    tnDwdmCmnClientPortOdu1TtiStatus OBJECT-TYPE
        SYNTAX         AluWdmTtiStatus
        MAX-ACCESS     read-only
        STATUS         current
        DESCRIPTION    "ODU1 TTI status."
        DEFVAL         { unspecified }
        ::= { tnDwdmCmnOtu1Odu1ClientPortInfoEntry 4 }

    tnDwdmCmnClientPortOtu1PreFec OBJECT-TYPE
        SYNTAX         Counter64
        MAX-ACCESS     read-only
        STATUS         current
        DESCRIPTION    "Real time error bit rate of pre-FEC (Forward
                        Error Correction).

                        Current configurable range: 0 to 4000."
        ::= { tnDwdmCmnOtu1Odu1ClientPortInfoEntry 5 }

    tnDwdmCmnClientPortOtu1PostFec OBJECT-TYPE
        SYNTAX         Counter64
        MAX-ACCESS     read-only
        STATUS         current
        DESCRIPTION    "Real time error bit rate of post-FEC (Forward
                        Error Correction).

                        Current configurable range: 0 to 4000."
        ::= { tnDwdmCmnOtu1Odu1ClientPortInfoEntry 6 }

--------------------------------------------------------------------------------
-- 43STX4 Optical Port Info Scalar
--------------------------------------------------------------------------------
    tn43stx4PortInfoAttributeTotal OBJECT-TYPE
        SYNTAX         Integer32
        MAX-ACCESS     read-only
        STATUS         current
        DESCRIPTION    "."
        ::= { tnOpticalPortInfo 83 }

--------------------------------------------------------------------------------
-- 43STX4 Optical Port Info Table
--------------------------------------------------------------------------------
    tn43stx4PortInfoTable OBJECT-TYPE
        SYNTAX         SEQUENCE OF Tn43stx4PortInfoEntry
        MAX-ACCESS     not-accessible
        STATUS         current
        DESCRIPTION    "The ports on a 43STX4 optical card."
        ::= { tnOpticalPortInfo 84 }

    tn43stx4PortInfoEntry OBJECT-TYPE
        SYNTAX         Tn43stx4PortInfoEntry
        MAX-ACCESS     not-accessible
        STATUS         current
        DESCRIPTION    "."
        INDEX { ifIndex }
        ::= { tn43stx4PortInfoTable 1 }

    Tn43stx4PortInfoEntry ::=
        SEQUENCE {
            tn43stx4PortInfoFunction INTEGER
        }

    tn43stx4PortInfoFunction OBJECT-TYPE
        SYNTAX         INTEGER {
                         network(1),
                         client(2)
                       }
        MAX-ACCESS     read-only
        STATUS         current
        DESCRIPTION    "Indicates the functional type of this 43STX4 port."
        ::= { tn43stx4PortInfoEntry 1 }

--------------------------------------------------------------------------------
-- DWDM Common OTU3/ODU3 Line Port Info Table
--------------------------------------------------------------------------------
    tnDwdmCmnOtu3Odu3LinePortInfoTable OBJECT-TYPE
        SYNTAX         SEQUENCE OF TnDwdmCmnOtu3Odu3LinePortInfoEntry
        MAX-ACCESS     not-accessible
        STATUS         current
        DESCRIPTION    "Common attributes against DWDM line ports."
        ::= { tnOpticalPortInfo 85 }

    tnDwdmCmnOtu3Odu3LinePortInfoEntry OBJECT-TYPE
        SYNTAX         TnDwdmCmnOtu3Odu3LinePortInfoEntry
        MAX-ACCESS     not-accessible
        STATUS         current
        DESCRIPTION    "."
        INDEX { ifIndex }
        ::= { tnDwdmCmnOtu3Odu3LinePortInfoTable 1 }

    TnDwdmCmnOtu3Odu3LinePortInfoEntry ::=
        SEQUENCE {
            tnDwdmCmnLinePortOtu3IncomingTti      OCTET STRING,
            tnDwdmCmnLinePortOtu3TtiStatus        AluWdmTtiStatus,
            tnDwdmCmnLinePortOdu3IncomingTti      OCTET STRING,
            tnDwdmCmnLinePortOdu3TtiStatus        AluWdmTtiStatus,
            tnDwdmCmnLinePortOtu3PreFec           Counter64,
            tnDwdmCmnLinePortOtu3PostFec          Counter64,
            tnDwdmCmnLinePortOdu3IncFwFTFLTypeID  OCTET STRING,
            tnDwdmCmnLinePortOdu3IncFwFTFLOperID  OCTET STRING,
            tnDwdmCmnLinePortOdu3IncBwFTFLTypeID  OCTET STRING,
            tnDwdmCmnLinePortOdu3IncBwFTFLOperID  OCTET STRING,
            tnDwdmCmnLinePortOdu3IncResRow2       OCTET STRING,
            tnDwdmCmnLinePortOdu3IncResRow4       OCTET STRING,
            tnDwdmCmnLinePortOdu3IncExp           OCTET STRING,
            tnDwdmCmnLinePortOtu3IncRes           OCTET STRING
        }

    tnDwdmCmnLinePortOtu3IncomingTti OBJECT-TYPE
        SYNTAX         OCTET STRING
        MAX-ACCESS     read-only
        STATUS         current
        DESCRIPTION    "OTU3 incoming TTI."
        DEFVAL         { "" }
        ::= { tnDwdmCmnOtu3Odu3LinePortInfoEntry 1 }

    tnDwdmCmnLinePortOtu3TtiStatus OBJECT-TYPE
        SYNTAX         AluWdmTtiStatus
        MAX-ACCESS     read-only
        STATUS         current
        DESCRIPTION    "OTU3 TTI status."
        DEFVAL         { unspecified }
        ::= { tnDwdmCmnOtu3Odu3LinePortInfoEntry 2 }

    tnDwdmCmnLinePortOdu3IncomingTti OBJECT-TYPE
        SYNTAX         OCTET STRING
        MAX-ACCESS     read-only
        STATUS         current
        DESCRIPTION    "ODU3 incoming TTI."
        DEFVAL         { "" }
        ::= { tnDwdmCmnOtu3Odu3LinePortInfoEntry 3 }

    tnDwdmCmnLinePortOdu3TtiStatus OBJECT-TYPE
        SYNTAX         AluWdmTtiStatus
        MAX-ACCESS     read-only
        STATUS         current
        DESCRIPTION    "ODU3 TTI status."
        DEFVAL         { unspecified }
        ::= { tnDwdmCmnOtu3Odu3LinePortInfoEntry 4 }

    tnDwdmCmnLinePortOtu3PreFec OBJECT-TYPE
        SYNTAX         Counter64
        MAX-ACCESS     read-only
        STATUS         current
        DESCRIPTION    "Real time error bit rate of pre-FEC (Forward
                        Error Correction).

                        Current configurable range: 0 to 4000."
        ::= { tnDwdmCmnOtu3Odu3LinePortInfoEntry 5 }

    tnDwdmCmnLinePortOtu3PostFec OBJECT-TYPE
        SYNTAX         Counter64
        MAX-ACCESS     read-only
        STATUS         current
        DESCRIPTION    "Real time error bit rate of post-FEC (Forward
                        Error Correction).

                        Current configurable range: 0 to 4000."
        ::= { tnDwdmCmnOtu3Odu3LinePortInfoEntry 6 }

    tnDwdmCmnLinePortOdu3IncFwFTFLTypeID OBJECT-TYPE
        SYNTAX         OCTET STRING
        MAX-ACCESS     read-only
        STATUS         current
        DESCRIPTION    "ODU3 Incoming Forward FTFL Type ID."
        DEFVAL         { "" }
        ::= { tnDwdmCmnOtu3Odu3LinePortInfoEntry 7 }

    tnDwdmCmnLinePortOdu3IncFwFTFLOperID OBJECT-TYPE
        SYNTAX         OCTET STRING
        MAX-ACCESS     read-only
        STATUS         current
        DESCRIPTION    "ODU3 Incoming Forward FTFL Operator ID."
        DEFVAL         { "" }
        ::= { tnDwdmCmnOtu3Odu3LinePortInfoEntry 8 }

    tnDwdmCmnLinePortOdu3IncBwFTFLTypeID OBJECT-TYPE
        SYNTAX         OCTET STRING
        MAX-ACCESS     read-only
        STATUS         current
        DESCRIPTION    "ODU3 Incoming Backward FTFL Type ID."
        DEFVAL         { "" }
        ::= { tnDwdmCmnOtu3Odu3LinePortInfoEntry 9 }

    tnDwdmCmnLinePortOdu3IncBwFTFLOperID OBJECT-TYPE
        SYNTAX         OCTET STRING
        MAX-ACCESS     read-only
        STATUS         current
        DESCRIPTION    "ODU3 Incoming Backward FTFL Operator ID."
        DEFVAL         { "" }
        ::= { tnDwdmCmnOtu3Odu3LinePortInfoEntry 10 }

    tnDwdmCmnLinePortOdu3IncResRow2 OBJECT-TYPE
        SYNTAX         OCTET STRING
        MAX-ACCESS     read-only
        STATUS         current
        DESCRIPTION    "ODU3 Incoming Res Row2."
        DEFVAL         { "" }
        ::= { tnDwdmCmnOtu3Odu3LinePortInfoEntry 11 }

    tnDwdmCmnLinePortOdu3IncResRow4 OBJECT-TYPE
        SYNTAX         OCTET STRING
        MAX-ACCESS     read-only
        STATUS         current
        DESCRIPTION    "ODU3 Incoming Res Row4."
        DEFVAL         { "" }
        ::= { tnDwdmCmnOtu3Odu3LinePortInfoEntry 12 }

    tnDwdmCmnLinePortOdu3IncExp OBJECT-TYPE
        SYNTAX         OCTET STRING
        MAX-ACCESS     read-only
        STATUS         current
        DESCRIPTION    "ODU3 Incoming Exp."
        DEFVAL         { "" }
        ::= { tnDwdmCmnOtu3Odu3LinePortInfoEntry 13 }

    tnDwdmCmnLinePortOtu3IncRes OBJECT-TYPE
        SYNTAX         OCTET STRING
        MAX-ACCESS     read-only
        STATUS         current
        DESCRIPTION    "OTU3 Incoming Res."
        DEFVAL         { "" }
        ::= { tnDwdmCmnOtu3Odu3LinePortInfoEntry 14 }

--------------------------------------------------------------------------------
-- ALPFGK Optical Port Info Scalar
--------------------------------------------------------------------------------
    tnAlpfgkPortInfoAttributeTotal OBJECT-TYPE
        SYNTAX         Integer32
        MAX-ACCESS     read-only
        STATUS         current
        DESCRIPTION    "."
        ::= { tnOpticalPortInfo 86 }

--------------------------------------------------------------------------------
-- ALPFGK Optical Port Info Table
--------------------------------------------------------------------------------
    tnAlpfgkPortInfoTable OBJECT-TYPE
        SYNTAX         SEQUENCE OF TnAlpfgkPortInfoEntry
        MAX-ACCESS     not-accessible
        STATUS         current
        DESCRIPTION    "The ports on an ALPFGK optical card."
        ::= { tnOpticalPortInfo 87 }

    tnAlpfgkPortInfoEntry OBJECT-TYPE
        SYNTAX         TnAlpfgkPortInfoEntry
        MAX-ACCESS     not-accessible
        STATUS         current
        DESCRIPTION    "."
        INDEX { ifIndex }
        ::= { tnAlpfgkPortInfoTable 1 }

    TnAlpfgkPortInfoEntry ::=
        SEQUENCE {
            tnAlpfgkPortInfoFunction  INTEGER
        }

    tnAlpfgkPortInfoFunction OBJECT-TYPE
        SYNTAX         INTEGER {
                         line(1),
                         signal(2),
                         inv(3),
                         osc(4),
                         oscSfp(5)
                       }
        MAX-ACCESS     read-only
        STATUS         current
        DESCRIPTION    "Indicates the functional type of this ALPFGK port."
        ::= { tnAlpfgkPortInfoEntry 1 }

--------------------------------------------------------------------------------
-- 4DPA2 Optical Port Info Scalar
--------------------------------------------------------------------------------
    tn4dpa2PortInfoAttributeTotal OBJECT-TYPE
        SYNTAX         Integer32
        MAX-ACCESS     read-only
        STATUS         current
        DESCRIPTION    "."
        ::= { tnOpticalPortInfo 88 }

--------------------------------------------------------------------------------
-- 4DPA2 Optical Port Info Table
--------------------------------------------------------------------------------
    tn4dpa2PortInfoTable OBJECT-TYPE
        SYNTAX         SEQUENCE OF Tn4dpa2PortInfoEntry
        MAX-ACCESS     not-accessible
        STATUS         current
        DESCRIPTION    "The ports on a 4DPA2 optical card."
        ::= { tnOpticalPortInfo 89 }

    tn4dpa2PortInfoEntry OBJECT-TYPE
        SYNTAX         Tn4dpa2PortInfoEntry
        MAX-ACCESS     not-accessible
        STATUS         current
        DESCRIPTION    "."
        INDEX { ifIndex }
        ::= { tn4dpa2PortInfoTable 1 }

    Tn4dpa2PortInfoEntry ::=
        SEQUENCE {
            tn4dpa2PortInfoFunction INTEGER
        }

    tn4dpa2PortInfoFunction OBJECT-TYPE
        SYNTAX         INTEGER {
                         network(1),
                         client(2)
                       }
        MAX-ACCESS     read-only
        STATUS         current
        DESCRIPTION    "Indicates the functional type of this 4DPA2 port."
        ::= { tn4dpa2PortInfoEntry 1 }

--------------------------------------------------------------------------------
-- 43STA1P Optical Port Info Scalar
--------------------------------------------------------------------------------
    tn43sta1pPortInfoAttributeTotal OBJECT-TYPE
        SYNTAX         Integer32
        MAX-ACCESS     read-only
        STATUS         current
        DESCRIPTION    "."
        ::= { tnOpticalPortInfo 90 }

--------------------------------------------------------------------------------
-- 43STA1P Optical Port Info Table
--------------------------------------------------------------------------------
    tn43sta1pPortInfoTable OBJECT-TYPE
        SYNTAX         SEQUENCE OF Tn43sta1pPortInfoEntry
        MAX-ACCESS     not-accessible
        STATUS         current
        DESCRIPTION    "The ports on a 43STA1P optical card."
        ::= { tnOpticalPortInfo 91 }

    tn43sta1pPortInfoEntry OBJECT-TYPE
        SYNTAX         Tn43sta1pPortInfoEntry
        MAX-ACCESS     not-accessible
        STATUS         current
        DESCRIPTION    "."
        INDEX { ifIndex }
        ::= { tn43sta1pPortInfoTable 1 }

    Tn43sta1pPortInfoEntry ::=
        SEQUENCE {
            tn43sta1pPortInfoFunction INTEGER
        }

    tn43sta1pPortInfoFunction OBJECT-TYPE
        SYNTAX         INTEGER {
                         network(1),
                         client(2)
                       }
        MAX-ACCESS     read-only
        STATUS         current
        DESCRIPTION    "Indicates the functional type of this 43STA1P port."
        ::= { tn43sta1pPortInfoEntry 1 }

--------------------------------------------------------------------------------
-- 43STX4P Optical Port Info Scalar
--------------------------------------------------------------------------------
    tn43stx4pPortInfoAttributeTotal OBJECT-TYPE
        SYNTAX         Integer32
        MAX-ACCESS     read-only
        STATUS         current
        DESCRIPTION    "."
        ::= { tnOpticalPortInfo 92 }

--------------------------------------------------------------------------------
-- 43STX4P Optical Port Info Table
--------------------------------------------------------------------------------
    tn43stx4pPortInfoTable OBJECT-TYPE
        SYNTAX         SEQUENCE OF Tn43stx4pPortInfoEntry
        MAX-ACCESS     not-accessible
        STATUS         current
        DESCRIPTION    "The ports on a 43STX4P optical card."
        ::= { tnOpticalPortInfo 93 }

    tn43stx4pPortInfoEntry OBJECT-TYPE
        SYNTAX         Tn43stx4pPortInfoEntry
        MAX-ACCESS     not-accessible
        STATUS         current
        DESCRIPTION    "."
        INDEX { ifIndex }
        ::= { tn43stx4pPortInfoTable 1 }

    Tn43stx4pPortInfoEntry ::=
        SEQUENCE {
            tn43stx4pPortInfoFunction INTEGER
        }

    tn43stx4pPortInfoFunction OBJECT-TYPE
        SYNTAX         INTEGER {
                         network(1),
                         client(2)
                       }
        MAX-ACCESS     read-only
        STATUS         current
        DESCRIPTION    "Indicates the functional type of this 43STX4P port."
        ::= { tn43stx4pPortInfoEntry 1 }

--------------------------------------------------------------------------------
-- RSMON Egress Port Info Table
--------------------------------------------------------------------------------
    tnRsmonEgrPortInfoTable OBJECT-TYPE
        SYNTAX         SEQUENCE OF TnRsmonEgrPortInfoEntry
        MAX-ACCESS     not-accessible
        STATUS         current
        DESCRIPTION    "Common attributes against RSMON Egress supported ports."
        ::= { tnOpticalPortInfo 96 }

    tnRsmonEgrPortInfoEntry OBJECT-TYPE
        SYNTAX         TnRsmonEgrPortInfoEntry
        MAX-ACCESS     not-accessible
        STATUS         current
        DESCRIPTION    "."
        INDEX { ifIndex }
        ::= { tnRsmonEgrPortInfoTable 1 }

    TnRsmonEgrPortInfoEntry ::=
        SEQUENCE {
            tnRsmonEgrPortIncomingTti  OCTET STRING,
            tnRsmonEgrPortTtiStatus    AluWdmTtiStatus
        }

    tnRsmonEgrPortIncomingTti OBJECT-TYPE
        SYNTAX         OCTET STRING
        MAX-ACCESS     read-only
        STATUS         current
        DESCRIPTION    "RSMON incoming TTI."
        DEFVAL         { "" }
        ::= { tnRsmonEgrPortInfoEntry 1 }

    tnRsmonEgrPortTtiStatus OBJECT-TYPE
        SYNTAX         AluWdmTtiStatus
        MAX-ACCESS     read-only
        STATUS         current
        DESCRIPTION    "RSMON TTI status."
        DEFVAL         { unspecified }
        ::= { tnRsmonEgrPortInfoEntry 2 }

--------------------------------------------------------------------------------
-- A2325A Optical Port Info Scalar
--------------------------------------------------------------------------------
    tnA2325aPortInfoAttributeTotal OBJECT-TYPE
        SYNTAX         Integer32
        MAX-ACCESS     read-only
        STATUS         current
        DESCRIPTION    "."
        ::= { tnOpticalPortInfo 97 }

--------------------------------------------------------------------------------
-- A2325A Optical Port Info Table
--------------------------------------------------------------------------------
    tnA2325aPortInfoTable OBJECT-TYPE
        SYNTAX         SEQUENCE OF TnA2325aPortInfoEntry
        MAX-ACCESS     not-accessible
        STATUS         current
        DESCRIPTION    "The ports on an A2325A optical card."
        ::= { tnOpticalPortInfo 98 }

    tnA2325aPortInfoEntry OBJECT-TYPE
        SYNTAX         TnA2325aPortInfoEntry
        MAX-ACCESS     not-accessible
        STATUS         current
        DESCRIPTION    "."
        INDEX { ifIndex }
        ::= { tnA2325aPortInfoTable 1 }

    TnA2325aPortInfoEntry ::=
        SEQUENCE {
            tnA2325aPortInfoFunction INTEGER
        }

    tnA2325aPortInfoFunction OBJECT-TYPE
        SYNTAX         INTEGER {
                         line(1),
                         signal(2),
                         dcm(3),
                         inv(4),
                         osc(5),
                         custLan(6)
                       }
        MAX-ACCESS     read-only
        STATUS         current
        DESCRIPTION    "Indicates the functional type of this A2325A port."
        ::= { tnA2325aPortInfoEntry 1 }

--------------------------------------------------------------------------------
-- 11QPA4 Optical Port Info Scalar
--------------------------------------------------------------------------------
    tn11qpa4PortInfoAttributeTotal OBJECT-TYPE
        SYNTAX         Integer32
        MAX-ACCESS     read-only
        STATUS         current
        DESCRIPTION    "."
        ::= { tnOpticalPortInfo 99 }

--------------------------------------------------------------------------------
-- 11QPA4 Optical Port Info Table
--------------------------------------------------------------------------------
    tn11qpa4PortInfoTable OBJECT-TYPE
        SYNTAX         SEQUENCE OF Tn11qpa4PortInfoEntry
        MAX-ACCESS     not-accessible
        STATUS         current
        DESCRIPTION    "The ports on a 11QPA4 optical card."
        ::= { tnOpticalPortInfo 100 }

    tn11qpa4PortInfoEntry OBJECT-TYPE
        SYNTAX         Tn11qpa4PortInfoEntry
        MAX-ACCESS     not-accessible
        STATUS         current
        DESCRIPTION    "."
        INDEX { ifIndex }
        ::= { tn11qpa4PortInfoTable 1 }

    Tn11qpa4PortInfoEntry ::=
        SEQUENCE {
            tn11qpa4PortInfoFunction INTEGER
        }

    tn11qpa4PortInfoFunction OBJECT-TYPE
        SYNTAX         INTEGER {
                         network(1),
                         client(2),
                         evoa(3)
                       }
        MAX-ACCESS     read-only
        STATUS         current
        DESCRIPTION    "Indicates the functional type of this 11QPA4 port."
        ::= { tn11qpa4PortInfoEntry 1 }

--------------------------------------------------------------------------------
-- 112SCX10 Optical Port Info Scalar
--------------------------------------------------------------------------------
    tn112scx10PortInfoAttributeTotal OBJECT-TYPE
        SYNTAX         Integer32
        MAX-ACCESS     read-only
        STATUS         current
        DESCRIPTION    "."
        ::= { tnOpticalPortInfo 101 }

--------------------------------------------------------------------------------
-- 112SCX10 Optical Port Info Table
--------------------------------------------------------------------------------
    tn112scx10PortInfoTable OBJECT-TYPE
        SYNTAX         SEQUENCE OF Tn112scx10PortInfoEntry
        MAX-ACCESS     not-accessible
        STATUS         current
        DESCRIPTION    "The ports on a 112SCX10 optical card."
        ::= { tnOpticalPortInfo 102 }

    tn112scx10PortInfoEntry OBJECT-TYPE
        SYNTAX         Tn112scx10PortInfoEntry
        MAX-ACCESS     not-accessible
        STATUS         current
        DESCRIPTION    "."
        INDEX { ifIndex }
        ::= { tn112scx10PortInfoTable 1 }

    Tn112scx10PortInfoEntry ::=
        SEQUENCE {
            tn112scx10PortInfoFunction INTEGER
        }

    tn112scx10PortInfoFunction OBJECT-TYPE
        SYNTAX         INTEGER {
                         network(1),
                         client(2)
                       }
        MAX-ACCESS     read-only
        STATUS         current
        DESCRIPTION    "Indicates the functional type of this 112SCX10 port."
        ::= { tn112scx10PortInfoEntry 1 }

--------------------------------------------------------------------------------
-- 112SCA1 Optical Port Info Scalar
--------------------------------------------------------------------------------
    tn112sca1PortInfoAttributeTotal OBJECT-TYPE
        SYNTAX         Integer32
        MAX-ACCESS     read-only
        STATUS         current
        DESCRIPTION    "."
        ::= { tnOpticalPortInfo 103 }

--------------------------------------------------------------------------------
-- 112SCA1 Optical Port Info Table
--------------------------------------------------------------------------------
    tn112sca1PortInfoTable OBJECT-TYPE
        SYNTAX         SEQUENCE OF Tn112sca1PortInfoEntry
        MAX-ACCESS     not-accessible
        STATUS         current
        DESCRIPTION    "The ports on a 112SCA1 optical card."
        ::= { tnOpticalPortInfo 104 }

    tn112sca1PortInfoEntry OBJECT-TYPE
        SYNTAX         Tn112sca1PortInfoEntry
        MAX-ACCESS     not-accessible
        STATUS         current
        DESCRIPTION    "."
        INDEX { ifIndex }
        ::= { tn112sca1PortInfoTable 1 }

    Tn112sca1PortInfoEntry ::=
        SEQUENCE {
            tn112sca1PortInfoFunction INTEGER
        }

    tn112sca1PortInfoFunction OBJECT-TYPE
        SYNTAX         INTEGER {
                         network(1),
                         client(2)
                       }
        MAX-ACCESS     read-only
        STATUS         current
        DESCRIPTION    "Indicates the functional type of this 112SCA1 port."
        ::= { tn112sca1PortInfoEntry 1 }

--------------------------------------------------------------------------------
-- DWDM Common OTU4/ODU4 Line Port Info Table
--------------------------------------------------------------------------------
    tnDwdmCmnOtu4Odu4LinePortInfoTable OBJECT-TYPE
        SYNTAX         SEQUENCE OF TnDwdmCmnOtu4Odu4LinePortInfoEntry
        MAX-ACCESS     not-accessible
        STATUS         current
        DESCRIPTION    "Common attributes against DWDM line ports."
        ::= { tnOpticalPortInfo 105 }

    tnDwdmCmnOtu4Odu4LinePortInfoEntry OBJECT-TYPE
        SYNTAX         TnDwdmCmnOtu4Odu4LinePortInfoEntry
        MAX-ACCESS     not-accessible
        STATUS         current
        DESCRIPTION    "."
        INDEX { ifIndex }
        ::= { tnDwdmCmnOtu4Odu4LinePortInfoTable 1 }

    TnDwdmCmnOtu4Odu4LinePortInfoEntry ::=
        SEQUENCE {
            tnDwdmCmnLinePortOtu4IncomingTti             OCTET STRING,
            tnDwdmCmnLinePortOtu4TtiStatus               AluWdmTtiStatus,
            tnDwdmCmnLinePortOdu4IncomingTti             OCTET STRING,
            tnDwdmCmnLinePortOdu4TtiStatus               AluWdmTtiStatus,
            tnDwdmCmnLinePortOtu4PreFec                  Counter64,
            tnDwdmCmnLinePortOtu4PostFec                 Counter64,
            tnDwdmCmnLinePortOdu4DMInfoCurrentStatus     AluWdmDMInfoCurrentStatus,
            tnDwdmCmnLinePortOdu4DMInfoCurrentValue      Unsigned32
        }

    tnDwdmCmnLinePortOtu4IncomingTti OBJECT-TYPE
        SYNTAX         OCTET STRING
        MAX-ACCESS     read-only
        STATUS         current
        DESCRIPTION    "OTU4 incoming TTI."
        DEFVAL         { "" }
        ::= { tnDwdmCmnOtu4Odu4LinePortInfoEntry 1 }

    tnDwdmCmnLinePortOtu4TtiStatus OBJECT-TYPE
        SYNTAX         AluWdmTtiStatus
        MAX-ACCESS     read-only
        STATUS         current
        DESCRIPTION    "OTU4 TTI status."
        DEFVAL         { unspecified }
        ::= { tnDwdmCmnOtu4Odu4LinePortInfoEntry 2 }

    tnDwdmCmnLinePortOdu4IncomingTti OBJECT-TYPE
        SYNTAX         OCTET STRING
        MAX-ACCESS     read-only
        STATUS         current
        DESCRIPTION    "ODU4 incoming TTI."
        DEFVAL         { "" }
        ::= { tnDwdmCmnOtu4Odu4LinePortInfoEntry 3 }

    tnDwdmCmnLinePortOdu4TtiStatus OBJECT-TYPE
        SYNTAX         AluWdmTtiStatus
        MAX-ACCESS     read-only
        STATUS         current
        DESCRIPTION    "ODU4 TTI status."
        DEFVAL         { unspecified }
        ::= { tnDwdmCmnOtu4Odu4LinePortInfoEntry 4 }

    tnDwdmCmnLinePortOtu4PreFec OBJECT-TYPE
        SYNTAX         Counter64
        MAX-ACCESS     read-only
        STATUS         current
        DESCRIPTION    "Real time error bit rate of pre-FEC (Forward
                        Error Correction).

                        Current configurable range: 0 to 4000."
        ::= { tnDwdmCmnOtu4Odu4LinePortInfoEntry 5 }

    tnDwdmCmnLinePortOtu4PostFec OBJECT-TYPE
        SYNTAX         Counter64
        MAX-ACCESS     read-only
        STATUS         current
        DESCRIPTION    "Real time error bit rate of post-FEC (Forward
                        Error Correction).

                        Current configurable range: 0 to 4000."
        ::= { tnDwdmCmnOtu4Odu4LinePortInfoEntry 6 }

    tnDwdmCmnLinePortOdu4DMInfoCurrentStatus OBJECT-TYPE
        SYNTAX         AluWdmDMInfoCurrentStatus
        MAX-ACCESS     read-only
        STATUS         current
        DESCRIPTION    "Indicates whether this DM test is valid."
        DEFVAL         { invalid }
        ::= { tnDwdmCmnOtu4Odu4LinePortInfoEntry 7 }

    tnDwdmCmnLinePortOdu4DMInfoCurrentValue OBJECT-TYPE
        SYNTAX         Unsigned32
        MAX-ACCESS     read-only
        STATUS         current
        DESCRIPTION    "Reports the DM value in 10**(-7) seconds in the
                        current Interval."
        DEFVAL         { 0 }
        ::= { tnDwdmCmnOtu4Odu4LinePortInfoEntry 8 }

--------------------------------------------------------------------------------
-- DWDM Common OTU4/ODU4 Client Port Info Table
--------------------------------------------------------------------------------
    tnDwdmCmnOtu4Odu4ClientPortInfoTable OBJECT-TYPE
        SYNTAX         SEQUENCE OF TnDwdmCmnOtu4Odu4ClientPortInfoEntry
        MAX-ACCESS     not-accessible
        STATUS         current
        DESCRIPTION    "Common attributes against DWDM client ports."
        ::= { tnOpticalPortInfo 106 }

    tnDwdmCmnOtu4Odu4ClientPortInfoEntry OBJECT-TYPE
        SYNTAX         TnDwdmCmnOtu4Odu4ClientPortInfoEntry
        MAX-ACCESS     not-accessible
        STATUS         current
        DESCRIPTION    "."
        INDEX { ifIndex }
        ::= { tnDwdmCmnOtu4Odu4ClientPortInfoTable 1 }

    TnDwdmCmnOtu4Odu4ClientPortInfoEntry ::=
        SEQUENCE {
            tnDwdmCmnClientPortOtu4IncomingTti  OCTET STRING,
            tnDwdmCmnClientPortOtu4TtiStatus    AluWdmTtiStatus,
            tnDwdmCmnClientPortOdu4IncomingTti  OCTET STRING,
            tnDwdmCmnClientPortOdu4TtiStatus    AluWdmTtiStatus,
            tnDwdmCmnClientPortOtu4PreFec       Counter64,
            tnDwdmCmnClientPortOtu4PostFec      Counter64
        }

    tnDwdmCmnClientPortOtu4IncomingTti OBJECT-TYPE
        SYNTAX         OCTET STRING
        MAX-ACCESS     read-only
        STATUS         current
        DESCRIPTION    "OTU4 incoming TTI."
        DEFVAL         { "" }
        ::= { tnDwdmCmnOtu4Odu4ClientPortInfoEntry 1 }

    tnDwdmCmnClientPortOtu4TtiStatus OBJECT-TYPE
        SYNTAX         AluWdmTtiStatus
        MAX-ACCESS     read-only
        STATUS         current
        DESCRIPTION    "OTU4 TTI status."
        DEFVAL         { unspecified }
        ::= { tnDwdmCmnOtu4Odu4ClientPortInfoEntry 2 }

    tnDwdmCmnClientPortOdu4IncomingTti OBJECT-TYPE
        SYNTAX         OCTET STRING
        MAX-ACCESS     read-only
        STATUS         current
        DESCRIPTION    "ODU4 incoming TTI."
        DEFVAL         { "" }
        ::= { tnDwdmCmnOtu4Odu4ClientPortInfoEntry 3 }

    tnDwdmCmnClientPortOdu4TtiStatus OBJECT-TYPE
        SYNTAX         AluWdmTtiStatus
        MAX-ACCESS     read-only
        STATUS         current
        DESCRIPTION    "ODU4 TTI status."
        DEFVAL         { unspecified }
        ::= { tnDwdmCmnOtu4Odu4ClientPortInfoEntry 4 }

    tnDwdmCmnClientPortOtu4PreFec OBJECT-TYPE
        SYNTAX         Counter64
        MAX-ACCESS     read-only
        STATUS         current
        DESCRIPTION    "Real time error bit rate of pre-FEC (Forward
                        Error Correction).

                        Current configurable range: 0 to 4000."
        ::= { tnDwdmCmnOtu4Odu4ClientPortInfoEntry 5 }

    tnDwdmCmnClientPortOtu4PostFec OBJECT-TYPE
        SYNTAX         Counter64
        MAX-ACCESS     read-only
        STATUS         current
        DESCRIPTION    "Real time error bit rate of post-FEC (Forward
                        Error Correction).

                        Current configurable range: 0 to 4000."
        ::= { tnDwdmCmnOtu4Odu4ClientPortInfoEntry 6 }

--------------------------------------------------------------------------------
-- ALPFGT Optical Port Info Scalar
--------------------------------------------------------------------------------
    tnAlpfgtPortInfoAttributeTotal OBJECT-TYPE
        SYNTAX         Integer32
        MAX-ACCESS     read-only
        STATUS         current
        DESCRIPTION    "."
        ::= { tnOpticalPortInfo 107 }

--------------------------------------------------------------------------------
-- ALPFGT Optical Port Info Table
--------------------------------------------------------------------------------
    tnAlpfgtPortInfoTable OBJECT-TYPE
        SYNTAX         SEQUENCE OF TnAlpfgtPortInfoEntry
        MAX-ACCESS     not-accessible
        STATUS         current
        DESCRIPTION    "The ports on an ALPFGT optical card."
        ::= { tnOpticalPortInfo 108 }

    tnAlpfgtPortInfoEntry OBJECT-TYPE
        SYNTAX         TnAlpfgtPortInfoEntry
        MAX-ACCESS     not-accessible
        STATUS         current
        DESCRIPTION    "."
        INDEX { ifIndex }
        ::= { tnAlpfgtPortInfoTable 1 }

    TnAlpfgtPortInfoEntry ::=
        SEQUENCE {
            tnAlpfgtPortInfoFunction  INTEGER
        }

    tnAlpfgtPortInfoFunction OBJECT-TYPE
        SYNTAX         INTEGER {
                         line(1),
                         signal(2),
                         inv(3),
                         osc(4),
                         oscSfp(5)
                       }
        MAX-ACCESS     read-only
        STATUS         current
        DESCRIPTION    "Indicates the functional type of this ALPFGT port."
        ::= { tnAlpfgtPortInfoEntry 1 }

--------------------------------------------------------------------------------
-- OSCT Optical Port Info Scalar
--------------------------------------------------------------------------------
    tnOsctPortInfoAttributeTotal OBJECT-TYPE
        SYNTAX         Integer32
        MAX-ACCESS     read-only
        STATUS         current
        DESCRIPTION    "."
        ::= { tnOpticalPortInfo 109 }

--------------------------------------------------------------------------------
-- OSCT Optical Port Info Table
--------------------------------------------------------------------------------
    tnOsctPortInfoTable OBJECT-TYPE
        SYNTAX         SEQUENCE OF TnOsctPortInfoEntry
        MAX-ACCESS     not-accessible
        STATUS         current
        DESCRIPTION    "The ports on an OSCT optical card."
        ::= { tnOpticalPortInfo 110 }

    tnOsctPortInfoEntry OBJECT-TYPE
        SYNTAX         TnOsctPortInfoEntry
        MAX-ACCESS     not-accessible
        STATUS         current
        DESCRIPTION    "."
        INDEX { ifIndex }
        ::= { tnOsctPortInfoTable 1 }

    TnOsctPortInfoEntry ::=
        SEQUENCE {
            tnOsctPortInfoFunction     INTEGER
        }

    tnOsctPortInfoFunction OBJECT-TYPE
        SYNTAX         INTEGER {
                         signal(1),
                         line(2),
                         inv(3),
                         osc(4),
                         oscSfp(5)
                       }
        MAX-ACCESS     read-only
        STATUS         current
        DESCRIPTION    "Indicates the functional type of this OSCT port."
        ::= { tnOsctPortInfoEntry 1 }

--------------------------------------------------------------------------------
-- WTOCM Optical Port Info Scalar
--------------------------------------------------------------------------------
    tnWtocmPortInfoAttributeTotal OBJECT-TYPE
        SYNTAX         Integer32
        MAX-ACCESS     read-only
        STATUS         current
        DESCRIPTION    "."
        ::= { tnOpticalPortInfo 111 }

--------------------------------------------------------------------------------
-- WTOCM Optical Port Info Table
--------------------------------------------------------------------------------
    tnWtocmPortInfoTable OBJECT-TYPE
        SYNTAX         SEQUENCE OF TnWtocmPortInfoEntry
        MAX-ACCESS     not-accessible
        STATUS         current
        DESCRIPTION    "The ports on a WTOCM optical card."
        ::= { tnOpticalPortInfo 112 }

    tnWtocmPortInfoEntry OBJECT-TYPE
        SYNTAX         TnWtocmPortInfoEntry
        MAX-ACCESS     not-accessible
        STATUS         current
        DESCRIPTION    "."
        INDEX { ifIndex }
        ::= { tnWtocmPortInfoTable 1 }

    TnWtocmPortInfoEntry ::=
        SEQUENCE {
            tnWtocmPortInfoFunction            INTEGER,
            tnWtocmPortInfoPower               Integer32,
            tnWtocmPortInfoPowerMonitoredPort  Integer32
        }

    tnWtocmPortInfoFunction OBJECT-TYPE
        SYNTAX         INTEGER {
                         detect(1)
                       }
        MAX-ACCESS     read-only
        STATUS         current
        DESCRIPTION    "Indicates the functional type of this WTOCM port."
        ::= { tnWtocmPortInfoEntry 1 }

    tnWtocmPortInfoPower OBJECT-TYPE
        SYNTAX         Integer32
        UNITS          "mBm"
        MAX-ACCESS     read-only
        STATUS         current
        DESCRIPTION    "The total power into the WTOCM IN port."
        DEFVAL         { -9900 }
        ::= { tnWtocmPortInfoEntry 2 }

    tnWtocmPortInfoPowerMonitoredPort OBJECT-TYPE
        SYNTAX         Integer32
        UNITS          "mBm"
        MAX-ACCESS     read-only
        STATUS         current
        DESCRIPTION    "The total power out of associated monitored port."
        DEFVAL         { -9900 }
        ::= { tnWtocmPortInfoEntry 3 }

--------------------------------------------------------------------------------
-- WR2-88 Optical Port Info Scalar
--------------------------------------------------------------------------------
    tnWr2c88PortInfoAttributeTotal OBJECT-TYPE
        SYNTAX         Integer32
        MAX-ACCESS     read-only
        STATUS         current
        DESCRIPTION    "."
        ::= { tnOpticalPortInfo 113 }

--------------------------------------------------------------------------------
-- WR2-88 Optical Port Info Table
--------------------------------------------------------------------------------
    tnWr2c88PortInfoTable OBJECT-TYPE
        SYNTAX         SEQUENCE OF TnWr2c88PortInfoEntry
        MAX-ACCESS     not-accessible
        STATUS         current
        DESCRIPTION    "The ports on a WR2-88 optical card."
        ::= { tnOpticalPortInfo 114 }

    tnWr2c88PortInfoEntry OBJECT-TYPE
        SYNTAX         TnWr2c88PortInfoEntry
        MAX-ACCESS     not-accessible
        STATUS         current
        DESCRIPTION    "."
        INDEX { ifIndex }
        ::= { tnWr2c88PortInfoTable 1 }

    TnWr2c88PortInfoEntry ::=
        SEQUENCE {
            tnWr2c88PortInfoFunction            INTEGER,
            tnWr2c88PortRelativeAttenuationMin  Unsigned32,
            tnWr2c88PortAverageAttenuationOut   Unsigned32
        }

    tnWr2c88PortInfoFunction OBJECT-TYPE
        SYNTAX         INTEGER {
                         signal(1),
                         thru(2),
                         dropOut(3),
                         addIn(4),
                         inv(5)
                       }
        MAX-ACCESS     read-only
        STATUS         current
        DESCRIPTION    "Indicates the functional type of this WR2-88 port."
        ::= { tnWr2c88PortInfoEntry 1 }

    tnWr2c88PortRelativeAttenuationMin OBJECT-TYPE
        SYNTAX         Unsigned32
        UNITS          "mB"
        MAX-ACCESS     read-only
        STATUS         current
        DESCRIPTION    "The following description applies to the Thru
                        port of the WR2-88 card:

                        The minimum attenuation on the blocker across
                        all of the channels."
        DEFVAL         { 0 }
        ::= { tnWr2c88PortInfoEntry 2 }

    tnWr2c88PortAverageAttenuationOut OBJECT-TYPE
        SYNTAX         Unsigned32
        UNITS          "mB"
        MAX-ACCESS     read-only
        STATUS         current
        DESCRIPTION    "The following description applies to the Thru
                        port of the WR2-88 card:

                        The average attenuation on the blocker across
                        all of the channels."
        ::= { tnWr2c88PortInfoEntry 3 }

--------------------------------------------------------------------------------
-- AM2017B Optical Port Info Scalar
--------------------------------------------------------------------------------
    tnAm2017bPortInfoAttributeTotal OBJECT-TYPE
        SYNTAX         Integer32
        MAX-ACCESS     read-only
        STATUS         current
        DESCRIPTION    "."
        ::= { tnOpticalPortInfo 115 }

--------------------------------------------------------------------------------
-- AM2017B Optical Port Info Table
--------------------------------------------------------------------------------
    tnAm2017bPortInfoTable OBJECT-TYPE
        SYNTAX         SEQUENCE OF TnAm2017bPortInfoEntry
        MAX-ACCESS     not-accessible
        STATUS         current
        DESCRIPTION    "The ports on an AM2017B optical card."
        ::= { tnOpticalPortInfo 116 }

    tnAm2017bPortInfoEntry OBJECT-TYPE
        SYNTAX         TnAm2017bPortInfoEntry
        MAX-ACCESS     not-accessible
        STATUS         current
        DESCRIPTION    "."
        INDEX { ifIndex }
        ::= { tnAm2017bPortInfoTable 1 }

    TnAm2017bPortInfoEntry ::=
        SEQUENCE {
            tnAm2017bPortInfoFunction INTEGER
        }

    tnAm2017bPortInfoFunction OBJECT-TYPE
        SYNTAX         INTEGER {
                         line(1),
                         signal(2),
                         dcm(3),
                         inv(4),
                         osc(5)
--                         obsolete
--                         custLan(6)
                       }
        MAX-ACCESS     read-only
        STATUS         current
        DESCRIPTION    "Indicates the functional type of this AM2017B port."
        ::= { tnAm2017bPortInfoEntry 1 }

--------------------------------------------------------------------------------
-- AM2325B Optical Port Info Scalar
--------------------------------------------------------------------------------
    tnAm2325bPortInfoAttributeTotal OBJECT-TYPE
        SYNTAX         Integer32
        MAX-ACCESS     read-only
        STATUS         current
        DESCRIPTION    "."
        ::= { tnOpticalPortInfo 117 }

--------------------------------------------------------------------------------
-- AM2325B Optical Port Info Table
--------------------------------------------------------------------------------
    tnAm2325bPortInfoTable OBJECT-TYPE
        SYNTAX         SEQUENCE OF TnAm2325bPortInfoEntry
        MAX-ACCESS     not-accessible
        STATUS         current
        DESCRIPTION    "The ports on an AM2325B optical card."
        ::= { tnOpticalPortInfo 118 }

    tnAm2325bPortInfoEntry OBJECT-TYPE
        SYNTAX         TnAm2325bPortInfoEntry
        MAX-ACCESS     not-accessible
        STATUS         current
        DESCRIPTION    "."
        INDEX { ifIndex }
        ::= { tnAm2325bPortInfoTable 1 }

    TnAm2325bPortInfoEntry ::=
        SEQUENCE {
            tnAm2325bPortInfoFunction INTEGER
        }

    tnAm2325bPortInfoFunction OBJECT-TYPE
        SYNTAX         INTEGER {
                         line(1),
                         signal(2),
                         dcm(3),
                         inv(4),
                         osc(5)
--                         obsolete
--                         custLan(6)
                       }
        MAX-ACCESS     read-only
        STATUS         current
        DESCRIPTION    "Indicates the functional type of this AM2325B port."
        ::= { tnAm2325bPortInfoEntry 1 }

--------------------------------------------------------------------------------
-- 1DPP21 Optical Port Info Scalar
--------------------------------------------------------------------------------
    tn1dpp21PortInfoAttributeTotal OBJECT-TYPE
        SYNTAX         Integer32
        MAX-ACCESS     read-only
        STATUS         current
        DESCRIPTION    "."
        ::= { tnOpticalPortInfo 119 }

--------------------------------------------------------------------------------
-- 1DPP21 Optical Port Info Table
--------------------------------------------------------------------------------
    tn1dpp21PortInfoTable OBJECT-TYPE
        SYNTAX         SEQUENCE OF Tn1dpp21PortInfoEntry
        MAX-ACCESS     not-accessible
        STATUS         current
        DESCRIPTION    "The ports on a 1DPP21 optical card."
        ::= { tnOpticalPortInfo 120 }

    tn1dpp21PortInfoEntry OBJECT-TYPE
        SYNTAX         Tn1dpp21PortInfoEntry
        MAX-ACCESS     not-accessible
        STATUS         current
        DESCRIPTION    "."
        INDEX { ifIndex }
        ::= { tn1dpp21PortInfoTable 1 }

    Tn1dpp21PortInfoEntry ::=
        SEQUENCE {
            tn1dpp21PortInfoFunction                 INTEGER,
            tn1dpp21PortClockSourceIncomingQLStatus  Unsigned32,
            tn1dpp21PortClockSourceIncomingQL        Unsigned32
        }

    tn1dpp21PortInfoFunction OBJECT-TYPE
        SYNTAX         INTEGER {
                         network(1),
                         client(2)
                       }
        MAX-ACCESS     read-only
        STATUS         current
        DESCRIPTION    "Indicates the functional type of this 1DPP21 port."
        ::= { tn1dpp21PortInfoEntry 1 }

    tn1dpp21PortClockSourceIncomingQLStatus OBJECT-TYPE
        SYNTAX         Unsigned32
        MAX-ACCESS     read-only
        STATUS         current
        DESCRIPTION    "This object indicates the current status of
                        incoming QL on that port.
                          0: Valid
                          1: Invalid
                          2: Not Supported
                          3: Not Applicable

                        It's only applicable to the timing port with
                        SSM capabilities."
        DEFVAL         { 3 }
        ::= { tn1dpp21PortInfoEntry 2 }

    tn1dpp21PortClockSourceIncomingQL OBJECT-TYPE
        SYNTAX         Unsigned32
        MAX-ACCESS     read-only
        STATUS         current
        DESCRIPTION    "This object indicates the current value of
                        incoming QL on that port.
                          0:  Quality Unknown
                          1:  PRC
                          2:  SSU_A
                          3:  SSU_B
                          4:  EEC Option 1
                          5:  DNU
                          11: PRS
                          12: STU
                          13: ST2
                          14: TNC
                          15: ST3E
                          16: ST3
                          17: SMC
                          18: ST4
                          19: DUS
                          20: PNO
                          30: Unstable
                          31: Not applicable

                        It's only applicable to the timing port
                        with SSM capabilities."
        ::= { tn1dpp21PortInfoEntry 3 }

--    obsolete
--    tnE1T1PortInfoTable OBJECT-TYPE ::= { tnOpticalPortInfo 121 }

--------------------------------------------------------------------------------
-- MVAC Optical Port Info Scalar
--------------------------------------------------------------------------------
    tnMvacPortInfoAttributeTotal OBJECT-TYPE
        SYNTAX         Integer32
        MAX-ACCESS     read-only
        STATUS         current
        DESCRIPTION    "."
        ::= { tnOpticalPortInfo 122 }

--------------------------------------------------------------------------------
-- MVAC Optical Port Info Table
--------------------------------------------------------------------------------
    tnMvacPortInfoTable OBJECT-TYPE
        SYNTAX         SEQUENCE OF TnMvacPortInfoEntry
        MAX-ACCESS     not-accessible
        STATUS         current
        DESCRIPTION    "The ports on a MVAC optical card."
        ::= { tnOpticalPortInfo 123 }

    tnMvacPortInfoEntry OBJECT-TYPE
        SYNTAX         TnMvacPortInfoEntry
        MAX-ACCESS     not-accessible
        STATUS         current
        DESCRIPTION    "."
        INDEX { ifIndex }
        ::= { tnMvacPortInfoTable 1 }

    TnMvacPortInfoEntry ::=
        SEQUENCE {
            tnMvacPortInfoFunction INTEGER
        }

    tnMvacPortInfoFunction OBJECT-TYPE
        SYNTAX         INTEGER {
                         general(1)
                       }
        MAX-ACCESS     read-only
        STATUS         current
        DESCRIPTION    "Indicates the functional type of this MVAC port."
        ::= { tnMvacPortInfoEntry 1 }

--------------------------------------------------------------------------------
-- 43SCX4 Optical Port Info Scalar
--------------------------------------------------------------------------------
    tn43scx4PortInfoAttributeTotal OBJECT-TYPE
        SYNTAX         Integer32
        MAX-ACCESS     read-only
        STATUS         current
        DESCRIPTION    "."
        ::= { tnOpticalPortInfo 126 }

--------------------------------------------------------------------------------
-- 43SCX4 Optical Port Info Table
--------------------------------------------------------------------------------
    tn43scx4PortInfoTable OBJECT-TYPE
        SYNTAX         SEQUENCE OF Tn43scx4PortInfoEntry
        MAX-ACCESS     not-accessible
        STATUS         current
        DESCRIPTION    "The ports on a 43SCX4 optical card."
        ::= { tnOpticalPortInfo 127 }

    tn43scx4PortInfoEntry OBJECT-TYPE
        SYNTAX         Tn43scx4PortInfoEntry
        MAX-ACCESS     not-accessible
        STATUS         current
        DESCRIPTION    "."
        INDEX { ifIndex }
        ::= { tn43scx4PortInfoTable 1 }

    Tn43scx4PortInfoEntry ::=
        SEQUENCE {
            tn43scx4PortInfoFunction INTEGER
        }

    tn43scx4PortInfoFunction OBJECT-TYPE
        SYNTAX         INTEGER {
                         network(1),
                         client(2)
                       }
        MAX-ACCESS     read-only
        STATUS         current
        DESCRIPTION    "Indicates the functional type of this 43SCX4 port."
        ::= { tn43scx4PortInfoEntry 1 }

--------------------------------------------------------------------------------
-- RA2P Optical Port Info Scalar
--------------------------------------------------------------------------------
    tnRa2pPortInfoAttributeTotal OBJECT-TYPE
        SYNTAX         Integer32
        MAX-ACCESS     read-only
        STATUS         current
        DESCRIPTION    "."
        ::= { tnOpticalPortInfo 128 }

--------------------------------------------------------------------------------
-- RA2P Optical Port Info Table
--------------------------------------------------------------------------------
    tnRa2pPortInfoTable OBJECT-TYPE
        SYNTAX         SEQUENCE OF TnRa2pPortInfoEntry
        MAX-ACCESS     not-accessible
        STATUS         current
        DESCRIPTION    "The ports on a RA2P optical card."
        ::= { tnOpticalPortInfo 129 }

    tnRa2pPortInfoEntry OBJECT-TYPE
        SYNTAX         TnRa2pPortInfoEntry
        MAX-ACCESS     not-accessible
        STATUS         current
        DESCRIPTION    "."
        INDEX { ifIndex }
        ::= { tnRa2pPortInfoTable 1 }

    TnRa2pPortInfoEntry ::=
        SEQUENCE {
            tnRa2pPortInfoFunction INTEGER
        }

    tnRa2pPortInfoFunction OBJECT-TYPE
        SYNTAX         INTEGER {
                         lineIn(1),
                         lineOut(2)
                       }
        MAX-ACCESS     read-only
        STATUS         current
        DESCRIPTION    "Indicates the functional type of this RA2P port."
        ::= { tnRa2pPortInfoEntry 1 }

--------------------------------------------------------------------------------
-- AM2318A Optical Port Info Scalar
--------------------------------------------------------------------------------
    tnAm2318aPortInfoAttributeTotal OBJECT-TYPE
        SYNTAX         Integer32
        MAX-ACCESS     read-only
        STATUS         current
        DESCRIPTION    "."
        ::= { tnOpticalPortInfo 130 }

--------------------------------------------------------------------------------
-- AM2318A Optical Port Info Table
--------------------------------------------------------------------------------
    tnAm2318aPortInfoTable OBJECT-TYPE
        SYNTAX         SEQUENCE OF TnAm2318aPortInfoEntry
        MAX-ACCESS     not-accessible
        STATUS         current
        DESCRIPTION    "The ports on an AM2318A optical card."
        ::= { tnOpticalPortInfo 131 }

    tnAm2318aPortInfoEntry OBJECT-TYPE
        SYNTAX         TnAm2318aPortInfoEntry
        MAX-ACCESS     not-accessible
        STATUS         current
        DESCRIPTION    "."
        INDEX { ifIndex }
        ::= { tnAm2318aPortInfoTable 1 }

    TnAm2318aPortInfoEntry ::=
        SEQUENCE {
            tnAm2318aPortInfoFunction INTEGER
        }

    tnAm2318aPortInfoFunction OBJECT-TYPE
        SYNTAX         INTEGER {
                         lineIn(1),
                         inv(2),
                         osc(3),
                         lineOut(4),
                         oscSfp(5),
                         det(6),
                         custLan(7)
                       }
        MAX-ACCESS     read-only
        STATUS         current
        DESCRIPTION    "Indicates the functional type of this AM2318A port."
        ::= { tnAm2318aPortInfoEntry 1 }

--------------------------------------------------------------------------------
-- AM2125A Optical Port Info Scalar
--------------------------------------------------------------------------------
    tnAm2125aPortInfoAttributeTotal OBJECT-TYPE
        SYNTAX         Integer32
        MAX-ACCESS     read-only
        STATUS         current
        DESCRIPTION    "."
        ::= { tnOpticalPortInfo 132 }

--------------------------------------------------------------------------------
-- AM2125A Optical Port Info Table
--------------------------------------------------------------------------------
    tnAm2125aPortInfoTable OBJECT-TYPE
        SYNTAX         SEQUENCE OF TnAm2125aPortInfoEntry
        MAX-ACCESS     not-accessible
        STATUS         current
        DESCRIPTION    "The ports on an AM2125A optical card."
        ::= { tnOpticalPortInfo 133 }

    tnAm2125aPortInfoEntry OBJECT-TYPE
        SYNTAX         TnAm2125aPortInfoEntry
        MAX-ACCESS     not-accessible
        STATUS         current
        DESCRIPTION    "."
        INDEX { ifIndex }
        ::= { tnAm2125aPortInfoTable 1 }

    TnAm2125aPortInfoEntry ::=
        SEQUENCE {
            tnAm2125aPortInfoFunction INTEGER
        }

    tnAm2125aPortInfoFunction OBJECT-TYPE
        SYNTAX         INTEGER {
                         lineIn(1),
                         inv(2),
                         dcm(3),
                         lineOut(4),
                         oscSfp(5),
                         det(6),
                         osc(7),
                         custLan(8)
                       }
        MAX-ACCESS     read-only
        STATUS         current
        DESCRIPTION    "Indicates the functional type of this AM2125A port."
        ::= { tnAm2125aPortInfoEntry 1 }

--------------------------------------------------------------------------------
-- WR8-88A Optical Port Info Scalar
--------------------------------------------------------------------------------
    tnWr8c88aPortInfoAttributeTotal OBJECT-TYPE
        SYNTAX         Integer32
        MAX-ACCESS     read-only
        STATUS         current
        DESCRIPTION    "."
        ::= { tnOpticalPortInfo 134 }

--------------------------------------------------------------------------------
-- WR8-88A Optical Port Info Table
--------------------------------------------------------------------------------
    tnWr8c88aPortInfoTable OBJECT-TYPE
        SYNTAX         SEQUENCE OF TnWr8c88aPortInfoEntry
        MAX-ACCESS     not-accessible
        STATUS         current
        DESCRIPTION    "The ports on a WR8-88A optical card."
        ::= { tnOpticalPortInfo 135 }

    tnWr8c88aPortInfoEntry OBJECT-TYPE
        SYNTAX         TnWr8c88aPortInfoEntry
        MAX-ACCESS     not-accessible
        STATUS         current
        DESCRIPTION    "."
        INDEX { ifIndex }
        ::= { tnWr8c88aPortInfoTable 1 }

    TnWr8c88aPortInfoEntry ::=
        SEQUENCE {
            tnWr8c88aPortInfoFunction     INTEGER
        }

    tnWr8c88aPortInfoFunction OBJECT-TYPE
        SYNTAX         INTEGER {
                         signal(1),
                         thru(2),
                         dropOut(3),
                         addIn(4),
--                       obsolete
--                         test(5),
                         meshOut(5),
                         inv(6)
                       }
        MAX-ACCESS     read-only
        STATUS         current
        DESCRIPTION    "Indicates the functional type of this WR8-88A port."
        ::= { tnWr8c88aPortInfoEntry 1 }

--------------------------------------------------------------------------------
-- 11DPE12E Optical Port Info Scalar
--------------------------------------------------------------------------------
    tn11dpe12ePortInfoAttributeTotal OBJECT-TYPE
        SYNTAX         Integer32
        MAX-ACCESS     read-only
        STATUS         current
        DESCRIPTION    "."
        ::= { tnOpticalPortInfo 136 }

--------------------------------------------------------------------------------
-- 11DPE12E Optical Port Info Table
--------------------------------------------------------------------------------
    tn11dpe12ePortInfoTable OBJECT-TYPE
        SYNTAX         SEQUENCE OF Tn11dpe12ePortInfoEntry
        MAX-ACCESS     not-accessible
        STATUS         current
        DESCRIPTION    "The ports on a 11DPE12E optical card."
        ::= { tnOpticalPortInfo 137 }

    tn11dpe12ePortInfoEntry OBJECT-TYPE
        SYNTAX         Tn11dpe12ePortInfoEntry
        MAX-ACCESS     not-accessible
        STATUS         current
        DESCRIPTION    "."
        INDEX { ifIndex }
        ::= { tn11dpe12ePortInfoTable 1 }

    Tn11dpe12ePortInfoEntry ::=
        SEQUENCE {
            tn11dpe12ePortInfoFunction           INTEGER,
            tn11dpe12ePortTotalVTS               Unsigned32,
            tn11dpe12ePortIngAvailableBandwidth  Unsigned32,
            tn11dpe12ePortEgrAvailableBandwidth  Unsigned32
        }

    tn11dpe12ePortInfoFunction OBJECT-TYPE
        SYNTAX         INTEGER {
                         network(1),
                         client(2),
                         evoa(3),
                         backplane(4)
                       }
        MAX-ACCESS     read-only
        STATUS         current
        DESCRIPTION    "Indicates the functional type of this 11DPE12E port."
        ::= { tn11dpe12ePortInfoEntry 1 }

    tn11dpe12ePortTotalVTS OBJECT-TYPE
        SYNTAX         Unsigned32
        MAX-ACCESS     read-only
        STATUS         current
        DESCRIPTION    "Total VTS for 11DPE12E ports."
        DEFVAL         { 0 }
        ::= { tn11dpe12ePortInfoEntry 2 }

    tn11dpe12ePortIngAvailableBandwidth OBJECT-TYPE
        SYNTAX         Unsigned32
        MAX-ACCESS     read-only
        STATUS         current
        DESCRIPTION    "Available bandwidth for ingress 11DPE12E ports."
        ::= { tn11dpe12ePortInfoEntry 3 }

    tn11dpe12ePortEgrAvailableBandwidth OBJECT-TYPE
        SYNTAX         Unsigned32
        MAX-ACCESS     read-only
        STATUS         current
        DESCRIPTION    "Available bandwidth for egress 11DPE12E ports."
        ::= { tn11dpe12ePortInfoEntry 4 }

--------------------------------------------------------------------------------
-- 112SX10L Optical Port Info Scalar
--------------------------------------------------------------------------------
    tn112sx10lPortInfoAttributeTotal OBJECT-TYPE
        SYNTAX         Integer32
        MAX-ACCESS     read-only
        STATUS         current
        DESCRIPTION    "."
        ::= { tnOpticalPortInfo 138 }

--------------------------------------------------------------------------------
-- 112SX10L Optical Port Info Table
--------------------------------------------------------------------------------
    tn112sx10lPortInfoTable OBJECT-TYPE
        SYNTAX         SEQUENCE OF Tn112sx10lPortInfoEntry
        MAX-ACCESS     not-accessible
        STATUS         current
        DESCRIPTION    "The ports on a 112SX10L optical card."
        ::= { tnOpticalPortInfo 139 }

    tn112sx10lPortInfoEntry OBJECT-TYPE
        SYNTAX         Tn112sx10lPortInfoEntry
        MAX-ACCESS     not-accessible
        STATUS         current
        DESCRIPTION    "."
        INDEX { ifIndex }
        ::= { tn112sx10lPortInfoTable 1 }

    Tn112sx10lPortInfoEntry ::=
        SEQUENCE {
            tn112sx10lPortInfoFunction INTEGER
        }

    tn112sx10lPortInfoFunction OBJECT-TYPE
        SYNTAX         INTEGER {
                         network(1),
                         client(2)
                       }
        MAX-ACCESS     read-only
        STATUS         current
        DESCRIPTION    "Indicates the functional type of this 112SX10L port."
        ::= { tn112sx10lPortInfoEntry 1 }

--------------------------------------------------------------------------------
-- 112SA1L Optical Port Info Scalar
--------------------------------------------------------------------------------
    tn112sa1lPortInfoAttributeTotal OBJECT-TYPE
        SYNTAX         Integer32
        MAX-ACCESS     read-only
        STATUS         current
        DESCRIPTION    "."
        ::= { tnOpticalPortInfo 140 }

--------------------------------------------------------------------------------
-- 112SA1L Optical Port Info Table
--------------------------------------------------------------------------------
    tn112sa1lPortInfoTable OBJECT-TYPE
        SYNTAX         SEQUENCE OF Tn112sa1lPortInfoEntry
        MAX-ACCESS     not-accessible
        STATUS         current
        DESCRIPTION    "The ports on a 112SA1L optical card."
        ::= { tnOpticalPortInfo 141 }

    tn112sa1lPortInfoEntry OBJECT-TYPE
        SYNTAX         Tn112sa1lPortInfoEntry
        MAX-ACCESS     not-accessible
        STATUS         current
        DESCRIPTION    "."
        INDEX { ifIndex }
        ::= { tn112sa1lPortInfoTable 1 }

    Tn112sa1lPortInfoEntry ::=
        SEQUENCE {
            tn112sa1lPortInfoFunction INTEGER
        }

    tn112sa1lPortInfoFunction OBJECT-TYPE
        SYNTAX         INTEGER {
                         network(1),
                         client(2)
                       }
        MAX-ACCESS     read-only
        STATUS         current
        DESCRIPTION    "Indicates the functional type of this 112SA1L port."
        ::= { tn112sa1lPortInfoEntry 1 }

--------------------------------------------------------------------------------
-- 11DPM12 Optical Port Info Scalar
--------------------------------------------------------------------------------
    tn11dpm12PortInfoAttributeTotal OBJECT-TYPE
        SYNTAX         Integer32
        MAX-ACCESS     read-only
        STATUS         current
        DESCRIPTION    "."
        ::= { tnOpticalPortInfo 142 }

--------------------------------------------------------------------------------
-- 11DPGM12 Optical Port Info Table
--------------------------------------------------------------------------------
    tn11dpm12PortInfoTable OBJECT-TYPE
        SYNTAX         SEQUENCE OF Tn11dpm12PortInfoEntry
        MAX-ACCESS     not-accessible
        STATUS         current
        DESCRIPTION    "The ports on a 11DPM12 optical card."
        ::= { tnOpticalPortInfo 143 }

    tn11dpm12PortInfoEntry OBJECT-TYPE
        SYNTAX         Tn11dpm12PortInfoEntry
        MAX-ACCESS     not-accessible
        STATUS         current
        DESCRIPTION    "."
        INDEX { ifIndex }
        ::= { tn11dpm12PortInfoTable 1 }

    Tn11dpm12PortInfoEntry ::=
        SEQUENCE {
            tn11dpm12PortInfoFunction     INTEGER
        }

    tn11dpm12PortInfoFunction OBJECT-TYPE
        SYNTAX         INTEGER {
                         network(1),
                         client(2),
                         evoa(3)
                       }
        MAX-ACCESS     read-only
        STATUS         current
        DESCRIPTION    "Indicates the functional type of this 11DPM12 port."
        ::= { tn11dpm12PortInfoEntry 1 }

--------------------------------------------------------------------------------
-- Raman Optical Port Info Table
--------------------------------------------------------------------------------
    tnRamanPortInfoTable OBJECT-TYPE
        SYNTAX         SEQUENCE OF TnRamanPortInfoEntry
        MAX-ACCESS     not-accessible
        STATUS         current
        DESCRIPTION    "The ports on a Raman optical card."
        ::= { tnOpticalPortInfo 144 }

    tnRamanPortInfoEntry OBJECT-TYPE
        SYNTAX         TnRamanPortInfoEntry
        MAX-ACCESS     not-accessible
        STATUS         current
        DESCRIPTION    "."
        INDEX { ifIndex }
        ::= { tnRamanPortInfoTable 1 }

    TnRamanPortInfoEntry ::=
        SEQUENCE {
            tnRamanPortTotalPowerIn       Integer32,
            tnRamanPortTotalPowerOut      Integer32,
            tnRamanPortSignalPowerOut     Integer32,
            tnRamanPortAsePowerOut        Integer32,
            tnRamanPortGain               Integer32,
            tnRamanPortPump1Power         Integer32,
            tnRamanPortPump2Power         Integer32,
            tnRamanPortPump3Power         Integer32,
            tnRamanPortPump4Power         Integer32,
            tnRamanPortPump5Power         Integer32,
            tnRamanPortBRRbaseline        Integer32,
            tnRamanPortPumpPowers         SnmpAdminString,
            tnRamanPortBRRCurrent         Integer32,
            tnRamanPortORLCurrentValue    Integer32,
            tnRamanPortSpanLoss           Integer32
         }

    tnRamanPortTotalPowerIn OBJECT-TYPE
        SYNTAX         Integer32
        UNITS          "mBm"
        MAX-ACCESS     read-only
        STATUS         current
        DESCRIPTION    "The total power into the Raman LINEIN port, with
                        -9900 means no measured power.

                        Current range:
                        A4PSWG     :  -9900, -4000 to 2500
                        Other Cards:  -9900, -3600 to 1600."
        ::= { tnRamanPortInfoEntry 1 }

    tnRamanPortTotalPowerOut OBJECT-TYPE
        SYNTAX         Integer32
        UNITS          "mBm"
        MAX-ACCESS     read-only
        STATUS         current
        DESCRIPTION    "The total power out of the Raman LINEOUT port,
                        with -9900 means no measured power.

                        Current range:
                        A4PSWG     : -9900, -4300 to 2500
                        Other Cards: -9900, -3800 to 1800."
        ::= { tnRamanPortInfoEntry 2 }

    tnRamanPortSignalPowerOut OBJECT-TYPE
        SYNTAX         Integer32
        UNITS          "mBm"
        MAX-ACCESS     read-only
        STATUS         current
        DESCRIPTION    "The signal power out of the Raman LINEOUT port,
                        with -9900 means no measured power.

                        Current range:
                        A4PSWG     : -9900, -4300 to 2500
                        Other Cards: -9900, -3800 to 1800."
        ::= { tnRamanPortInfoEntry 3 }

    tnRamanPortAsePowerOut OBJECT-TYPE
        SYNTAX         Integer32
        UNITS          "mBm"
        MAX-ACCESS     read-only
        STATUS         current
        DESCRIPTION    "The ASE noise power out of the Raman LINEOUT
                        port, with -9900 means no measured power.

                        Current range: -9900, -3000 to 1000."
        ::= { tnRamanPortInfoEntry 4 }

    tnRamanPortGain OBJECT-TYPE
        SYNTAX         Integer32
        UNITS          "mB"
        MAX-ACCESS     read-only
        STATUS         current
        DESCRIPTION    "The current operating gain.

                        Current range: 0 to 2500."
        ::= { tnRamanPortInfoEntry 5 }

    tnRamanPortPump1Power OBJECT-TYPE
        SYNTAX         Integer32
        UNITS          "mW"
        MAX-ACCESS     read-only
        STATUS         current
        DESCRIPTION    "The pump 1 power for LINEIN.

                        Current range: 0 to 400."
        DEFVAL         { 0 }
        ::= { tnRamanPortInfoEntry 6 }

    tnRamanPortPump2Power OBJECT-TYPE
        SYNTAX         Integer32
        UNITS          "mW"
        MAX-ACCESS     read-only
        STATUS         current
        DESCRIPTION    "The pump 2 power for LINEIN.

                        Current range: 0 to 400."
        DEFVAL         { 0 }
        ::= { tnRamanPortInfoEntry 7 }

    tnRamanPortPump3Power OBJECT-TYPE
        SYNTAX         Integer32
        UNITS          "mW"
        MAX-ACCESS     read-only
        STATUS         current
        DESCRIPTION    "The pump 3 power for LINEIN.

                        Current range: 0 to 400."
        ::= { tnRamanPortInfoEntry 8 }

    tnRamanPortPump4Power OBJECT-TYPE
        SYNTAX         Integer32
        UNITS          "mW"
        MAX-ACCESS     read-only
        STATUS         current
        DESCRIPTION    "The pump 4 power for LINEIN.

                        Current range: 0 to 400."
        ::= { tnRamanPortInfoEntry 9 }

    tnRamanPortPump5Power OBJECT-TYPE
        SYNTAX         Integer32
        UNITS          "mW"
        MAX-ACCESS     read-only
        STATUS         current
        DESCRIPTION    "The pump 5 power for LINEIN.

                        Current range: 0 to 400."
        ::= { tnRamanPortInfoEntry 10 }

    tnRamanPortBRRbaseline OBJECT-TYPE
        SYNTAX         Integer32
        UNITS          "mBm"
        MAX-ACCESS     read-only
        STATUS         current
        DESCRIPTION    "Back-reflection Ratio baseline."
        ::= { tnRamanPortInfoEntry 11 }

    tnRamanPortPumpPowers OBJECT-TYPE
        SYNTAX         SnmpAdminString (SIZE(0..512))
        MAX-ACCESS     read-only
        STATUS         current
        DESCRIPTION    "String containing number of pumps."
        ::= { tnRamanPortInfoEntry 12 }

    tnRamanPortBRRCurrent OBJECT-TYPE
        SYNTAX         Integer32
        UNITS          "mB"
        MAX-ACCESS     read-only
        STATUS         current
        DESCRIPTION    "Real time Back-reflection Ratio."
        ::= { tnRamanPortInfoEntry 13 }

    tnRamanPortORLCurrentValue OBJECT-TYPE
        SYNTAX         Integer32
        UNITS          "mB"
        MAX-ACCESS     read-only
        STATUS         current
        DESCRIPTION    "."
        ::= { tnRamanPortInfoEntry 14 }

    tnRamanPortSpanLoss OBJECT-TYPE
        SYNTAX         Integer32
        UNITS          "mB"
        MAX-ACCESS     read-only
        STATUS         current
        DESCRIPTION    "Span loss."
        DEFVAL         { 9900 }
        ::= { tnRamanPortInfoEntry 15 }

--------------------------------------------------------------------------------
-- MESH4 Optical Port Info Scalar
--------------------------------------------------------------------------------
    tnMesh4PortInfoAttributeTotal OBJECT-TYPE
        SYNTAX         Integer32
        MAX-ACCESS     read-only
        STATUS         current
        DESCRIPTION    "."
        ::= { tnOpticalPortInfo 145 }

--------------------------------------------------------------------------------
-- MESH4 Optical Port Info Table
--------------------------------------------------------------------------------
    tnMesh4PortInfoTable OBJECT-TYPE
        SYNTAX         SEQUENCE OF TnMesh4PortInfoEntry
        MAX-ACCESS     not-accessible
        STATUS         current
        DESCRIPTION    "The ports on a MESH4 card."
        ::= { tnOpticalPortInfo 146 }

    tnMesh4PortInfoEntry OBJECT-TYPE
        SYNTAX         TnMesh4PortInfoEntry
        MAX-ACCESS     not-accessible
        STATUS         current
        DESCRIPTION    "."
        INDEX { ifIndex }
        ::= { tnMesh4PortInfoTable 1 }

    TnMesh4PortInfoEntry ::=
        SEQUENCE {
            tnMesh4PortInfoFunction   INTEGER
         }

    tnMesh4PortInfoFunction OBJECT-TYPE
        SYNTAX         INTEGER {
                         sigIn(1),
                         sigOut(2)
                       }
        MAX-ACCESS     read-only
        STATUS         current
        DESCRIPTION    "Indicates the functional type of this MESH4 port."
        ::= { tnMesh4PortInfoEntry 1 }

--    obsolete
--    tnTcmPortInfoAttributeTotal OBJECT-TYPE ::= { tnOpticalPortInfo 147 }
--    tnTcmPortInfoTable          OBJECT-TYPE ::= { tnOpticalPortInfo 148 }

--------------------------------------------------------------------------------
-- 43SCA1 Optical Port Info Scalar
--------------------------------------------------------------------------------
    tn43sca1PortInfoAttributeTotal OBJECT-TYPE
        SYNTAX         Integer32
        MAX-ACCESS     read-only
        STATUS         current
        DESCRIPTION    "."
        ::= { tnOpticalPortInfo 149 }

--------------------------------------------------------------------------------
-- 43SCA1 Optical Port Info Table
--------------------------------------------------------------------------------
    tn43sca1PortInfoTable OBJECT-TYPE
        SYNTAX         SEQUENCE OF Tn43sca1PortInfoEntry
        MAX-ACCESS     not-accessible
        STATUS         current
        DESCRIPTION    "The ports on a 43SCA1 optical card."
        ::= { tnOpticalPortInfo 150 }

    tn43sca1PortInfoEntry OBJECT-TYPE
        SYNTAX         Tn43sca1PortInfoEntry
        MAX-ACCESS     not-accessible
        STATUS         current
        DESCRIPTION    "."
        INDEX { ifIndex }
        ::= { tn43sca1PortInfoTable 1 }

    Tn43sca1PortInfoEntry ::=
        SEQUENCE {
            tn43sca1PortInfoFunction INTEGER
        }

    tn43sca1PortInfoFunction OBJECT-TYPE
        SYNTAX         INTEGER {
                         network(1),
                         client(2)
                       }
        MAX-ACCESS     read-only
        STATUS         current
        DESCRIPTION    "Indicates the functional type of this 43SCA1 port."
        ::= { tn43sca1PortInfoEntry 1 }

--------------------------------------------------------------------------------
-- 43SCX4L Optical Port Info Scalar
--------------------------------------------------------------------------------
    tn43scx4lPortInfoAttributeTotal OBJECT-TYPE
        SYNTAX         Integer32
        MAX-ACCESS     read-only
        STATUS         current
        DESCRIPTION    "."
        ::= { tnOpticalPortInfo 151 }

--------------------------------------------------------------------------------
-- 43SCX4L Optical Port Info Table
--------------------------------------------------------------------------------
    tn43scx4lPortInfoTable OBJECT-TYPE
        SYNTAX         SEQUENCE OF Tn43scx4lPortInfoEntry
        MAX-ACCESS     not-accessible
        STATUS         current
        DESCRIPTION    "The ports on a 43SCX4L optical card."
        ::= { tnOpticalPortInfo 152 }

    tn43scx4lPortInfoEntry OBJECT-TYPE
        SYNTAX         Tn43scx4lPortInfoEntry
        MAX-ACCESS     not-accessible
        STATUS         current
        DESCRIPTION    "."
        INDEX { ifIndex }
        ::= { tn43scx4lPortInfoTable 1 }

    Tn43scx4lPortInfoEntry ::=
        SEQUENCE {
            tn43scx4lPortInfoFunction INTEGER
        }

    tn43scx4lPortInfoFunction OBJECT-TYPE
        SYNTAX         INTEGER {
                         network(1),
                         client(2)
                       }
        MAX-ACCESS     read-only
        STATUS         current
        DESCRIPTION    "Indicates the functional type of this 43SCX4L port."
        ::= { tn43scx4lPortInfoEntry 1 }

--------------------------------------------------------------------------------
-- AM2125B Optical Port Info Scalar
--------------------------------------------------------------------------------
    tnAm2125bPortInfoAttributeTotal OBJECT-TYPE
        SYNTAX         Integer32
        MAX-ACCESS     read-only
        STATUS         current
        DESCRIPTION    "."
        ::= { tnOpticalPortInfo 153 }

--------------------------------------------------------------------------------
-- AM2125B Optical Port Info Table
--------------------------------------------------------------------------------
    tnAm2125bPortInfoTable OBJECT-TYPE
        SYNTAX         SEQUENCE OF TnAm2125bPortInfoEntry
        MAX-ACCESS     not-accessible
        STATUS         current
        DESCRIPTION    "The ports on an AM2125B optical card."
        ::= { tnOpticalPortInfo 154 }

    tnAm2125bPortInfoEntry OBJECT-TYPE
        SYNTAX         TnAm2125bPortInfoEntry
        MAX-ACCESS     not-accessible
        STATUS         current
        DESCRIPTION    "."
        INDEX { ifIndex }
        ::= { tnAm2125bPortInfoTable 1 }

    TnAm2125bPortInfoEntry ::=
        SEQUENCE {
            tnAm2125bPortInfoFunction INTEGER
        }

    tnAm2125bPortInfoFunction OBJECT-TYPE
        SYNTAX         INTEGER {
                         lineIn(1),
                         inv(2),
                         dcm(3),
                         lineOut(4),
                         oscSfp(5),
                         det(6),
                         osc(7),
                         custLan(8)
                       }
        MAX-ACCESS     read-only
        STATUS         current
        DESCRIPTION    "Indicates the functional type of this AM2125B port."
        ::= { tnAm2125bPortInfoEntry 1 }

--------------------------------------------------------------------------------
-- 112SNX10 Optical Port Info Scalar
--------------------------------------------------------------------------------
    tn112snx10PortInfoAttributeTotal OBJECT-TYPE
        SYNTAX         Integer32
        MAX-ACCESS     read-only
        STATUS         current
        DESCRIPTION    "."
        ::= { tnOpticalPortInfo 155 }

--------------------------------------------------------------------------------
-- 112SNX10 Optical Port Info Table
--------------------------------------------------------------------------------
    tn112snx10PortInfoTable OBJECT-TYPE
        SYNTAX         SEQUENCE OF Tn112snx10PortInfoEntry
        MAX-ACCESS     not-accessible
        STATUS         current
        DESCRIPTION    "The ports on a 112SNX10 optical card."
        ::= { tnOpticalPortInfo 156 }

    tn112snx10PortInfoEntry OBJECT-TYPE
        SYNTAX         Tn112snx10PortInfoEntry
        MAX-ACCESS     not-accessible
        STATUS         current
        DESCRIPTION    "."
        INDEX { ifIndex }
        ::= { tn112snx10PortInfoTable 1 }

    Tn112snx10PortInfoEntry ::=
        SEQUENCE {
            tn112snx10PortInfoFunction INTEGER
        }

    tn112snx10PortInfoFunction OBJECT-TYPE
        SYNTAX         INTEGER {
                         network(1),
                         client(2)
                       }
        MAX-ACCESS     read-only
        STATUS         current
        DESCRIPTION    "Indicates the functional type of this 112SNX10 port."
        ::= { tn112snx10PortInfoEntry 1 }

--------------------------------------------------------------------------------
-- 112SNA1 Optical Port Info Scalar
--------------------------------------------------------------------------------
    tn112sna1PortInfoAttributeTotal OBJECT-TYPE
        SYNTAX         Integer32
        MAX-ACCESS     read-only
        STATUS         current
        DESCRIPTION    "."
        ::= { tnOpticalPortInfo 157 }

--------------------------------------------------------------------------------
-- 112SNA1 Optical Port Info Table
--------------------------------------------------------------------------------
    tn112sna1PortInfoTable OBJECT-TYPE
        SYNTAX         SEQUENCE OF Tn112sna1PortInfoEntry
        MAX-ACCESS     not-accessible
        STATUS         current
        DESCRIPTION    "The ports on a 112SNA1 optical card."
        ::= { tnOpticalPortInfo 158 }

    tn112sna1PortInfoEntry OBJECT-TYPE
        SYNTAX         Tn112sna1PortInfoEntry
        MAX-ACCESS     not-accessible
        STATUS         current
        DESCRIPTION    "."
        INDEX { ifIndex }
        ::= { tn112sna1PortInfoTable 1 }

    Tn112sna1PortInfoEntry ::=
        SEQUENCE {
            tn112sna1PortInfoFunction INTEGER
        }

    tn112sna1PortInfoFunction OBJECT-TYPE
        SYNTAX         INTEGER {
                         network(1),
                         client(2)
                       }
        MAX-ACCESS     read-only
        STATUS         current
        DESCRIPTION    "Indicates the functional type of this 112SNA1 port."
        ::= { tn112sna1PortInfoEntry 1 }

--    obsolete
--    tn11qta4PortInfoTable OBJECT-TYPE ::= { tnOpticalPortInfo 160 }

--------------------------------------------------------------------------------
-- 1DPP24M Optical Port Info Scalar
--------------------------------------------------------------------------------
    tn1dpp24mPortInfoAttributeTotal OBJECT-TYPE
        SYNTAX         Integer32
        MAX-ACCESS     read-only
        STATUS         current
        DESCRIPTION    "."
        ::= { tnOpticalPortInfo 161 }

--------------------------------------------------------------------------------
-- 1DPP24M Optical Port Info Table
--------------------------------------------------------------------------------
    tn1dpp24mPortInfoTable OBJECT-TYPE
        SYNTAX         SEQUENCE OF Tn1dpp24mPortInfoEntry
        MAX-ACCESS     not-accessible
        STATUS         current
        DESCRIPTION    "The ports on a 1DPP24M optical card."
        ::= { tnOpticalPortInfo 162 }

    tn1dpp24mPortInfoEntry OBJECT-TYPE
        SYNTAX         Tn1dpp24mPortInfoEntry
        MAX-ACCESS     not-accessible
        STATUS         current
        DESCRIPTION    "."
        INDEX { ifIndex }
        ::= { tn1dpp24mPortInfoTable 1 }

    Tn1dpp24mPortInfoEntry ::=
        SEQUENCE {
            tn1dpp24mPortInfoFunction                 INTEGER
--            obsolete
--            tn1dpp24mPortClockSourceIncomingQLStatus  Unsigned32,
--            tn1dpp24mPortClockSourceIncomingQL        Unsigned32
        }

    tn1dpp24mPortInfoFunction OBJECT-TYPE
        SYNTAX         INTEGER {
                         network(1),
                         client(2)
                       }
        MAX-ACCESS     read-only
        STATUS         current
        DESCRIPTION    "Indicates the functional type of this 1DPP24M port."
        ::= { tn1dpp24mPortInfoEntry 1 }

--    obsolete
--    tn1dpp24mPortClockSourceIncomingQLStatus OBJECT-TYPE ::= { tn1dpp24mPortInfoEntry 2 }
--    tn1dpp24mPortClockSourceIncomingQL       OBJECT-TYPE ::= { tn1dpp24mPortInfoEntry 3 }

--------------------------------------------------------------------------------
-- DWDM Common OTU3/ODU3 Client Port Info Table
--------------------------------------------------------------------------------
    tnDwdmCmnOtu3Odu3ClientPortInfoTable OBJECT-TYPE
        SYNTAX         SEQUENCE OF TnDwdmCmnOtu3Odu3ClientPortInfoEntry
        MAX-ACCESS     not-accessible
        STATUS         current
        DESCRIPTION    "Common attributes against DWDM client ports."
        ::= { tnOpticalPortInfo 163 }

    tnDwdmCmnOtu3Odu3ClientPortInfoEntry OBJECT-TYPE
        SYNTAX         TnDwdmCmnOtu3Odu3ClientPortInfoEntry
        MAX-ACCESS     not-accessible
        STATUS         current
        DESCRIPTION    "."
        INDEX { ifIndex }
        ::= { tnDwdmCmnOtu3Odu3ClientPortInfoTable 1 }

    TnDwdmCmnOtu3Odu3ClientPortInfoEntry ::=
        SEQUENCE {
            tnDwdmCmnClientPortOtu3IncomingTti  OCTET STRING,
            tnDwdmCmnClientPortOtu3TtiStatus    AluWdmTtiStatus,
            tnDwdmCmnClientPortOdu3IncomingTti  OCTET STRING,
            tnDwdmCmnClientPortOdu3TtiStatus    AluWdmTtiStatus,
            tnDwdmCmnClientPortOtu3PreFec       Counter64,
            tnDwdmCmnClientPortOtu3PostFec      Counter64
        }

    tnDwdmCmnClientPortOtu3IncomingTti OBJECT-TYPE
        SYNTAX         OCTET STRING
        MAX-ACCESS     read-only
        STATUS         current
        DESCRIPTION    "OTU3 incoming TTI."
        DEFVAL         { "" }
        ::= { tnDwdmCmnOtu3Odu3ClientPortInfoEntry 1 }

    tnDwdmCmnClientPortOtu3TtiStatus OBJECT-TYPE
        SYNTAX         AluWdmTtiStatus
        MAX-ACCESS     read-only
        STATUS         current
        DESCRIPTION    "OTU3 TTI status."
        DEFVAL         { unspecified }
        ::= { tnDwdmCmnOtu3Odu3ClientPortInfoEntry 2 }

    tnDwdmCmnClientPortOdu3IncomingTti OBJECT-TYPE
        SYNTAX         OCTET STRING
        MAX-ACCESS     read-only
        STATUS         current
        DESCRIPTION    "ODU3 incoming TTI."
        DEFVAL         { "" }
        ::= { tnDwdmCmnOtu3Odu3ClientPortInfoEntry 3 }

    tnDwdmCmnClientPortOdu3TtiStatus OBJECT-TYPE
        SYNTAX         AluWdmTtiStatus
        MAX-ACCESS     read-only
        STATUS         current
        DESCRIPTION    "ODU3 TTI status."
        DEFVAL         { unspecified }
        ::= { tnDwdmCmnOtu3Odu3ClientPortInfoEntry 4 }

    tnDwdmCmnClientPortOtu3PreFec OBJECT-TYPE
        SYNTAX         Counter64
        MAX-ACCESS     read-only
        STATUS         current
        DESCRIPTION    "Real time error bit rate of pre-FEC (Forward
                        Error Correction).

                        Current configurable range: 0 to 4000."
        ::= { tnDwdmCmnOtu3Odu3ClientPortInfoEntry 5 }

    tnDwdmCmnClientPortOtu3PostFec OBJECT-TYPE
        SYNTAX         Counter64
        MAX-ACCESS     read-only
        STATUS         current
        DESCRIPTION    "Real time error bit rate of post-FEC (Forward
                        Error Correction).

                        Current configurable range: 0 to 4000."
        ::= { tnDwdmCmnOtu3Odu3ClientPortInfoEntry 6 }

--------------------------------------------------------------------------------
-- UL43SCUP Optical Port Info Scalar
--------------------------------------------------------------------------------
    tnul43scupPortInfoAttributeTotal OBJECT-TYPE
        SYNTAX         Integer32
        MAX-ACCESS     read-only
        STATUS         current
        DESCRIPTION    "."
        ::= { tnOpticalPortInfo 164 }

--------------------------------------------------------------------------------
-- UL43SCUP Optical Port Info Table
--------------------------------------------------------------------------------
    tnul43scupPortInfoTable OBJECT-TYPE
        SYNTAX         SEQUENCE OF Tnul43scupPortInfoEntry
        MAX-ACCESS     not-accessible
        STATUS         current
        DESCRIPTION    "The ports on a UL43SCUP optical card."
        ::= { tnOpticalPortInfo 165 }

    tnul43scupPortInfoEntry OBJECT-TYPE
        SYNTAX         Tnul43scupPortInfoEntry
        MAX-ACCESS     not-accessible
        STATUS         current
        DESCRIPTION    "."
        INDEX { ifIndex }
        ::= { tnul43scupPortInfoTable 1 }

    Tnul43scupPortInfoEntry ::=
        SEQUENCE {
            tnul43scupPortInfoFunction  INTEGER
        }

    tnul43scupPortInfoFunction OBJECT-TYPE
        SYNTAX         INTEGER {
                         network(1)
                       }
        MAX-ACCESS     read-only
        STATUS         current
        DESCRIPTION    "Indicates the functional type of this UL43SCUP port."
        ::= { tnul43scupPortInfoEntry 1 }

--------------------------------------------------------------------------------
-- UL11QCUP Optical Port Info Scalar
--------------------------------------------------------------------------------
    tnul11qcupPortInfoAttributeTotal OBJECT-TYPE
        SYNTAX         Integer32
        MAX-ACCESS     read-only
        STATUS         current
        DESCRIPTION    "."
        ::= { tnOpticalPortInfo 166 }

--------------------------------------------------------------------------------
-- UL11QCUP Optical Port Info Table
--------------------------------------------------------------------------------
    tnul11qcupPortInfoTable OBJECT-TYPE
        SYNTAX         SEQUENCE OF Tnul11qcupPortInfoEntry
        MAX-ACCESS     not-accessible
        STATUS         current
        DESCRIPTION    "The ports on a UL11QCUP optical card."
        ::= { tnOpticalPortInfo 167 }

    tnul11qcupPortInfoEntry OBJECT-TYPE
        SYNTAX         Tnul11qcupPortInfoEntry
        MAX-ACCESS     not-accessible
        STATUS         current
        DESCRIPTION    "."
        INDEX { ifIndex }
        ::= { tnul11qcupPortInfoTable 1 }

    Tnul11qcupPortInfoEntry ::=
        SEQUENCE {
            tnul11qcupPortInfoFunction     INTEGER
        }

    tnul11qcupPortInfoFunction OBJECT-TYPE
        SYNTAX         INTEGER {
                         network(1)
                       }
        MAX-ACCESS     read-only
        STATUS         current
        DESCRIPTION    "Indicates the functional type of this UL11QCUP port."
        ::= { tnul11qcupPortInfoEntry 1 }

--------------------------------------------------------------------------------
-- 11QPEN4 Optical Port Info Scalar
--------------------------------------------------------------------------------
    tn11qpen4PortInfoAttributeTotal OBJECT-TYPE
        SYNTAX         Integer32
        MAX-ACCESS     read-only
        STATUS         current
        DESCRIPTION    "."
        ::= { tnOpticalPortInfo 168 }

--------------------------------------------------------------------------------
-- 11QPEN4 Optical Port Info Table
--------------------------------------------------------------------------------
    tn11qpen4PortInfoTable OBJECT-TYPE
        SYNTAX         SEQUENCE OF Tn11qpen4PortInfoEntry
        MAX-ACCESS     not-accessible
        STATUS         current
        DESCRIPTION    "The ports on a 11QPEN4 optical card."
        ::= { tnOpticalPortInfo 169 }

    tn11qpen4PortInfoEntry OBJECT-TYPE
        SYNTAX         Tn11qpen4PortInfoEntry
        MAX-ACCESS     not-accessible
        STATUS         current
        DESCRIPTION    "."
        INDEX { ifIndex }
        ::= { tn11qpen4PortInfoTable 1 }

    Tn11qpen4PortInfoEntry ::=
        SEQUENCE {
            tn11qpen4PortInfoFunction                  INTEGER,
            tn11qpen4PortInfoEncryptionCurrentKeyInfo  SnmpAdminString,
            tn11qpen4PortInfoEncryptionNextKeyInfo     SnmpAdminString
        }

    tn11qpen4PortInfoFunction OBJECT-TYPE
        SYNTAX         INTEGER {
                         network(1),
                         client(2),
                         evoa(3)
                       }
        MAX-ACCESS     read-only
        STATUS         current
        DESCRIPTION    "Indicates the functional type of this 11QPEN4 port."
        ::= { tn11qpen4PortInfoEntry 1 }

    tn11qpen4PortInfoEncryptionCurrentKeyInfo OBJECT-TYPE
        SYNTAX         SnmpAdminString (SIZE(0..256))
        MAX-ACCESS     read-only
        STATUS         current
        DESCRIPTION    "Non-cryptographic information identifying the
                        current key."
        DEFVAL         { "" }
        ::= { tn11qpen4PortInfoEntry 2 }

    tn11qpen4PortInfoEncryptionNextKeyInfo OBJECT-TYPE
        SYNTAX         SnmpAdminString (SIZE(0..256))
        MAX-ACCESS     read-only
        STATUS         current
        DESCRIPTION    "Non-cryptographic information identifying the
                        standby key."
        DEFVAL         { "" }
        ::= { tn11qpen4PortInfoEntry 3 }

--------------------------------------------------------------------------------
-- 43SCX4E Optical Port Info Scalar
--------------------------------------------------------------------------------
    tn43scx4ePortInfoAttributeTotal OBJECT-TYPE
        SYNTAX         Integer32
        MAX-ACCESS     read-only
        STATUS         current
        DESCRIPTION    "."
        ::= { tnOpticalPortInfo 170 }

--------------------------------------------------------------------------------
-- 43SCX4E Optical Port Info Table
--------------------------------------------------------------------------------
    tn43scx4ePortInfoTable OBJECT-TYPE
        SYNTAX         SEQUENCE OF Tn43scx4ePortInfoEntry
        MAX-ACCESS     not-accessible
        STATUS         current
        DESCRIPTION    "The ports on a 43SCX4E optical card."
        ::= { tnOpticalPortInfo 171 }

    tn43scx4ePortInfoEntry OBJECT-TYPE
        SYNTAX         Tn43scx4ePortInfoEntry
        MAX-ACCESS     not-accessible
        STATUS         current
        DESCRIPTION    "."
        INDEX { ifIndex }
        ::= { tn43scx4ePortInfoTable 1 }

    Tn43scx4ePortInfoEntry ::=
        SEQUENCE {
            tn43scx4ePortInfoFunction INTEGER
        }

    tn43scx4ePortInfoFunction OBJECT-TYPE
        SYNTAX         INTEGER {
                         network(1),
                         client(2)
                       }
        MAX-ACCESS     read-only
        STATUS         current
        DESCRIPTION    "Indicates the functional type of this 43SCX4E port."
        ::= { tn43scx4ePortInfoEntry 1 }

--------------------------------------------------------------------------------
-- WSS Attenuation Optical Port Info Scalar
--------------------------------------------------------------------------------
    tnWssAttenPortInfoAttributeTotal OBJECT-TYPE
        SYNTAX         Integer32
        MAX-ACCESS     read-only
        STATUS         current
        DESCRIPTION    "."
        ::= { tnOpticalPortInfo 172 }

--------------------------------------------------------------------------------
-- WSS Attenuation Port Info Table
--------------------------------------------------------------------------------
    tnWssAttenPortInfoTable OBJECT-TYPE
        SYNTAX         SEQUENCE OF TnWssAttenPortInfoEntry
        MAX-ACCESS     not-accessible
        STATUS         current
        DESCRIPTION    "Through this table, a network operator may read
                        the WSS attenuation."
        ::= { tnOpticalPortInfo 173 }

    tnWssAttenPortInfoEntry OBJECT-TYPE
        SYNTAX         TnWssAttenPortInfoEntry
        MAX-ACCESS     not-accessible
        STATUS         current
        DESCRIPTION    "."
        INDEX { ifIndex,
                tnDirection,
                tnChannel }
        ::= { tnWssAttenPortInfoTable 1 }

    TnWssAttenPortInfoEntry ::=
        SEQUENCE {
            tnWssAttenPortInfoWssCurrentRelativeAtten  Unsigned32,
            tnWssAttenPortInfoApplicability            INTEGER
        }

    tnWssAttenPortInfoWssCurrentRelativeAtten OBJECT-TYPE
        SYNTAX         Unsigned32
        UNITS          "mB"
        MAX-ACCESS     read-only
        STATUS         current
        DESCRIPTION    "The attenuation, expressed in units of mB, is
                        associated with the WSS channel attenuation.
                        This is the current relative attenuation.

                        Current range: 0 to 1500."
        ::= { tnWssAttenPortInfoEntry 1 }

    tnWssAttenPortInfoApplicability OBJECT-TYPE
        SYNTAX         INTEGER {
                         notApplicable(1),
                         applicableAndAvailable(2)
                       }
        MAX-ACCESS     read-only
        STATUS         current
        DESCRIPTION    "Values include:

                        notApplicable - no XC is configured for this
                          channel.
                        applicableAndAvailable - XC is configured for
                          this channel."
        ::= { tnWssAttenPortInfoEntry 2 }

--------------------------------------------------------------------------------
-- 43SCGE1 Optical Port Info Scalar
--------------------------------------------------------------------------------
    tn43scge1PortInfoAttributeTotal OBJECT-TYPE
        SYNTAX         Integer32
        MAX-ACCESS     read-only
        STATUS         current
        DESCRIPTION    "."
        ::= { tnOpticalPortInfo 174 }

--------------------------------------------------------------------------------
-- 43SCGE1 Optical Port Info Table
--------------------------------------------------------------------------------
    tn43scge1PortInfoTable OBJECT-TYPE
        SYNTAX         SEQUENCE OF Tn43scge1PortInfoEntry
        MAX-ACCESS     not-accessible
        STATUS         current
        DESCRIPTION    "The ports on a 43SCGE1 optical card."
        ::= { tnOpticalPortInfo 175 }

    tn43scge1PortInfoEntry OBJECT-TYPE
        SYNTAX         Tn43scge1PortInfoEntry
        MAX-ACCESS     not-accessible
        STATUS         current
        DESCRIPTION    "."
        INDEX { ifIndex }
        ::= { tn43scge1PortInfoTable 1 }

    Tn43scge1PortInfoEntry ::=
        SEQUENCE {
            tn43scge1PortInfoFunction INTEGER
        }

    tn43scge1PortInfoFunction OBJECT-TYPE
        SYNTAX         INTEGER {
                         network(1),
                         client(2)
                       }
        MAX-ACCESS     read-only
        STATUS         current
        DESCRIPTION    "Indicates the functional type of this 43SCGE1 port."
        ::= { tn43scge1PortInfoEntry 1 }

--------------------------------------------------------------------------------
-- 11QPE24 Optical Port Info Scalar
--------------------------------------------------------------------------------
    tn11qpe24PortInfoAttributeTotal OBJECT-TYPE
        SYNTAX         Integer32
        MAX-ACCESS     read-only
        STATUS         current
        DESCRIPTION    "."
        ::= { tnOpticalPortInfo 176 }

--------------------------------------------------------------------------------
-- 11QPE24 Optical Port Info Table
--------------------------------------------------------------------------------
    tn11qpe24PortInfoTable OBJECT-TYPE
        SYNTAX         SEQUENCE OF Tn11qpe24PortInfoEntry
        MAX-ACCESS     not-accessible
        STATUS         current
        DESCRIPTION    "The ports on a 11QPE24 optical card."
        ::= { tnOpticalPortInfo 177 }

    tn11qpe24PortInfoEntry OBJECT-TYPE
        SYNTAX         Tn11qpe24PortInfoEntry
        MAX-ACCESS     not-accessible
        STATUS         current
        DESCRIPTION    "."
        INDEX { ifIndex }
        ::= { tn11qpe24PortInfoTable 1 }

    Tn11qpe24PortInfoEntry ::=
        SEQUENCE {
            tn11qpe24PortInfoFunction INTEGER
        }

    tn11qpe24PortInfoFunction OBJECT-TYPE
        SYNTAX         INTEGER {
                         network(1),
                         client(2),
                         evoa(3)
                       }
        MAX-ACCESS     read-only
        STATUS         current
        DESCRIPTION    "Indicates the functional type of this 11QPE24 port."
        ::= { tn11qpe24PortInfoEntry 1 }

--------------------------------------------------------------------------------
-- 11STAR1A Optical Port Info Scalar
--------------------------------------------------------------------------------
    tn11star1aPortInfoAttributeTotal OBJECT-TYPE
        SYNTAX         Integer32
        MAX-ACCESS     read-only
        STATUS         current
        DESCRIPTION    "."
        ::= { tnOpticalPortInfo 178 }

--------------------------------------------------------------------------------
-- 11STAR1A Optical Port Info Table
--------------------------------------------------------------------------------
    tn11star1aPortInfoTable OBJECT-TYPE
        SYNTAX         SEQUENCE OF Tn11star1aPortInfoEntry
        MAX-ACCESS     not-accessible
        STATUS         current
        DESCRIPTION    "The ports on a 11STAR1A optical card."
        ::= { tnOpticalPortInfo 179 }

    tn11star1aPortInfoEntry OBJECT-TYPE
        SYNTAX         Tn11star1aPortInfoEntry
        MAX-ACCESS     not-accessible
        STATUS         current
        DESCRIPTION    "."
        INDEX { ifIndex }
        ::= { tn11star1aPortInfoTable 1 }

    Tn11star1aPortInfoEntry ::=
        SEQUENCE {
            tn11star1aPortInfoFunction INTEGER
        }

    tn11star1aPortInfoFunction OBJECT-TYPE
        SYNTAX         INTEGER {
                         network(1),
                         client(2)
                       }
        MAX-ACCESS     read-only
        STATUS         current
        DESCRIPTION    "Indicates the functional type of this 11STAR1A port."
        ::= { tn11star1aPortInfoEntry 1 }

--------------------------------------------------------------------------------
-- MVAC8B Optical Port Info Scalar
--------------------------------------------------------------------------------
    tnMvac8bPortInfoAttributeTotal OBJECT-TYPE
        SYNTAX         Integer32
        MAX-ACCESS     read-only
        STATUS         current
        DESCRIPTION    "."
        ::= { tnOpticalPortInfo 180 }

--------------------------------------------------------------------------------
-- MVAC8B Optical Port Info Table
--------------------------------------------------------------------------------
    tnMvac8bPortInfoTable OBJECT-TYPE
        SYNTAX         SEQUENCE OF TnMvac8bPortInfoEntry
        MAX-ACCESS     not-accessible
        STATUS         current
        DESCRIPTION    "The ports on a MVAC8B optical card."
        ::= { tnOpticalPortInfo 181 }

    tnMvac8bPortInfoEntry OBJECT-TYPE
        SYNTAX         TnMvac8bPortInfoEntry
        MAX-ACCESS     not-accessible
        STATUS         current
        DESCRIPTION    "."
        INDEX { ifIndex }
        ::= { tnMvac8bPortInfoTable 1 }

    TnMvac8bPortInfoEntry ::=
        SEQUENCE {
            tnMvac8bPortInfoFunction INTEGER
        }

    tnMvac8bPortInfoFunction OBJECT-TYPE
        SYNTAX         INTEGER {
                         network(1),
                         client(2)
                       }
        MAX-ACCESS     read-only
        STATUS         current
        DESCRIPTION    "Indicates the functional type of this MVAC8B port."
        ::= { tnMvac8bPortInfoEntry 1 }

--------------------------------------------------------------------------------
-- WR8-88AF Optical Port Info Scalar
--------------------------------------------------------------------------------
    tnWr8c88afPortInfoAttributeTotal OBJECT-TYPE
        SYNTAX         Integer32
        MAX-ACCESS     read-only
        STATUS         current
        DESCRIPTION    "."
        ::= { tnOpticalPortInfo 182 }

--------------------------------------------------------------------------------
-- WR8-88AF Optical Port Info Table
--------------------------------------------------------------------------------
    tnWr8c88afPortInfoTable OBJECT-TYPE
        SYNTAX         SEQUENCE OF TnWr8c88afPortInfoEntry
        MAX-ACCESS     not-accessible
        STATUS         current
        DESCRIPTION    "The ports on a WR8-88AF optical card."
        ::= { tnOpticalPortInfo 183 }

    tnWr8c88afPortInfoEntry OBJECT-TYPE
        SYNTAX         TnWr8c88afPortInfoEntry
        MAX-ACCESS     not-accessible
        STATUS         current
        DESCRIPTION    "."
        INDEX { ifIndex }
        ::= { tnWr8c88afPortInfoTable 1 }

    TnWr8c88afPortInfoEntry ::=
        SEQUENCE {
            tnWr8c88afPortInfoFunction     INTEGER
        }

    tnWr8c88afPortInfoFunction OBJECT-TYPE
        SYNTAX         INTEGER {
                         signal(1),
                         thru(2),
                         dropOut(3),
                         addIn(4),
                         meshOut(5),
                         inv(6)
                       }
        MAX-ACCESS     read-only
        STATUS         current
        DESCRIPTION    "Indicates the functional type of this WR8-88AF port."
        ::= { tnWr8c88afPortInfoEntry 1 }

--------------------------------------------------------------------------------
-- 10AN10G Optical Port Info Scalar
--------------------------------------------------------------------------------
    tncl10an10gPortInfoAttributeTotal OBJECT-TYPE
        SYNTAX         Integer32
        MAX-ACCESS     read-only
        STATUS         current
        DESCRIPTION    "."
        ::= { tnOpticalPortInfo 184 }

--------------------------------------------------------------------------------
-- 10AN10G Optical Port Info Table
--------------------------------------------------------------------------------
    tncl10an10gPortInfoTable OBJECT-TYPE
        SYNTAX         SEQUENCE OF Tncl10an10gPortInfoEntry
        MAX-ACCESS     not-accessible
        STATUS         current
        DESCRIPTION    "The ports on a 10AN10G optical card."
        ::= { tnOpticalPortInfo 185 }

    tncl10an10gPortInfoEntry OBJECT-TYPE
        SYNTAX         Tncl10an10gPortInfoEntry
        MAX-ACCESS     not-accessible
        STATUS         current
        DESCRIPTION    "."
        INDEX { ifIndex }
        ::= { tncl10an10gPortInfoTable 1 }

    Tncl10an10gPortInfoEntry ::=
        SEQUENCE {
            tncl10an10gPortInfoFunction INTEGER
        }

    tncl10an10gPortInfoFunction OBJECT-TYPE
        SYNTAX         INTEGER {
                         network(1),
                         client(2)
                       }
        MAX-ACCESS     read-only
        STATUS         current
        DESCRIPTION    "Indicates the functional type of this 10AN10G port."
        ::= { tncl10an10gPortInfoEntry 1 }

--------------------------------------------------------------------------------
-- 24ANM Optical Port Info Scalar
--------------------------------------------------------------------------------
    tncl24anmPortInfoAttributeTotal OBJECT-TYPE
        SYNTAX         Integer32
        MAX-ACCESS     read-only
        STATUS         current
        DESCRIPTION    "."
        ::= { tnOpticalPortInfo 186 }

--------------------------------------------------------------------------------
-- 24ANM Optical Port Info Table
--------------------------------------------------------------------------------
    tncl24anmPortInfoTable OBJECT-TYPE
        SYNTAX         SEQUENCE OF Tncl24anmPortInfoEntry
        MAX-ACCESS     not-accessible
        STATUS         current
        DESCRIPTION    "The ports on a 24ANM optical card."
        ::= { tnOpticalPortInfo 187 }

    tncl24anmPortInfoEntry OBJECT-TYPE
        SYNTAX         Tncl24anmPortInfoEntry
        MAX-ACCESS     not-accessible
        STATUS         current
        DESCRIPTION    "."
        INDEX { ifIndex }
        ::= { tncl24anmPortInfoTable 1 }

    Tncl24anmPortInfoEntry ::=
        SEQUENCE {
            tncl24anmPortInfoFunction INTEGER
        }

    tncl24anmPortInfoFunction OBJECT-TYPE
        SYNTAX         INTEGER {
                         network(1),
                         client(2)
                       }
        MAX-ACCESS     read-only
        STATUS         current
        DESCRIPTION    "Indicates the functional type of this 24ANM port."
        ::= { tncl24anmPortInfoEntry 1 }

--------------------------------------------------------------------------------
-- OPSB Optical Port Info Scalar
--------------------------------------------------------------------------------
    tnOpsbPortInfoAttributeTotal OBJECT-TYPE
        SYNTAX         Integer32
        MAX-ACCESS     read-only
        STATUS         current
        DESCRIPTION    "."
        ::= { tnOpticalPortInfo 188 }

--------------------------------------------------------------------------------
-- OPSB Optical Port Info Table
--------------------------------------------------------------------------------
    tnOpsbPortInfoTable OBJECT-TYPE
        SYNTAX         SEQUENCE OF TnOpsbPortInfoEntry
        MAX-ACCESS     not-accessible
        STATUS         current
        DESCRIPTION    "The ports on an OPSB optical card."
        ::= { tnOpticalPortInfo 189 }

    tnOpsbPortInfoEntry OBJECT-TYPE
        SYNTAX         TnOpsbPortInfoEntry
        MAX-ACCESS     not-accessible
        STATUS         current
        DESCRIPTION    "."
        INDEX { ifIndex }
        ::= { tnOpsbPortInfoTable 1 }

    TnOpsbPortInfoEntry ::=
        SEQUENCE {
            tnOpsbPortInfoFunction     INTEGER
        }

    tnOpsbPortInfoFunction OBJECT-TYPE
        SYNTAX         INTEGER {
                         signal(1),
                         workingProtected(2)
                       }
        MAX-ACCESS     read-only
        STATUS         current
        DESCRIPTION    "Indicates the functional type of this OPSB port."
        ::= { tnOpsbPortInfoEntry 1 }

--------------------------------------------------------------------------------
-- OPS Optical Port Info Scalar
--------------------------------------------------------------------------------
    tnOpsPortInfoAttributeTotal OBJECT-TYPE
        SYNTAX         Integer32
        MAX-ACCESS     read-only
        STATUS         current
        DESCRIPTION    "."
        ::= { tnOpticalPortInfo 190 }

--------------------------------------------------------------------------------
-- OPS Optical Port Info Table
--------------------------------------------------------------------------------
    tnOpsPortInfoTable OBJECT-TYPE
        SYNTAX         SEQUENCE OF TnOpsPortInfoEntry
        MAX-ACCESS     not-accessible
        STATUS         current
        DESCRIPTION    "The attributes for an OPS optical card."
        ::= { tnOpticalPortInfo 191 }

    tnOpsPortInfoEntry OBJECT-TYPE
        SYNTAX         TnOpsPortInfoEntry
        MAX-ACCESS     not-accessible
        STATUS         current
        DESCRIPTION    "."
        INDEX { ifIndex }
        ::= { tnOpsPortInfoTable 1 }

    TnOpsPortInfoEntry ::=
        SEQUENCE {
            tnOpsPortInfoReceivedPower                  Integer32,
            tnOpsPortInfoPresentTransmitAttenuation     Integer32,
            tnOpsPortInfoChannelMeasuredPsd             Integer32,
            tnOpsPortInfoChanMeasuredPower              Integer32,
            tnOpsPortInfoExpectedInputPowerDev          Integer32
        }

    tnOpsPortInfoReceivedPower OBJECT-TYPE
        SYNTAX         Integer32
        UNITS          "mBm"
        MAX-ACCESS     read-only
        STATUS         current
        DESCRIPTION    "The received power in mBm.  This is accessible
                        from ports 2 and 3 (working or protected)
                        exclusively."
        ::= { tnOpsPortInfoEntry 1 }

    tnOpsPortInfoPresentTransmitAttenuation OBJECT-TYPE
        SYNTAX         Integer32
        UNITS          "mB"
        MAX-ACCESS     read-only
        STATUS         current
        DESCRIPTION    "The present attenuation of the attenuator -
                        applies to the network ports of the OPS
                        optical card with attenuators."
        ::= { tnOpsPortInfoEntry 2 }

    tnOpsPortInfoChannelMeasuredPsd OBJECT-TYPE
        SYNTAX         Integer32
        MAX-ACCESS     read-only
        STATUS         current
        DESCRIPTION    "."
        ::= { tnOpsPortInfoEntry 3 }

    tnOpsPortInfoChanMeasuredPower OBJECT-TYPE
        SYNTAX         Integer32
        UNITS          "mBm"
        MAX-ACCESS     read-only
        STATUS         current
        DESCRIPTION    "."
        ::= { tnOpsPortInfoEntry 4 }

    tnOpsPortInfoExpectedInputPowerDev OBJECT-TYPE
        SYNTAX         Integer32
        MAX-ACCESS     read-only
        STATUS         current
        DESCRIPTION    "."
        ::= { tnOpsPortInfoEntry 5 }

--------------------------------------------------------------------------------
-- 11DPE12A Optical Port Info Scalar
--------------------------------------------------------------------------------
    tn11dpe12aPortInfoAttributeTotal OBJECT-TYPE
        SYNTAX         Integer32
        MAX-ACCESS     read-only
        STATUS         current
        DESCRIPTION    "."
        ::= { tnOpticalPortInfo 192 }

--------------------------------------------------------------------------------
-- 11DPE12A Optical Port Info Table
--------------------------------------------------------------------------------
    tn11dpe12aPortInfoTable OBJECT-TYPE
        SYNTAX         SEQUENCE OF Tn11dpe12aPortInfoEntry
        MAX-ACCESS     not-accessible
        STATUS         current
        DESCRIPTION    "The ports on a 11DPE12A optical card."
        ::= { tnOpticalPortInfo 193 }

    tn11dpe12aPortInfoEntry OBJECT-TYPE
        SYNTAX         Tn11dpe12aPortInfoEntry
        MAX-ACCESS     not-accessible
        STATUS         current
        DESCRIPTION    "."
        INDEX { ifIndex }
        ::= { tn11dpe12aPortInfoTable 1 }

    Tn11dpe12aPortInfoEntry ::=
        SEQUENCE {
            tn11dpe12aPortInfoFunction               INTEGER,
            tn11dpe12aPortInfoTotalVTS               Unsigned32,
            tn11dpe12aPortInfoIngAvailableBandwidth  Unsigned32,
            tn11dpe12aPortInfoEgrAvailableBandwidth  Unsigned32
        }

    tn11dpe12aPortInfoFunction OBJECT-TYPE
        SYNTAX         INTEGER {
                         network(1),
                         client(2),
                         evoa(3),
                         backplane(4),
                         tod(5),
                         bits(6)
                       }
        MAX-ACCESS     read-only
        STATUS         current
        DESCRIPTION    "Indicates the functional type of this 11DPE12A port."
        ::= { tn11dpe12aPortInfoEntry 1 }

    tn11dpe12aPortInfoTotalVTS OBJECT-TYPE
        SYNTAX         Unsigned32
        MAX-ACCESS     read-only
        STATUS         current
        DESCRIPTION    "Total VTS for 11dpe12a ports."
        ::= { tn11dpe12aPortInfoEntry 2 }

    tn11dpe12aPortInfoIngAvailableBandwidth OBJECT-TYPE
        SYNTAX         Unsigned32
        MAX-ACCESS     read-only
        STATUS         current
        DESCRIPTION    "Available bandwidth for ingress 11DPE12A ports."
        ::= { tn11dpe12aPortInfoEntry 3 }

    tn11dpe12aPortInfoEgrAvailableBandwidth OBJECT-TYPE
        SYNTAX         Unsigned32
        MAX-ACCESS     read-only
        STATUS         current
        DESCRIPTION    "Available bandwidth for egress 11DPE12A ports."
        ::= { tn11dpe12aPortInfoEntry 4 }

--------------------------------------------------------------------------------
-- UL130SCUP Optical Port Info Scalar
--------------------------------------------------------------------------------
    tnul130scupPortInfoAttributeTotal OBJECT-TYPE
        SYNTAX         Integer32
        MAX-ACCESS     read-only
        STATUS         current
        DESCRIPTION    "."
        ::= { tnOpticalPortInfo 194 }

--------------------------------------------------------------------------------
-- UL130SCUP Optical Port Info Table
--------------------------------------------------------------------------------
    tnul130scupPortInfoTable OBJECT-TYPE
        SYNTAX         SEQUENCE OF Tnul130scupPortInfoEntry
        MAX-ACCESS     not-accessible
        STATUS         current
        DESCRIPTION    "The ports on a UL130SCUP optical card."
        ::= { tnOpticalPortInfo 195 }

    tnul130scupPortInfoEntry OBJECT-TYPE
        SYNTAX         Tnul130scupPortInfoEntry
        MAX-ACCESS     not-accessible
        STATUS         current
        DESCRIPTION    "."
        INDEX { ifIndex }
        ::= { tnul130scupPortInfoTable 1 }

    Tnul130scupPortInfoEntry ::=
        SEQUENCE {
            tnul130scupPortInfoFunction  INTEGER
        }

    tnul130scupPortInfoFunction OBJECT-TYPE
        SYNTAX         INTEGER {
                         network(1)
                       }
        MAX-ACCESS     read-only
        STATUS         current
        DESCRIPTION    "Indicates the functional type of this UL130SCUP port."
        ::= { tnul130scupPortInfoEntry 1 }

--------------------------------------------------------------------------------
-- 130SCX10 Optical Port Info Scalar
--------------------------------------------------------------------------------
    tn130scx10PortInfoAttributeTotal OBJECT-TYPE
        SYNTAX         Integer32
        MAX-ACCESS     read-only
        STATUS         current
        DESCRIPTION    "."
        ::= { tnOpticalPortInfo 196 }

--------------------------------------------------------------------------------
-- 130SCX10 Optical Port Info Table
--------------------------------------------------------------------------------
    tn130scx10PortInfoTable OBJECT-TYPE
        SYNTAX         SEQUENCE OF Tn130scx10PortInfoEntry
        MAX-ACCESS     not-accessible
        STATUS         current
        DESCRIPTION    "The ports on a 130SCX10 optical card."
        ::= { tnOpticalPortInfo 197 }

    tn130scx10PortInfoEntry OBJECT-TYPE
        SYNTAX         Tn130scx10PortInfoEntry
        MAX-ACCESS     not-accessible
        STATUS         current
        DESCRIPTION    "."
        INDEX { ifIndex }
        ::= { tn130scx10PortInfoTable 1 }

    Tn130scx10PortInfoEntry ::=
        SEQUENCE {
            tn130scx10PortInfoFunction  INTEGER
        }

    tn130scx10PortInfoFunction OBJECT-TYPE
        SYNTAX         INTEGER {
                         network(1),
                         client(2)
                       }
        MAX-ACCESS     read-only
        STATUS         current
        DESCRIPTION    "Indicates the functional type of this 130SCX10 port."
        ::= { tn130scx10PortInfoEntry 1 }

--------------------------------------------------------------------------------
-- A2P2125 Optical Port Info Scalar
--------------------------------------------------------------------------------
    tnA2p2125PortInfoAttributeTotal OBJECT-TYPE
        SYNTAX         Integer32
        MAX-ACCESS     read-only
        STATUS         current
        DESCRIPTION    "."
        ::= { tnOpticalPortInfo 198 }

--------------------------------------------------------------------------------
-- A2P2125 Optical Port Info Table
--------------------------------------------------------------------------------
    tnA2p2125PortInfoTable OBJECT-TYPE
        SYNTAX         SEQUENCE OF TnA2p2125PortInfoEntry
        MAX-ACCESS     not-accessible
        STATUS         current
        DESCRIPTION    "The ports on a A2P2125 optical card."
        ::= { tnOpticalPortInfo 199 }

    tnA2p2125PortInfoEntry OBJECT-TYPE
        SYNTAX         TnA2p2125PortInfoEntry
        MAX-ACCESS     not-accessible
        STATUS         current
        DESCRIPTION    "."
        INDEX { ifIndex }
        ::= { tnA2p2125PortInfoTable 1 }

    TnA2p2125PortInfoEntry ::=
        SEQUENCE {
            tnA2p2125PortInfoFunction  INTEGER
        }

    tnA2p2125PortInfoFunction OBJECT-TYPE
        SYNTAX         INTEGER {
                         lineIn(1),
                         inv(2),
                         dcm(3),
                         lineOut(4),
                         oscSfp(5),
                         osc(6),
                         custLan(7)
                       }
        MAX-ACCESS     read-only
        STATUS         current
        DESCRIPTION    "Indicates the functional type of this A2P2125 port."
        ::= { tnA2p2125PortInfoEntry 1 }

--------------------------------------------------------------------------------
-- 4QPA8 Optical Port Info Scalar
--------------------------------------------------------------------------------
    tn4qpa8PortInfoAttributeTotal OBJECT-TYPE
        SYNTAX         Integer32
        MAX-ACCESS     read-only
        STATUS         current
        DESCRIPTION    "."
        ::= { tnOpticalPortInfo 200 }

--------------------------------------------------------------------------------
-- 4QPA8 Optical Port Info Table
--------------------------------------------------------------------------------
    tn4qpa8PortInfoTable OBJECT-TYPE
        SYNTAX         SEQUENCE OF Tn4qpa8PortInfoEntry
        MAX-ACCESS     not-accessible
        STATUS         current
        DESCRIPTION    "The ports on a 4QPA8 optical card."
        ::= { tnOpticalPortInfo 201 }

    tn4qpa8PortInfoEntry OBJECT-TYPE
        SYNTAX         Tn4qpa8PortInfoEntry
        MAX-ACCESS     not-accessible
        STATUS         current
        DESCRIPTION    "."
        INDEX { ifIndex }
        ::= { tn4qpa8PortInfoTable 1 }

    Tn4qpa8PortInfoEntry ::=
        SEQUENCE {
            tn4qpa8PortInfoFunction INTEGER
        }

    tn4qpa8PortInfoFunction OBJECT-TYPE
        SYNTAX         INTEGER {
                         network(1),
                         client(2),
                         evoa(3)
                       }
        MAX-ACCESS     read-only
        STATUS         current
        DESCRIPTION    "Indicates the functional type of this 4QPA8 port."
        ::= { tn4qpa8PortInfoEntry 1 }

--------------------------------------------------------------------------------
-- 112PDM11 Optical Port Info Scalar
--------------------------------------------------------------------------------
    tnOt112pdm11PortInfoAttributeTotal OBJECT-TYPE
        SYNTAX         Integer32
        MAX-ACCESS     read-only
        STATUS         current
        DESCRIPTION    "."
        ::= { tnOpticalPortInfo 202 }

--------------------------------------------------------------------------------
-- 112PDM11 Optical Port Info Table
--------------------------------------------------------------------------------
    tnOt112pdm11PortInfoTable OBJECT-TYPE
        SYNTAX         SEQUENCE OF TnOt112pdm11PortInfoEntry
        MAX-ACCESS     not-accessible
        STATUS         current
        DESCRIPTION    "The ports on a 112PDM11 optical card."
        ::= { tnOpticalPortInfo 203 }

    tnOt112pdm11PortInfoEntry OBJECT-TYPE
        SYNTAX         TnOt112pdm11PortInfoEntry
        MAX-ACCESS     not-accessible
        STATUS         current
        DESCRIPTION    "."
        INDEX { ifIndex }
        ::= { tnOt112pdm11PortInfoTable 1 }

    TnOt112pdm11PortInfoEntry ::=
        SEQUENCE {
            tnOt112pdm11PortInfoFunction INTEGER
        }

    tnOt112pdm11PortInfoFunction OBJECT-TYPE
        SYNTAX         INTEGER {
                         network(1),
                         client(2)
                       }
        MAX-ACCESS     read-only
        STATUS         current
        DESCRIPTION    "Indicates the functional type of this 112PDM11 port."
        ::= { tnOt112pdm11PortInfoEntry 1 }

--------------------------------------------------------------------------------
-- WTOCMA Optical Port Info Scalar
--------------------------------------------------------------------------------
    tnWtocmaPortInfoAttributeTotal OBJECT-TYPE
        SYNTAX         Integer32
        MAX-ACCESS     read-only
        STATUS         current
        DESCRIPTION    "."
        ::= { tnOpticalPortInfo 204 }

--------------------------------------------------------------------------------
-- WTOCMA Optical Port Info Table
--------------------------------------------------------------------------------
    tnWtocmaPortInfoTable OBJECT-TYPE
        SYNTAX         SEQUENCE OF TnWtocmaPortInfoEntry
        MAX-ACCESS     not-accessible
        STATUS         current
        DESCRIPTION    "The ports on a WTOCMA optical card."
        ::= { tnOpticalPortInfo 205 }

    tnWtocmaPortInfoEntry OBJECT-TYPE
        SYNTAX         TnWtocmaPortInfoEntry
        MAX-ACCESS     not-accessible
        STATUS         current
        DESCRIPTION    "."
        INDEX { ifIndex }
        ::= { tnWtocmaPortInfoTable 1 }

    TnWtocmaPortInfoEntry ::=
        SEQUENCE {
            tnWtocmaPortInfoFunction            INTEGER,
            tnWtocmaPortInfoPower               Integer32,
            tnWtocmaPortInfoPowerMonitoredPort  Integer32
        }

    tnWtocmaPortInfoFunction OBJECT-TYPE
        SYNTAX         INTEGER {
                         detect(1)
                       }
        MAX-ACCESS     read-only
        STATUS         current
        DESCRIPTION    "Indicates the functional type of this WTOCMA port."
        ::= { tnWtocmaPortInfoEntry 1 }

    tnWtocmaPortInfoPower OBJECT-TYPE
        SYNTAX         Integer32
        UNITS          "mBm"
        MAX-ACCESS     read-only
        STATUS         current
        DESCRIPTION    "The total power into the WTOCMA IN port."
        DEFVAL         { -9900 }
        ::= { tnWtocmaPortInfoEntry 2 }

    tnWtocmaPortInfoPowerMonitoredPort OBJECT-TYPE
        SYNTAX         Integer32
        UNITS          "mBm"
        MAX-ACCESS     read-only
        STATUS         current
        DESCRIPTION    "The total power out of the associated monitored
                        port."
        DEFVAL         { -9900 }
        ::= { tnWtocmaPortInfoEntry 3 }

--------------------------------------------------------------------------------
-- PTPCTL Optical Port Info Scalar
--------------------------------------------------------------------------------
    tnPtpctlPortInfoAttributeTotal OBJECT-TYPE
        SYNTAX         Integer32
        MAX-ACCESS     read-only
        STATUS         current
        DESCRIPTION    "."
        ::= { tnOpticalPortInfo 206 }

--------------------------------------------------------------------------------
-- PTPCTL Optical Port Info Table
--------------------------------------------------------------------------------
    tnPtpctlPortInfoTable OBJECT-TYPE
        SYNTAX         SEQUENCE OF TnPtpctlPortInfoEntry
        MAX-ACCESS     not-accessible
        STATUS         current
        DESCRIPTION    "The ports on a PTPCTL optical card."
        ::= { tnOpticalPortInfo 207 }

    tnPtpctlPortInfoEntry OBJECT-TYPE
        SYNTAX         TnPtpctlPortInfoEntry
        MAX-ACCESS     not-accessible
        STATUS         current
        DESCRIPTION    "."
        INDEX { ifIndex }
        ::= { tnPtpctlPortInfoTable 1 }

    TnPtpctlPortInfoEntry ::=
        SEQUENCE {
            tnPtpctlPortInfoFunction  INTEGER
        }

    tnPtpctlPortInfoFunction OBJECT-TYPE
        SYNTAX         INTEGER {
                         tp(1),
                         bits(2),
                         tod(3)
                       }
        MAX-ACCESS     read-only
        STATUS         current
        DESCRIPTION    "Indicates the functional type of this PTPCTL port."
        ::= { tnPtpctlPortInfoEntry 1 }

--------------------------------------------------------------------------------
-- PTPIO Optical Port Info Scalar
--------------------------------------------------------------------------------
    tnPtpioPortInfoAttributeTotal OBJECT-TYPE
        SYNTAX         Integer32
        MAX-ACCESS     read-only
        STATUS         current
        DESCRIPTION    "."
        ::= { tnOpticalPortInfo 208 }

--------------------------------------------------------------------------------
-- PTPIO Optical Port Info Table
--------------------------------------------------------------------------------
    tnPtpioPortInfoTable OBJECT-TYPE
        SYNTAX         SEQUENCE OF TnPtpioPortInfoEntry
        MAX-ACCESS     not-accessible
        STATUS         current
        DESCRIPTION    "The ports on a PTPIO optical card."
        ::= { tnOpticalPortInfo 209 }

    tnPtpioPortInfoEntry OBJECT-TYPE
        SYNTAX         TnPtpioPortInfoEntry
        MAX-ACCESS     not-accessible
        STATUS         current
        DESCRIPTION    "."
        INDEX { ifIndex }
        ::= { tnPtpioPortInfoTable 1 }

    TnPtpioPortInfoEntry ::=
        SEQUENCE {
            tnPtpioPortInfoFunction  INTEGER
        }

    tnPtpioPortInfoFunction OBJECT-TYPE
        SYNTAX         INTEGER {
                         tp(1),
                         line(2),
                         sig(3),
                         itp(4)
                       }
        MAX-ACCESS     read-only
        STATUS         current
        DESCRIPTION    "Indicates the functional type of this PTPIO port."
        ::= { tnPtpioPortInfoEntry 1 }

--------------------------------------------------------------------------------
-- 24ET1GB Optical Port Info Scalar
--------------------------------------------------------------------------------
    tnIo24et1gbPortInfoAttributeTotal OBJECT-TYPE
        SYNTAX         Integer32
        MAX-ACCESS     read-only
        STATUS         current
        DESCRIPTION    "."
        ::= { tnOpticalPortInfo 210 }

--------------------------------------------------------------------------------
-- 24ET1GB Optical Port Info Table
--------------------------------------------------------------------------------
    tnIo24et1gbPortInfoTable OBJECT-TYPE
        SYNTAX         SEQUENCE OF TnIo24et1gbPortInfoEntry
        MAX-ACCESS     not-accessible
        STATUS         current
        DESCRIPTION    "The ports on a 24ET1GB optical card."
        ::= { tnOpticalPortInfo 211 }

    tnIo24et1gbPortInfoEntry OBJECT-TYPE
        SYNTAX         TnIo24et1gbPortInfoEntry
        MAX-ACCESS     not-accessible
        STATUS         current
        DESCRIPTION    "."
        INDEX { ifIndex }
        ::= { tnIo24et1gbPortInfoTable 1 }

    TnIo24et1gbPortInfoEntry ::=
        SEQUENCE {
            tnIo24et1gbPortInfoFunction INTEGER
        }

    tnIo24et1gbPortInfoFunction OBJECT-TYPE
        SYNTAX         INTEGER {
                         network(1),
                         client(2)
                       }
        MAX-ACCESS     read-only
        STATUS         current
        DESCRIPTION    "Indicates the functional type of this 24ET1GB port."
        ::= { tnIo24et1gbPortInfoEntry 1 }

--------------------------------------------------------------------------------
-- 4AN10G Optical Port Info Scalar
--------------------------------------------------------------------------------
    tnIo4an10gPortInfoAttributeTotal OBJECT-TYPE
        SYNTAX         Integer32
        MAX-ACCESS     read-only
        STATUS         current
        DESCRIPTION    "."
        ::= { tnOpticalPortInfo 212 }

--------------------------------------------------------------------------------
-- 4AN10G Optical Port Info Table
--------------------------------------------------------------------------------
    tnIo4an10gPortInfoTable OBJECT-TYPE
        SYNTAX         SEQUENCE OF TnIo4an10gPortInfoEntry
        MAX-ACCESS     not-accessible
        STATUS         current
        DESCRIPTION    "The ports on a 4AN10G optical card."
        ::= { tnOpticalPortInfo 213 }

    tnIo4an10gPortInfoEntry OBJECT-TYPE
        SYNTAX         TnIo4an10gPortInfoEntry
        MAX-ACCESS     not-accessible
        STATUS         current
        DESCRIPTION    "."
        INDEX { ifIndex }
        ::= { tnIo4an10gPortInfoTable 1 }

    TnIo4an10gPortInfoEntry ::=
        SEQUENCE {
            tnIo4an10gPortInfoFunction INTEGER
        }

    tnIo4an10gPortInfoFunction OBJECT-TYPE
        SYNTAX         INTEGER {
                         network(1),
                         client(2)
                       }
        MAX-ACCESS     read-only
        STATUS         current
        DESCRIPTION    "Indicates the functional type of this 4AN10G port."
        ::= { tnIo4an10gPortInfoEntry 1 }

--------------------------------------------------------------------------------
-- 8ET1GB Optical Port Info Scalar
--------------------------------------------------------------------------------
    tnIo8et1gbPortInfoAttributeTotal OBJECT-TYPE
        SYNTAX         Integer32
        MAX-ACCESS     read-only
        STATUS         current
        DESCRIPTION    "."
        ::= { tnOpticalPortInfo 214 }

--------------------------------------------------------------------------------
-- 8ET1GB Optical Port Info Table
--------------------------------------------------------------------------------
    tnIo8et1gbPortInfoTable OBJECT-TYPE
        SYNTAX         SEQUENCE OF TnIo8et1gbPortInfoEntry
        MAX-ACCESS     not-accessible
        STATUS         current
        DESCRIPTION    "The ports on a 8ET1GB optical card."
        ::= { tnOpticalPortInfo 215 }

    tnIo8et1gbPortInfoEntry OBJECT-TYPE
        SYNTAX         TnIo8et1gbPortInfoEntry
        MAX-ACCESS     not-accessible
        STATUS         current
        DESCRIPTION    "."
        INDEX { ifIndex }
        ::= { tnIo8et1gbPortInfoTable 1 }

    TnIo8et1gbPortInfoEntry ::=
        SEQUENCE {
            tnIo8et1gbPortInfoFunction INTEGER
        }

    tnIo8et1gbPortInfoFunction OBJECT-TYPE
        SYNTAX         INTEGER {
                         network(1),
                         client(2)
                       }
        MAX-ACCESS     read-only
        STATUS         current
        DESCRIPTION    "Indicates the functional type of this 8ET1GB port."
        ::= { tnIo8et1gbPortInfoEntry 1 }

--------------------------------------------------------------------------------
-- 10ET10G Optical Port Info Scalar
--------------------------------------------------------------------------------
    tnIo10et10gPortInfoAttributeTotal OBJECT-TYPE
        SYNTAX         Integer32
        MAX-ACCESS     read-only
        STATUS         current
        DESCRIPTION    "."
        ::= { tnOpticalPortInfo 216 }

--------------------------------------------------------------------------------
-- 10ET10G Optical Port Info Table
--------------------------------------------------------------------------------
    tnIo10et10gPortInfoTable OBJECT-TYPE
        SYNTAX         SEQUENCE OF TnIo10et10gPortInfoEntry
        MAX-ACCESS     not-accessible
        STATUS         current
        DESCRIPTION    "The ports on a 10ET10G optical card."
        ::= { tnOpticalPortInfo 217 }

    tnIo10et10gPortInfoEntry OBJECT-TYPE
        SYNTAX         TnIo10et10gPortInfoEntry
        MAX-ACCESS     not-accessible
        STATUS         current
        DESCRIPTION    "."
        INDEX { ifIndex }
        ::= { tnIo10et10gPortInfoTable 1 }

    TnIo10et10gPortInfoEntry ::=
        SEQUENCE {
            tnIo10et10gPortInfoFunction INTEGER
        }

    tnIo10et10gPortInfoFunction OBJECT-TYPE
        SYNTAX         INTEGER {
                         network(1),
                         client(2)
                       }
        MAX-ACCESS     read-only
        STATUS         current
        DESCRIPTION    "Indicates the functional type of this 10ET10G port."
        ::= { tnIo10et10gPortInfoEntry 1 }

--------------------------------------------------------------------------------
-- UL11QCUPC Optical Port Info Scalar
--------------------------------------------------------------------------------
    tnUl11qcupcPortInfoAttributeTotal OBJECT-TYPE
        SYNTAX         Integer32
        MAX-ACCESS     read-only
        STATUS         current
        DESCRIPTION    "."
        ::= { tnOpticalPortInfo 218 }

--------------------------------------------------------------------------------
-- UL11QCUPC Optical Port Info Table
--------------------------------------------------------------------------------
    tnUl11qcupcPortInfoTable OBJECT-TYPE
        SYNTAX         SEQUENCE OF TnUl11qcupcPortInfoEntry
        MAX-ACCESS     not-accessible
        STATUS         current
        DESCRIPTION    "The ports on a UL11QCUPC optical card."
        ::= { tnOpticalPortInfo 219 }

    tnUl11qcupcPortInfoEntry OBJECT-TYPE
        SYNTAX         TnUl11qcupcPortInfoEntry
        MAX-ACCESS     not-accessible
        STATUS         current
        DESCRIPTION    "."
        INDEX { ifIndex }
        ::= { tnUl11qcupcPortInfoTable 1 }

    TnUl11qcupcPortInfoEntry ::=
        SEQUENCE {
            tnUl11qcupcPortInfoFunction INTEGER
        }

    tnUl11qcupcPortInfoFunction OBJECT-TYPE
        SYNTAX         INTEGER {
                         network(1),
                         evoa(2)
                       }
        MAX-ACCESS     read-only
        STATUS         current
        DESCRIPTION    "Indicates the functional type of this UL11QCUPC port."
        ::= { tnUl11qcupcPortInfoEntry 1 }

--------------------------------------------------------------------------------
-- 520SCX4 Optical Port Info Scalar
--------------------------------------------------------------------------------
    tnOt520scx4PortInfoAttributeTotal OBJECT-TYPE
        SYNTAX         Integer32
        MAX-ACCESS     read-only
        STATUS         current
        DESCRIPTION    "."
        ::= { tnOpticalPortInfo 220 }

--------------------------------------------------------------------------------
-- 520SCX4 Optical Port Info Table
--------------------------------------------------------------------------------
    tnOt520scx4PortInfoTable OBJECT-TYPE
        SYNTAX         SEQUENCE OF TnOt520scx4PortInfoEntry
        MAX-ACCESS     not-accessible
        STATUS         current
        DESCRIPTION    "The ports on a 520SCX4 optical card."
        ::= { tnOpticalPortInfo 221 }

    tnOt520scx4PortInfoEntry OBJECT-TYPE
        SYNTAX         TnOt520scx4PortInfoEntry
        MAX-ACCESS     not-accessible
        STATUS         current
        DESCRIPTION    "."
        INDEX { ifIndex }
        ::= { tnOt520scx4PortInfoTable 1 }

    TnOt520scx4PortInfoEntry ::=
        SEQUENCE {
            tnOt520scx4PortInfoFunction INTEGER
        }

    tnOt520scx4PortInfoFunction OBJECT-TYPE
        SYNTAX         INTEGER {
                         network(1),
                         client(2)
                       }
        MAX-ACCESS     read-only
        STATUS         current
        DESCRIPTION    "Indicates the functional type of this 520SCX4 port."
        ::= { tnOt520scx4PortInfoEntry 1 }

--------------------------------------------------------------------------------
-- Skew Info Table
--------------------------------------------------------------------------------
    tnSkewInfoTable OBJECT-TYPE
        SYNTAX         SEQUENCE OF TnSkewInfoEntry
        MAX-ACCESS     not-accessible
        STATUS         current
        DESCRIPTION    "."
        ::= { tnOpticalPortInfo 222 }

    tnSkewInfoEntry OBJECT-TYPE
        SYNTAX         TnSkewInfoEntry
        MAX-ACCESS     not-accessible
        STATUS         current
        DESCRIPTION    "."
        INDEX { ifIndex }
        ::= { tnSkewInfoTable 1 }

    TnSkewInfoEntry ::=
        SEQUENCE {
            tnSkewInfoString     OCTET STRING
         }

    tnSkewInfoString OBJECT-TYPE
        SYNTAX         OCTET STRING (SIZE(0..256))
        MAX-ACCESS     read-only
        STATUS         current
        DESCRIPTION    "The relative skew between the 20 logical lanes
                        on OTU4.  The string contains the skew for each
                        logical lane separated by spaces.

                        UNIT: ns"
        ::= { tnSkewInfoEntry 1 }

--------------------------------------------------------------------------------
-- Power Filter Port Info Scalar
--------------------------------------------------------------------------------
    tnPowerFilterPortInfoAttributeTotal OBJECT-TYPE
        SYNTAX         Integer32
        MAX-ACCESS     read-only
        STATUS         current
        DESCRIPTION    "."
        ::= { tnOpticalPortInfo 223 }

--------------------------------------------------------------------------------
-- Power Filter Port Info Table
--------------------------------------------------------------------------------
    tnPowerFilterPortInfoTable OBJECT-TYPE
        SYNTAX         SEQUENCE OF TnPowerFilterPortInfoEntry
        MAX-ACCESS     not-accessible
        STATUS         current
        DESCRIPTION    "The ports on a PowerFilter optical card."
        ::= { tnOpticalPortInfo 224 }

    tnPowerFilterPortInfoEntry OBJECT-TYPE
        SYNTAX         TnPowerFilterPortInfoEntry
        MAX-ACCESS     not-accessible
        STATUS         current
        DESCRIPTION    "."
        INDEX { ifIndex }
        ::= { tnPowerFilterPortInfoTable 1 }

    TnPowerFilterPortInfoEntry ::=
        SEQUENCE {
            tnPowerFilterPortInfoFunction INTEGER
        }

    tnPowerFilterPortInfoFunction OBJECT-TYPE
        SYNTAX         INTEGER {
                         oneTru(1)
                       }
        MAX-ACCESS     read-only
        STATUS         current
        DESCRIPTION    "Indicates the functional type of this PowerFilter port."
        ::= { tnPowerFilterPortInfoEntry 1 }

--------------------------------------------------------------------------------
-- 11OPE8 Optical Port Info Scalar
--------------------------------------------------------------------------------
    tn11ope8PortInfoAttributeTotal OBJECT-TYPE
        SYNTAX         Integer32
        MAX-ACCESS     read-only
        STATUS         current
        DESCRIPTION    "."
        ::= { tnOpticalPortInfo 225 }

--------------------------------------------------------------------------------
-- 11OPE8 Optical Port Info Table
--------------------------------------------------------------------------------
    tn11ope8PortInfoTable OBJECT-TYPE
        SYNTAX         SEQUENCE OF Tn11ope8PortInfoEntry
        MAX-ACCESS     not-accessible
        STATUS         current
        DESCRIPTION    "The ports on a 11OPE8 optical card."
        ::= { tnOpticalPortInfo 226 }

    tn11ope8PortInfoEntry OBJECT-TYPE
        SYNTAX         Tn11ope8PortInfoEntry
        MAX-ACCESS     not-accessible
        STATUS         current
        DESCRIPTION    "."
        INDEX { ifIndex }
        ::= { tn11ope8PortInfoTable 1 }

    Tn11ope8PortInfoEntry ::=
        SEQUENCE {
            tn11ope8PortInfoFunction INTEGER
        }

    tn11ope8PortInfoFunction OBJECT-TYPE
        SYNTAX         INTEGER {
                         network(1),
                         client(2),
                         evoa(3),
                         backplane(4),
                         tod(5),
                         ethman(6)
                       }
        MAX-ACCESS     read-only
        STATUS         current
        DESCRIPTION    "Indicates the functional type of this 11OPE8 port."
        ::= { tn11ope8PortInfoEntry 1 }

--------------------------------------------------------------------------------
-- 11QCE12X Optical Port Info Scalar
--------------------------------------------------------------------------------
    tn11qce12xPortInfoAttributeTotal OBJECT-TYPE
        SYNTAX         Integer32
        MAX-ACCESS     read-only
        STATUS         current
        DESCRIPTION    "."
        ::= { tnOpticalPortInfo 227 }

--------------------------------------------------------------------------------
-- 11QCE12X Optical Port Info Table
--------------------------------------------------------------------------------
    tn11qce12xPortInfoTable OBJECT-TYPE
        SYNTAX         SEQUENCE OF Tn11qce12xPortInfoEntry
        MAX-ACCESS     not-accessible
        STATUS         current
        DESCRIPTION    "The ports on a 11QCE12X optical card."
        ::= { tnOpticalPortInfo 228 }

    tn11qce12xPortInfoEntry OBJECT-TYPE
        SYNTAX         Tn11qce12xPortInfoEntry
        MAX-ACCESS     not-accessible
        STATUS         current
        DESCRIPTION    "."
        INDEX { ifIndex }
        ::= { tn11qce12xPortInfoTable 1 }

    Tn11qce12xPortInfoEntry ::=
        SEQUENCE {
            tn11qce12xPortInfoFunction INTEGER
        }

    tn11qce12xPortInfoFunction OBJECT-TYPE
        SYNTAX         INTEGER {
                         network(1),
                         client(2),
                         evoa(3),
                         backplane(4),
                         tod(5),
                         bits(6),
                         ethman(7)
                       }
        MAX-ACCESS     read-only
        STATUS         current
        DESCRIPTION    "Indicates the functional type of this 11QCE12X port."
        ::= { tn11qce12xPortInfoEntry 1 }

--------------------------------------------------------------------------------
-- AM2625A Optical Port Info Scalar
--------------------------------------------------------------------------------
    tnAm2625aPortInfoAttributeTotal OBJECT-TYPE
        SYNTAX         Integer32
        MAX-ACCESS     read-only
        STATUS         current
        DESCRIPTION    "."
        ::= { tnOpticalPortInfo 229 }

--------------------------------------------------------------------------------
-- AM2625A Optical Port Info Table
--------------------------------------------------------------------------------
    tnAm2625aPortInfoTable OBJECT-TYPE
        SYNTAX         SEQUENCE OF TnAm2625aPortInfoEntry
        MAX-ACCESS     not-accessible
        STATUS         current
        DESCRIPTION    "The ports on an AM2625A optical card."
        ::= { tnOpticalPortInfo 230 }

    tnAm2625aPortInfoEntry OBJECT-TYPE
        SYNTAX         TnAm2625aPortInfoEntry
        MAX-ACCESS     not-accessible
        STATUS         current
        DESCRIPTION    "."
        INDEX { ifIndex }
        ::= { tnAm2625aPortInfoTable 1 }

    TnAm2625aPortInfoEntry ::=
        SEQUENCE {
            tnAm2625aPortInfoFunction INTEGER
        }

    tnAm2625aPortInfoFunction OBJECT-TYPE
        SYNTAX         INTEGER {
                         lineIn(1),
                         inv(2),
                         dcm(3),
                         lineOut(4),
                         oscSfp(5),
                         det(6),
                         osc(7),
                         custLan(8)
                       }
        MAX-ACCESS     read-only
        STATUS         current
        DESCRIPTION    "Indicates the functional type of this AM2625A port."
        ::= { tnAm2625aPortInfoEntry 1 }

--------------------------------------------------------------------------------
-- AM2032A Optical Port Info Scalar
--------------------------------------------------------------------------------
    tnAm2032aPortInfoAttributeTotal OBJECT-TYPE
        SYNTAX         Integer32
        MAX-ACCESS     read-only
        STATUS         current
        DESCRIPTION    "."
        ::= { tnOpticalPortInfo 231 }

--------------------------------------------------------------------------------
-- AM2032A Optical Port Info Table
--------------------------------------------------------------------------------
    tnAm2032aPortInfoTable OBJECT-TYPE
        SYNTAX         SEQUENCE OF TnAm2032aPortInfoEntry
        MAX-ACCESS     not-accessible
        STATUS         current
        DESCRIPTION    "The ports on an AM2032A optical card."
        ::= { tnOpticalPortInfo 232 }

    tnAm2032aPortInfoEntry OBJECT-TYPE
        SYNTAX         TnAm2032aPortInfoEntry
        MAX-ACCESS     not-accessible
        STATUS         current
        DESCRIPTION    "."
        INDEX { ifIndex }
        ::= { tnAm2032aPortInfoTable 1 }

    TnAm2032aPortInfoEntry ::=
        SEQUENCE {
            tnAm2032aPortInfoFunction INTEGER
        }

    tnAm2032aPortInfoFunction OBJECT-TYPE
        SYNTAX         INTEGER {
                         lineIn(1),
                         inv(2),
                         dcm(3),
                         lineOut(4),
                         oscSfp(5),
                         det(6),
                         osc(7),
                         custLan(8)
                       }
        MAX-ACCESS     read-only
        STATUS         current
        DESCRIPTION    "Indicates the functional type of this AM2032A port."
        ::= { tnAm2032aPortInfoEntry 1 }

--------------------------------------------------------------------------------
-- OT260SCX2 Optical Port Info Scalar
--------------------------------------------------------------------------------
    tnOt260scx2PortInfoAttributeTotal OBJECT-TYPE
        SYNTAX         Integer32
        MAX-ACCESS     read-only
        STATUS         current
        DESCRIPTION    "."
        ::= { tnOpticalPortInfo 233 }

--------------------------------------------------------------------------------
-- OT260SCX2 Optical Port Info Table
--------------------------------------------------------------------------------
    tnOt260scx2PortInfoTable OBJECT-TYPE
        SYNTAX         SEQUENCE OF TnOt260scx2PortInfoEntry
        MAX-ACCESS     not-accessible
        STATUS         current
        DESCRIPTION    "The ports on a OT260SCX2 optical card."
        ::= { tnOpticalPortInfo 234 }

    tnOt260scx2PortInfoEntry OBJECT-TYPE
        SYNTAX         TnOt260scx2PortInfoEntry
        MAX-ACCESS     not-accessible
        STATUS         current
        DESCRIPTION    "."
        INDEX { ifIndex }
        ::= { tnOt260scx2PortInfoTable 1 }

    TnOt260scx2PortInfoEntry ::=
        SEQUENCE {
            tnOt260scx2PortInfoFunction INTEGER
        }

    tnOt260scx2PortInfoFunction OBJECT-TYPE
        SYNTAX         INTEGER {
                         network(1),
                         client(2)
                       }
        MAX-ACCESS     read-only
        STATUS         current
        DESCRIPTION    "Indicates the functional type of this OT260SCX2 port."
        ::= { tnOt260scx2PortInfoEntry 1 }

--------------------------------------------------------------------------------
-- OT130SNX10 Optical Port Info Scalar
--------------------------------------------------------------------------------
    tnOt130snx10PortInfoAttributeTotal OBJECT-TYPE
        SYNTAX         Integer32
        MAX-ACCESS     read-only
        STATUS         current
        DESCRIPTION    "."
        ::= { tnOpticalPortInfo 235 }

--------------------------------------------------------------------------------
-- OT130SNX10 Optical Port Info Table
--------------------------------------------------------------------------------
    tnOt130snx10PortInfoTable OBJECT-TYPE
        SYNTAX         SEQUENCE OF TnOt130snx10PortInfoEntry
        MAX-ACCESS     not-accessible
        STATUS         current
        DESCRIPTION    "The ports on a OT130SNX10 optical card."
        ::= { tnOpticalPortInfo 236 }

    tnOt130snx10PortInfoEntry OBJECT-TYPE
        SYNTAX         TnOt130snx10PortInfoEntry
        MAX-ACCESS     not-accessible
        STATUS         current
        DESCRIPTION    "."
        INDEX { ifIndex }
        ::= { tnOt130snx10PortInfoTable 1 }

    TnOt130snx10PortInfoEntry ::=
        SEQUENCE {
            tnOt130snx10PortInfoFunction  INTEGER
        }

    tnOt130snx10PortInfoFunction OBJECT-TYPE
        SYNTAX         INTEGER {
                         network(1),
                         client(2)
                       }
        MAX-ACCESS     read-only
        STATUS         current
        DESCRIPTION    "Indicates the functional type of this OT130SNX10 port."
        ::= { tnOt130snx10PortInfoEntry 1 }

--------------------------------------------------------------------------------
-- IO24ANMB Optical Port Info Scalar
--------------------------------------------------------------------------------
    tnIo24anmbPortInfoAttributeTotal OBJECT-TYPE
        SYNTAX         Integer32
        MAX-ACCESS     read-only
        STATUS         current
        DESCRIPTION    "."
        ::= { tnOpticalPortInfo 237 }

--------------------------------------------------------------------------------
-- IO24ANMB Optical Port Info Table
--------------------------------------------------------------------------------
    tnIo24anmbPortInfoTable OBJECT-TYPE
        SYNTAX         SEQUENCE OF TnIo24anmbPortInfoEntry
        MAX-ACCESS     not-accessible
        STATUS         current
        DESCRIPTION    "The ports on a IO24ANMB optical card."
        ::= { tnOpticalPortInfo 238 }

    tnIo24anmbPortInfoEntry OBJECT-TYPE
        SYNTAX         TnIo24anmbPortInfoEntry
        MAX-ACCESS     not-accessible
        STATUS         current
        DESCRIPTION    "."
        INDEX { ifIndex }
        ::= { tnIo24anmbPortInfoTable 1 }

    TnIo24anmbPortInfoEntry ::=
        SEQUENCE {
            tnIo24anmbPortInfoFunction INTEGER
        }

    tnIo24anmbPortInfoFunction OBJECT-TYPE
        SYNTAX         INTEGER {
                         client(1)
                       }
        MAX-ACCESS     read-only
        STATUS         current
        DESCRIPTION    "Indicates the functional type of this IO24ANMB port."
        ::= { tnIo24anmbPortInfoEntry 1 }

--------------------------------------------------------------------------------
-- OT11DPM8 Optical Port Info Scalar
--------------------------------------------------------------------------------
    tnOt11dpm8PortInfoAttributeTotal OBJECT-TYPE
        SYNTAX         Integer32
        MAX-ACCESS     read-only
        STATUS         current
        DESCRIPTION    "."
        ::= { tnOpticalPortInfo 239 }

--------------------------------------------------------------------------------
-- OT11DPM8 Optical Port Info Table
--------------------------------------------------------------------------------
    tnOt11dpm8PortInfoTable OBJECT-TYPE
        SYNTAX         SEQUENCE OF TnOt11dpm8PortInfoEntry
        MAX-ACCESS     not-accessible
        STATUS         current
        DESCRIPTION    "The ports on a OT11DPM8 optical card."
        ::= { tnOpticalPortInfo 240 }

    tnOt11dpm8PortInfoEntry OBJECT-TYPE
        SYNTAX         TnOt11dpm8PortInfoEntry
        MAX-ACCESS     not-accessible
        STATUS         current
        DESCRIPTION    "."
        INDEX { ifIndex }
        ::= { tnOt11dpm8PortInfoTable 1 }

    TnOt11dpm8PortInfoEntry ::=
        SEQUENCE {
            tnOt11dpm8PortInfoFunction INTEGER
        }

    tnOt11dpm8PortInfoFunction OBJECT-TYPE
        SYNTAX         INTEGER {
                         network(1),
                         client(2),
                         evoa(3)
                       }
        MAX-ACCESS     read-only
        STATUS         current
        DESCRIPTION    "Indicates the functional type of this OT11DPM8 port."
        ::= { tnOt11dpm8PortInfoEntry 1 }

--------------------------------------------------------------------------------
-- OT11DPM4M Optical Port Info Scalar
--------------------------------------------------------------------------------
    tnOt11dpm4mPortInfoAttributeTotal OBJECT-TYPE
        SYNTAX         Integer32
        MAX-ACCESS     read-only
        STATUS         current
        DESCRIPTION    "."
        ::= { tnOpticalPortInfo 241 }

--------------------------------------------------------------------------------
-- OT11DPM4M Optical Port Info Table
--------------------------------------------------------------------------------
    tnOt11dpm4mPortInfoTable OBJECT-TYPE
        SYNTAX         SEQUENCE OF TnOt11dpm4mPortInfoEntry
        MAX-ACCESS     not-accessible
        STATUS         current
        DESCRIPTION    "The ports on a OT11DPM4M optical card."
        ::= { tnOpticalPortInfo 242 }

    tnOt11dpm4mPortInfoEntry OBJECT-TYPE
        SYNTAX         TnOt11dpm4mPortInfoEntry
        MAX-ACCESS     not-accessible
        STATUS         current
        DESCRIPTION    "."
        INDEX { ifIndex }
        ::= { tnOt11dpm4mPortInfoTable 1 }

    TnOt11dpm4mPortInfoEntry ::=
        SEQUENCE {
            tnOt11dpm4mPortInfoFunction INTEGER
        }

    tnOt11dpm4mPortInfoFunction OBJECT-TYPE
        SYNTAX         INTEGER {
                         network(1),
                         client(2)
                       }
        MAX-ACCESS     read-only
        STATUS         current
        DESCRIPTION    "Indicates the functional type of this OT11DPM4M port."
        ::= { tnOt11dpm4mPortInfoEntry 1 }

--------------------------------------------------------------------------------
-- UL130SCUPB Optical Port Info Scalar
--------------------------------------------------------------------------------
    tnUl130scupbPortInfoAttributeTotal OBJECT-TYPE
        SYNTAX         Integer32
        MAX-ACCESS     read-only
        STATUS         current
        DESCRIPTION    "."
        ::= { tnOpticalPortInfo 243 }

--------------------------------------------------------------------------------
-- UL130SCUPB Optical Port Info Table
--------------------------------------------------------------------------------
    tnUl130scupbPortInfoTable OBJECT-TYPE
        SYNTAX         SEQUENCE OF TnUl130scupbPortInfoEntry
        MAX-ACCESS     not-accessible
        STATUS         current
        DESCRIPTION    "The ports on a UL130SCUPB optical card."
        ::= { tnOpticalPortInfo 244 }

    tnUl130scupbPortInfoEntry OBJECT-TYPE
        SYNTAX         TnUl130scupbPortInfoEntry
        MAX-ACCESS     not-accessible
        STATUS         current
        DESCRIPTION    "."
        INDEX { ifIndex }
        ::= { tnUl130scupbPortInfoTable 1 }

    TnUl130scupbPortInfoEntry ::=
        SEQUENCE {
            tnUl130scupbPortInfoFunction  INTEGER
        }

    tnUl130scupbPortInfoFunction OBJECT-TYPE
        SYNTAX         INTEGER {
                         network(1)
                       }
        MAX-ACCESS     read-only
        STATUS         current
        DESCRIPTION    "Indicates the functional type of this UL130SCUPB port."
        ::= { tnUl130scupbPortInfoEntry 1 }

--------------------------------------------------------------------------------
-- OT112SDX11 Optical Port Info Scalar
--------------------------------------------------------------------------------
    tnOt112sdx11PortInfoAttributeTotal OBJECT-TYPE
        SYNTAX         Integer32
        MAX-ACCESS     read-only
        STATUS         current
        DESCRIPTION    "."
        ::= { tnOpticalPortInfo 245 }

--------------------------------------------------------------------------------
-- OT112SDX11 Optical Port Info Table
--------------------------------------------------------------------------------
    tnOt112sdx11PortInfoTable OBJECT-TYPE
        SYNTAX         SEQUENCE OF TnOt112sdx11PortInfoEntry
        MAX-ACCESS     not-accessible
        STATUS         current
        DESCRIPTION    "The ports on a OT112SDX11 optical card."
        ::= { tnOpticalPortInfo 246 }

    tnOt112sdx11PortInfoEntry OBJECT-TYPE
        SYNTAX         TnOt112sdx11PortInfoEntry
        MAX-ACCESS     not-accessible
        STATUS         current
        DESCRIPTION    "."
        INDEX { ifIndex }
        ::= { tnOt112sdx11PortInfoTable 1 }

    TnOt112sdx11PortInfoEntry ::=
        SEQUENCE {
            tnOt112sdx11PortInfoFunction  INTEGER,
            tnOt112sdx11PortInfoAggrRate  INTEGER
        }

    tnOt112sdx11PortInfoFunction OBJECT-TYPE
        SYNTAX         INTEGER {
                         network(1),
                         client(2)
                       }
        MAX-ACCESS     read-only
        STATUS         current
        DESCRIPTION    "Indicates the functional type of this OT112SDX11 port."
        ::= { tnOt112sdx11PortInfoEntry 1 }

    tnOt112sdx11PortInfoAggrRate OBJECT-TYPE
        SYNTAX         INTEGER {
                         elan40Gb(1),
                         elan100Gb(2)
                       }
        MAX-ACCESS     read-only
        STATUS         current
        DESCRIPTION    "Indicates the Aggregation Ethernet signal rate
                        attached on the first lane of 112SDX11 client
                        ports."
        ::= { tnOt112sdx11PortInfoEntry 2 }

--------------------------------------------------------------------------------
-- AA2DONW Optical Port Info Scalar
--------------------------------------------------------------------------------
    tnAa2donwPortInfoAttributeTotal OBJECT-TYPE
        SYNTAX         Integer32
        MAX-ACCESS     read-only
        STATUS         current
        DESCRIPTION    "."
        ::= { tnOpticalPortInfo 247 }

--------------------------------------------------------------------------------
-- AA2DONW Optical Port Info Table
--------------------------------------------------------------------------------
    tnAa2donwPortInfoTable OBJECT-TYPE
        SYNTAX         SEQUENCE OF TnAa2donwPortInfoEntry
        MAX-ACCESS     not-accessible
        STATUS         current
        DESCRIPTION    "The ports on an AA2DONW optical card."
        ::= { tnOpticalPortInfo 248 }

    tnAa2donwPortInfoEntry OBJECT-TYPE
        SYNTAX         TnAa2donwPortInfoEntry
        MAX-ACCESS     not-accessible
        STATUS         current
        DESCRIPTION    "."
        INDEX { ifIndex }
        ::= { tnAa2donwPortInfoTable 1 }

    TnAa2donwPortInfoEntry ::=
        SEQUENCE {
            tnAa2donwPortInfoFunction  INTEGER
        }

    tnAa2donwPortInfoFunction OBJECT-TYPE
        SYNTAX         INTEGER {
                         line(1),
                         signal(2),
                         inv(3),
                         osc(4),
                         oscSfp(5)
                       }
        MAX-ACCESS     read-only
        STATUS         current
        DESCRIPTION    "Indicates the functional type of this AA2DONW port."
        ::= { tnAa2donwPortInfoEntry 1 }

--------------------------------------------------------------------------------
-- 130SCA1 Optical Port Info Scalar
--------------------------------------------------------------------------------
    tnOt130sca1PortInfoAttributeTotal OBJECT-TYPE
        SYNTAX         Integer32
        MAX-ACCESS     read-only
        STATUS         current
        DESCRIPTION    "."
        ::= { tnOpticalPortInfo 249 }

--------------------------------------------------------------------------------
-- 130SCA1 Optical Port Info Table
--------------------------------------------------------------------------------
    tnOt130sca1PortInfoTable OBJECT-TYPE
        SYNTAX         SEQUENCE OF TnOt130sca1PortInfoEntry
        MAX-ACCESS     not-accessible
        STATUS         current
        DESCRIPTION    "The ports on a 130SCA1 optical card."
        ::= { tnOpticalPortInfo 250 }

    tnOt130sca1PortInfoEntry OBJECT-TYPE
        SYNTAX         TnOt130sca1PortInfoEntry
        MAX-ACCESS     not-accessible
        STATUS         current
        DESCRIPTION    "."
        INDEX { ifIndex }
        ::= { tnOt130sca1PortInfoTable 1 }

    TnOt130sca1PortInfoEntry ::=
        SEQUENCE {
            tnOt130sca1PortInfoFunction INTEGER
        }

    tnOt130sca1PortInfoFunction OBJECT-TYPE
        SYNTAX         INTEGER {
                         network(1),
                         client(2)
                       }
        MAX-ACCESS     read-only
        STATUS         current
        DESCRIPTION    "Indicates the functional type of this 130SCA1 port."
        ::= { tnOt130sca1PortInfoEntry 1 }

--------------------------------------------------------------------------------
-- 10AN10GB Optical Port Info Scalar
--------------------------------------------------------------------------------
    tnIo10an10gbPortInfoAttributeTotal OBJECT-TYPE
        SYNTAX         Integer32
        MAX-ACCESS     read-only
        STATUS         current
        DESCRIPTION    "."
        ::= { tnOpticalPortInfo 251 }

--------------------------------------------------------------------------------
-- 10AN10GB Optical Port Info Table
--------------------------------------------------------------------------------
    tnIo10an10gbPortInfoTable OBJECT-TYPE
        SYNTAX         SEQUENCE OF TnIo10an10gbPortInfoEntry
        MAX-ACCESS     not-accessible
        STATUS         current
        DESCRIPTION    "The ports on a 10AN10GB optical card."
        ::= { tnOpticalPortInfo 252 }

    tnIo10an10gbPortInfoEntry OBJECT-TYPE
        SYNTAX         TnIo10an10gbPortInfoEntry
        MAX-ACCESS     not-accessible
        STATUS         current
        DESCRIPTION    "."
        INDEX { ifIndex }
        ::= { tnIo10an10gbPortInfoTable 1 }

    TnIo10an10gbPortInfoEntry ::=
        SEQUENCE {
            tnIo10an10gbPortInfoFunction INTEGER
        }

    tnIo10an10gbPortInfoFunction OBJECT-TYPE
        SYNTAX         INTEGER {
                         network(1),
                         client(2)
                       }
        MAX-ACCESS     read-only
        STATUS         current
        DESCRIPTION    "Indicates the functional type of this 10AN10GB port."
        ::= { tnIo10an10gbPortInfoEntry 1 }

--------------------------------------------------------------------------------
-- 10ET10GB Optical Port Info Scalar
--------------------------------------------------------------------------------
    tnIo10et10gbPortInfoAttributeTotal OBJECT-TYPE
        SYNTAX         Integer32
        MAX-ACCESS     read-only
        STATUS         current
        DESCRIPTION    "."
        ::= { tnOpticalPortInfo 253 }

--------------------------------------------------------------------------------
-- 10ET10GB Optical Port Info Table
--------------------------------------------------------------------------------
    tnIo10et10gbPortInfoTable OBJECT-TYPE
        SYNTAX         SEQUENCE OF TnIo10et10gbPortInfoEntry
        MAX-ACCESS     not-accessible
        STATUS         current
        DESCRIPTION    "The ports on a 10ET10GB optical card."
        ::= { tnOpticalPortInfo 254 }

    tnIo10et10gbPortInfoEntry OBJECT-TYPE
        SYNTAX         TnIo10et10gbPortInfoEntry
        MAX-ACCESS     not-accessible
        STATUS         current
        DESCRIPTION    "."
        INDEX { ifIndex }
        ::= { tnIo10et10gbPortInfoTable 1 }

    TnIo10et10gbPortInfoEntry ::=
        SEQUENCE {
            tnIo10et10gbPortInfoFunction INTEGER
        }

    tnIo10et10gbPortInfoFunction OBJECT-TYPE
        SYNTAX         INTEGER {
                         network(1),
                         client(2)
                       }
        MAX-ACCESS     read-only
        STATUS         current
        DESCRIPTION    "Indicates the functional type of this 10ET10GB port."
        ::= { tnIo10et10gbPortInfoEntry 1 }

--------------------------------------------------------------------------------
-- WR20-TF Optical Port Info Scalar
--------------------------------------------------------------------------------
    tnWr20tfPortInfoAttributeTotal OBJECT-TYPE
        SYNTAX         Integer32
        MAX-ACCESS     read-only
        STATUS         current
        DESCRIPTION    "."
        ::= { tnOpticalPortInfo 255 }

--------------------------------------------------------------------------------
-- WR20-TF Optical Port Info Table
--------------------------------------------------------------------------------
    tnWr20tfPortInfoTable OBJECT-TYPE
        SYNTAX         SEQUENCE OF TnWr20tfPortInfoEntry
        MAX-ACCESS     not-accessible
        STATUS         current
        DESCRIPTION    "The ports on a WR20-TF optical card."
        ::= { tnOpticalPortInfo 256 }

    tnWr20tfPortInfoEntry OBJECT-TYPE
        SYNTAX         TnWr20tfPortInfoEntry
        MAX-ACCESS     not-accessible
        STATUS         current
        DESCRIPTION    "."
        INDEX { ifIndex }
        ::= { tnWr20tfPortInfoTable 1 }

    TnWr20tfPortInfoEntry ::=
        SEQUENCE {
            tnWr20tfPortInfoFunction INTEGER
        }

    tnWr20tfPortInfoFunction OBJECT-TYPE
        SYNTAX         INTEGER {
                         signal(1),
                         adt(2),
                         ad(3),
                         inv(4)
                       }
        MAX-ACCESS     read-only
        STATUS         current
        DESCRIPTION    "Indicates the functional type of this WR20-TF port."
        ::= { tnWr20tfPortInfoEntry 1 }

--------------------------------------------------------------------------------
-- WSS Optical Port Info Scalar
--------------------------------------------------------------------------------
    tnWssPortInfoAttributeTotal OBJECT-TYPE
        SYNTAX         Integer32
        MAX-ACCESS     read-only
        STATUS         current
        DESCRIPTION    "."
        ::= { tnOpticalPortInfo 257 }

--------------------------------------------------------------------------------
-- WSS Optical Port Info Table
--------------------------------------------------------------------------------
    tnWssPortInfoTable OBJECT-TYPE
        SYNTAX         SEQUENCE OF TnWssPortInfoEntry
        MAX-ACCESS     not-accessible
        STATUS         current
        DESCRIPTION    "The ports on a WSS optical card."
        ::= { tnOpticalPortInfo 258 }

    tnWssPortInfoEntry OBJECT-TYPE
        SYNTAX         TnWssPortInfoEntry
        MAX-ACCESS     not-accessible
        STATUS         current
        DESCRIPTION    "."
        INDEX { ifIndex }
        ::= { tnWssPortInfoTable 1 }

    TnWssPortInfoEntry ::=
        SEQUENCE {
            tnWssPortInfoRelativeAttenuationMinIn       Unsigned32,
            tnWssPortInfoRelativeAttenuationMinOut      Unsigned32,
            tnWssPortInfoRelativeAverageAttenuationIn   Unsigned32,
            tnWssPortInfoRelativeAverageAttenuationOut  Unsigned32,
            tnWssPortInfoLossFromInToCommon             Integer32,
            tnWssPortInfoCurrentLossFromInToCommon      Integer32
        }

    tnWssPortInfoRelativeAttenuationMinIn OBJECT-TYPE
        SYNTAX         Unsigned32
        UNITS          "mB"
        MAX-ACCESS     read-only
        STATUS         current
        DESCRIPTION    "WR20-TF: The minimum attenuation on the WSS for
                                 the channels on the ADT or AD In port
                                 to SIG Out path.

                        Current range: 0 to 1500."
        DEFVAL         { 0 }
        ::= { tnWssPortInfoEntry 1 }

    tnWssPortInfoRelativeAttenuationMinOut OBJECT-TYPE
        SYNTAX         Unsigned32
        UNITS          "mB"
        MAX-ACCESS     read-only
        STATUS         current
        DESCRIPTION    "WR20-TF: The minimum attenuation on the WSS for
                                 the channels on the Sig In to ADT or AD
                                 Out port path.

                        Current range: 0 to 1500."
        DEFVAL         { 0 }
        ::= { tnWssPortInfoEntry 2 }

    tnWssPortInfoRelativeAverageAttenuationIn OBJECT-TYPE
        SYNTAX         Unsigned32
        UNITS          "mB"
        MAX-ACCESS     read-only
        STATUS         current
        DESCRIPTION    "WR20-TF: The average attenuation on the WSS for
                                 the channels on the ADT or AD In port
                                 to SIG Out path.

                        Current range: 0 to 1500."
        ::= { tnWssPortInfoEntry 3 }

    tnWssPortInfoRelativeAverageAttenuationOut OBJECT-TYPE
        SYNTAX         Unsigned32
        UNITS          "mB"
        MAX-ACCESS     read-only
        STATUS         current
        DESCRIPTION    "WR20-TF: The average attenuation on the WSS for
                                 the channels on the Sig In to ADT or
                                 AD Out port path.

                        Current range: 0 to 1500."
        ::= { tnWssPortInfoEntry 4 }

    tnWssPortInfoLossFromInToCommon OBJECT-TYPE
        SYNTAX         Integer32
        UNITS          "mB"
        MAX-ACCESS     read-only
        STATUS         current
        DESCRIPTION    "The measured loss during commissioning from input
                        port to SIG Out

                        Current range: -9900 to 9900."
        DEFVAL         { -9900 }
        ::= { tnWssPortInfoEntry 5 }

    tnWssPortInfoCurrentLossFromInToCommon OBJECT-TYPE
        SYNTAX         Integer32
        UNITS          "mB"
        MAX-ACCESS     read-only
        STATUS         current
        DESCRIPTION    "The most recent measured loss from input port
                        to SIG Out.

                        Current range: -9900 to 9900."
        DEFVAL         { -9900 }
        ::= { tnWssPortInfoEntry 6 }

--------------------------------------------------------------------------------
-- WTOCMF Optical Port Info Scalar
--------------------------------------------------------------------------------
    tnWtocmfPortInfoAttributeTotal OBJECT-TYPE
        SYNTAX         Integer32
        MAX-ACCESS     read-only
        STATUS         current
        DESCRIPTION    "."
        ::= { tnOpticalPortInfo 259 }

--------------------------------------------------------------------------------
-- WTOCMF Optical Port Info Table
--------------------------------------------------------------------------------
    tnWtocmfPortInfoTable OBJECT-TYPE
        SYNTAX         SEQUENCE OF TnWtocmfPortInfoEntry
        MAX-ACCESS     not-accessible
        STATUS         current
        DESCRIPTION    "The ports on a WTOCMF optical card."
        ::= { tnOpticalPortInfo 260 }

    tnWtocmfPortInfoEntry OBJECT-TYPE
        SYNTAX         TnWtocmfPortInfoEntry
        MAX-ACCESS     not-accessible
        STATUS         current
        DESCRIPTION    "."
        INDEX { ifIndex }
        ::= { tnWtocmfPortInfoTable 1 }

    TnWtocmfPortInfoEntry ::=
        SEQUENCE {
            tnWtocmfPortInfoFunction  INTEGER
        }

    tnWtocmfPortInfoFunction OBJECT-TYPE
        SYNTAX         INTEGER {
                         detect(1)
                       }
        MAX-ACCESS     read-only
        STATUS         current
        DESCRIPTION    "Indicates the functional type of this WTOCMF port."
        ::= { tnWtocmfPortInfoEntry 1 }

--------------------------------------------------------------------------------
-- ASWG Optical Port Info Scalar
--------------------------------------------------------------------------------
    tnAswgPortInfoAttributeTotal OBJECT-TYPE
        SYNTAX         Integer32
        MAX-ACCESS     read-only
        STATUS         current
        DESCRIPTION    "."
        ::= { tnOpticalPortInfo 261 }

--------------------------------------------------------------------------------
-- ASWG Optical Port Info Table
--------------------------------------------------------------------------------
    tnAswgPortInfoTable OBJECT-TYPE
        SYNTAX         SEQUENCE OF TnAswgPortInfoEntry
        MAX-ACCESS     not-accessible
        STATUS         current
        DESCRIPTION    "The ports on a ASWG optical card."
        ::= { tnOpticalPortInfo 262 }

    tnAswgPortInfoEntry OBJECT-TYPE
        SYNTAX         TnAswgPortInfoEntry
        MAX-ACCESS     not-accessible
        STATUS         current
        DESCRIPTION    "."
        INDEX { ifIndex }
        ::= { tnAswgPortInfoTable 1 }

    TnAswgPortInfoEntry ::=
        SEQUENCE {
            tnAswgPortInfoFunction  INTEGER
        }

    tnAswgPortInfoFunction OBJECT-TYPE
        SYNTAX         INTEGER {
                         lineIn(1),
                         otdrRx(2),
                         otdrTx(3),
                         lineOut(4),
                         oscSfp(5),
                         osc(6),
                         custLan(7),
                         inv(8)
                       }
        MAX-ACCESS     read-only
        STATUS         current
        DESCRIPTION    "Indicates the functional type of this ASWG port."
        ::= { tnAswgPortInfoEntry 1 }

--------------------------------------------------------------------------------
-- A4PSWG Optical Port Info Scalar
--------------------------------------------------------------------------------
    tnA4pswgPortInfoAttributeTotal OBJECT-TYPE
        SYNTAX         Integer32
        MAX-ACCESS     read-only
        STATUS         current
        DESCRIPTION    "."
        ::= { tnOpticalPortInfo 263 }

--------------------------------------------------------------------------------
-- A4PSWG Optical Port Info Table
--------------------------------------------------------------------------------
    tnA4pswgPortInfoTable OBJECT-TYPE
        SYNTAX         SEQUENCE OF TnA4pswgPortInfoEntry
        MAX-ACCESS     not-accessible
        STATUS         current
        DESCRIPTION    "The ports on a A4PSWG optical card."
        ::= { tnOpticalPortInfo 264 }

    tnA4pswgPortInfoEntry OBJECT-TYPE
        SYNTAX         TnA4pswgPortInfoEntry
        MAX-ACCESS     not-accessible
        STATUS         current
        DESCRIPTION    "."
        INDEX { ifIndex }
        ::= { tnA4pswgPortInfoTable 1 }

    TnA4pswgPortInfoEntry ::=
        SEQUENCE {
            tnA4pswgPortInfoFunction  INTEGER
        }

    tnA4pswgPortInfoFunction OBJECT-TYPE
        SYNTAX         INTEGER {
                         lineIn(1),
                         otdrRx(2),
                         otdrTx(3),
                         lineOut(4),
                         oscSfp(5),
                         osc(6),
                         custLan(7)
                       }
        MAX-ACCESS     read-only
        STATUS         current
        DESCRIPTION    "Indicates the functional type of this A4PSWG port."
        ::= { tnA4pswgPortInfoEntry 1 }

--------------------------------------------------------------------------------
-- OTDR (Optical Time Domain Reflectometer) Optical Port Info Scalar
--------------------------------------------------------------------------------
    tnOtdrPortInfoAttributeTotal OBJECT-TYPE
        SYNTAX         Integer32
        MAX-ACCESS     read-only
        STATUS         current
        DESCRIPTION    "."
        ::= { tnOpticalPortInfo 265 }

--------------------------------------------------------------------------------
-- OTDR (Optical Time Domain Reflectometer) Optical Port Info Table
--------------------------------------------------------------------------------
    tnOtdrPortInfoTable OBJECT-TYPE
        SYNTAX         SEQUENCE OF TnOtdrPortInfoEntry
        MAX-ACCESS     not-accessible
        STATUS         current
        DESCRIPTION    "The ports on an OTDR optical card."
        ::= { tnOpticalPortInfo 266 }

    tnOtdrPortInfoEntry OBJECT-TYPE
        SYNTAX         TnOtdrPortInfoEntry
        MAX-ACCESS     not-accessible
        STATUS         current
        DESCRIPTION    "."
        INDEX { ifIndex }
        ::= { tnOtdrPortInfoTable 1 }

    TnOtdrPortInfoEntry ::=
        SEQUENCE {
            tnOtdrPortInfoFunction INTEGER
        }

    tnOtdrPortInfoFunction OBJECT-TYPE
        SYNTAX         INTEGER {
                         px(1)
                       }
        MAX-ACCESS     read-only
        STATUS         current
        DESCRIPTION    "Indicates the functional type of this OTDR port."
        ::= { tnOtdrPortInfoEntry 1 }

--------------------------------------------------------------------------------
-- WR20-TFM Optical Port Info Scalar
--------------------------------------------------------------------------------
    tnWr20tfmPortInfoAttributeTotal OBJECT-TYPE
        SYNTAX         Integer32
        MAX-ACCESS     read-only
        STATUS         current
        DESCRIPTION    "."
        ::= { tnOpticalPortInfo 267 }

--------------------------------------------------------------------------------
-- WR20-TFM Optical Port Info Table
--------------------------------------------------------------------------------
    tnWr20tfmPortInfoTable OBJECT-TYPE
        SYNTAX         SEQUENCE OF TnWr20tfmPortInfoEntry
        MAX-ACCESS     not-accessible
        STATUS         current
        DESCRIPTION    "The ports on a WR20-TFM optical card."
        ::= { tnOpticalPortInfo 268 }

    tnWr20tfmPortInfoEntry OBJECT-TYPE
        SYNTAX         TnWr20tfmPortInfoEntry
        MAX-ACCESS     not-accessible
        STATUS         current
        DESCRIPTION    "."
        INDEX { ifIndex }
        ::= { tnWr20tfmPortInfoTable 1 }

    TnWr20tfmPortInfoEntry ::=
        SEQUENCE {
            tnWr20tfmPortInfoFunction      INTEGER,
            tnWr20tfmPortInfoTestingActive TruthValue
        }

    tnWr20tfmPortInfoFunction OBJECT-TYPE
        SYNTAX         INTEGER {
                         signal(1),
                         adt(2),
                         ad(3),
                         inv(4),
                         mpoDropOut(5),
                         mpoAddIn(6)
                       }
        MAX-ACCESS     read-only
        STATUS         current
        DESCRIPTION    "Indicates the functional type of this WR20-TFM port."
        ::= { tnWr20tfmPortInfoEntry 1 }

    tnWr20tfmPortInfoTestingActive OBJECT-TYPE
        SYNTAX         TruthValue
        MAX-ACCESS     read-only
        STATUS         current
        DESCRIPTION    "Node sets to true when testing in progress
                        on port (logic)."
        DEFVAL         { false }
        ::= { tnWr20tfmPortInfoEntry 2 }

--------------------------------------------------------------------------------
-- AAR-8A Optical Port Info Scalar
--------------------------------------------------------------------------------
    tnAar8aPortInfoAttributeTotal OBJECT-TYPE
        SYNTAX         Integer32
        MAX-ACCESS     read-only
        STATUS         current
        DESCRIPTION    "."
        ::= { tnOpticalPortInfo 269 }

--------------------------------------------------------------------------------
-- AAR-8A Optical Port Info Table
--------------------------------------------------------------------------------
    tnAar8aPortInfoTable OBJECT-TYPE
        SYNTAX         SEQUENCE OF TnAar8aPortInfoEntry
        MAX-ACCESS     not-accessible
        STATUS         current
        DESCRIPTION    "The ports on an AAR-8A optical card."
        ::= { tnOpticalPortInfo 270 }

    tnAar8aPortInfoEntry OBJECT-TYPE
        SYNTAX         TnAar8aPortInfoEntry
        MAX-ACCESS     not-accessible
        STATUS         current
        DESCRIPTION    "."
        INDEX { ifIndex }
        ::= { tnAar8aPortInfoTable 1 }

    TnAar8aPortInfoEntry ::=
        SEQUENCE {
            tnAar8aPortInfoFunction   INTEGER
        }

    tnAar8aPortInfoFunction OBJECT-TYPE
        SYNTAX         INTEGER {
                         ampIn(1),
                         ampOut(2),
                         mpoFsm(3),
                         mpoMcs(4)
                       }
        MAX-ACCESS     read-only
        STATUS         current
        DESCRIPTION    "Indicates the functional type of this AAR-8A port."
        ::= { tnAar8aPortInfoEntry 1 }

--------------------------------------------------------------------------------
-- MCS8-16 Optical Port Info Scalar
--------------------------------------------------------------------------------
    tnMcs8x16PortInfoAttributeTotal OBJECT-TYPE
        SYNTAX         Integer32
        MAX-ACCESS     read-only
        STATUS         current
        DESCRIPTION    "."
        ::= { tnOpticalPortInfo 271 }

--------------------------------------------------------------------------------
-- MCS8-16 Optical Port Info Table
--------------------------------------------------------------------------------
    tnMcs8x16PortInfoTable OBJECT-TYPE
        SYNTAX         SEQUENCE OF TnMcs8x16PortInfoEntry
        MAX-ACCESS     not-accessible
        STATUS         current
        DESCRIPTION    "The ports on a MCS8-16 optical card."
        ::= { tnOpticalPortInfo 272 }

    tnMcs8x16PortInfoEntry OBJECT-TYPE
        SYNTAX         TnMcs8x16PortInfoEntry
        MAX-ACCESS     not-accessible
        STATUS         current
        DESCRIPTION    "."
        INDEX { ifIndex }
        ::= { tnMcs8x16PortInfoTable 1 }

    TnMcs8x16PortInfoEntry ::=
        SEQUENCE {
            tnMcs8x16PortInfoFunction                  INTEGER,
            tnMcs8x16PortInfoAddInsertionLossToSig1    Unsigned32,
            tnMcs8x16PortInfoAddInsertionLossToSig2    Unsigned32,
            tnMcs8x16PortInfoAddInsertionLossToSig3    Unsigned32,
            tnMcs8x16PortInfoAddInsertionLossToSig4    Unsigned32,
            tnMcs8x16PortInfoAddInsertionLossToSig5    Unsigned32,
            tnMcs8x16PortInfoAddInsertionLossToSig6    Unsigned32,
            tnMcs8x16PortInfoAddInsertionLossToSig7    Unsigned32,
            tnMcs8x16PortInfoAddInsertionLossToSig8    Unsigned32,
            tnMcs8x16PortInfoDropInsertionLossFromSig1 Unsigned32,
            tnMcs8x16PortInfoDropInsertionLossFromSig2 Unsigned32,
            tnMcs8x16PortInfoDropInsertionLossFromSig3 Unsigned32,
            tnMcs8x16PortInfoDropInsertionLossFromSig4 Unsigned32,
            tnMcs8x16PortInfoDropInsertionLossFromSig5 Unsigned32,
            tnMcs8x16PortInfoDropInsertionLossFromSig6 Unsigned32,
            tnMcs8x16PortInfoDropInsertionLossFromSig7 Unsigned32,
            tnMcs8x16PortInfoDropInsertionLossFromSig8 Unsigned32
        }

    tnMcs8x16PortInfoFunction OBJECT-TYPE
        SYNTAX         INTEGER {
                         signal(1),
                         ad(2),
                         mpoAar(3)
                       }
        MAX-ACCESS     read-only
        STATUS         current
        DESCRIPTION    "Indicates the functional type of this
                        MCS8-16 port."
        ::= { tnMcs8x16PortInfoEntry 1 }

    tnMcs8x16PortInfoAddInsertionLossToSig1 OBJECT-TYPE
        SYNTAX         Unsigned32
        UNITS          "mB"
        MAX-ACCESS     read-only
        STATUS         current
        DESCRIPTION    "Insertion loss to port SIG1 when disposed
                        to this path.  Add direction.

                        Current range: 0 to 2000."
        DEFVAL         { 1600 }
        ::= { tnMcs8x16PortInfoEntry 2 }

    tnMcs8x16PortInfoAddInsertionLossToSig2 OBJECT-TYPE
        SYNTAX         Unsigned32
        UNITS          "mB"
        MAX-ACCESS     read-only
        STATUS         current
        DESCRIPTION    "Insertion loss to port SIG2 when disposed
                        to this path.  Add direction.

                        Current range: 0 to 2000."
        DEFVAL         { 1600 }
        ::= { tnMcs8x16PortInfoEntry 3 }

    tnMcs8x16PortInfoAddInsertionLossToSig3 OBJECT-TYPE
        SYNTAX         Unsigned32
        UNITS          "mB"
        MAX-ACCESS     read-only
        STATUS         current
        DESCRIPTION    "Insertion loss to port SIG3 when disposed
                        to this path.  Add direction.  Applies to
                        NxM MCS where N>=3.

                        Current range: 0 to 2000."
        DEFVAL         { 1600 }
        ::= { tnMcs8x16PortInfoEntry 4 }

    tnMcs8x16PortInfoAddInsertionLossToSig4 OBJECT-TYPE
        SYNTAX         Unsigned32
        UNITS          "mB"
        MAX-ACCESS     read-only
        STATUS         current
        DESCRIPTION    "Insertion loss to port SIG4 when disposed
                        to this path. Add direction.  Applies to
                        NxM MCS where N>=4.

                        Current range: 0 to 2000."
        DEFVAL         { 1600 }
        ::= { tnMcs8x16PortInfoEntry 5 }

    tnMcs8x16PortInfoAddInsertionLossToSig5 OBJECT-TYPE
        SYNTAX         Unsigned32
        UNITS          "mB"
        MAX-ACCESS     read-only
        STATUS         current
        DESCRIPTION    "Insertion loss to port SIG5 when disposed
                        to this path.  Add direction.  Applies to
                        NxM MCS where N>=5.

                        Current range: 0 to 2000."
        DEFVAL         { 1600 }
        ::= { tnMcs8x16PortInfoEntry 6 }

    tnMcs8x16PortInfoAddInsertionLossToSig6 OBJECT-TYPE
        SYNTAX         Unsigned32
        UNITS          "mB"
        MAX-ACCESS     read-only
        STATUS         current
        DESCRIPTION    "Insertion loss to port SIG6 when disposed
                        to this path.  Add direction.  Applies to
                        NxM MCS where N>=6.

                        Current range: 0 to 2000."
        DEFVAL         { 1600 }
        ::= { tnMcs8x16PortInfoEntry 7 }

    tnMcs8x16PortInfoAddInsertionLossToSig7 OBJECT-TYPE
        SYNTAX         Unsigned32
        UNITS          "mB"
        MAX-ACCESS     read-only
        STATUS         current
        DESCRIPTION    "Insertion loss to port SIG7 when disposed
                        to this path.  Add direction.  Applies to
                        NxM MCS where N>=7.

                        Current range: 0 to 2000."
        DEFVAL         { 1600 }
        ::= { tnMcs8x16PortInfoEntry 8 }

    tnMcs8x16PortInfoAddInsertionLossToSig8 OBJECT-TYPE
        SYNTAX         Unsigned32
        UNITS          "mB"
        MAX-ACCESS     read-only
        STATUS         current
        DESCRIPTION    "Insertion loss to port SIG8 when disposed
                        to this path.  Add direction.  Applies to
                        NxM MCS where N>=8.

                        Current range: 0 to 2000."
        DEFVAL         { 1600 }
        ::= { tnMcs8x16PortInfoEntry 9 }

    tnMcs8x16PortInfoDropInsertionLossFromSig1 OBJECT-TYPE
        SYNTAX         Unsigned32
        UNITS          "mB"
        MAX-ACCESS     read-only
        STATUS         current
        DESCRIPTION    "Insertion loss from port SIG1 when disposed
                        to this path.  Drop direction.

                        Current range: 0 to 2000."
        DEFVAL         { 1600 }
        ::= { tnMcs8x16PortInfoEntry 10 }

    tnMcs8x16PortInfoDropInsertionLossFromSig2 OBJECT-TYPE
        SYNTAX         Unsigned32
        UNITS          "mB"
        MAX-ACCESS     read-only
        STATUS         current
        DESCRIPTION    "Insertion loss from port SIG2 when disposed
                        to this path.  Drop direction.

                        Current range: 0 to 2000."
        DEFVAL         { 1600 }
        ::= { tnMcs8x16PortInfoEntry 11 }

    tnMcs8x16PortInfoDropInsertionLossFromSig3 OBJECT-TYPE
        SYNTAX         Unsigned32
        UNITS          "mB"
        MAX-ACCESS     read-only
        STATUS         current
        DESCRIPTION    "Insertion loss from port SIG3 when disposed
                        to this path.  Drop direction.

                        Current range: 0 to 2000."
        DEFVAL         { 1600 }
        ::= { tnMcs8x16PortInfoEntry 12 }

    tnMcs8x16PortInfoDropInsertionLossFromSig4 OBJECT-TYPE
        SYNTAX         Unsigned32
        UNITS          "mB"
        MAX-ACCESS     read-only
        STATUS         current
        DESCRIPTION    "Insertion loss from port SIG4 when disposed
                        to this path.  Drop direction.

                        Current range: 0 to 2000."
        DEFVAL         { 1600 }
        ::= { tnMcs8x16PortInfoEntry 13 }

    tnMcs8x16PortInfoDropInsertionLossFromSig5 OBJECT-TYPE
        SYNTAX         Unsigned32
        UNITS          "mB"
        MAX-ACCESS     read-only
        STATUS         current
        DESCRIPTION    "Insertion loss from port SIG5 when disposed
                        to this path.  Drop direction.

                        Current range: 0 to 2000."
        DEFVAL         { 1600 }
        ::= { tnMcs8x16PortInfoEntry 14 }

    tnMcs8x16PortInfoDropInsertionLossFromSig6 OBJECT-TYPE
        SYNTAX         Unsigned32
        UNITS          "mB"
        MAX-ACCESS     read-only
        STATUS         current
        DESCRIPTION    "Insertion loss from port SIG6 when disposed
                        to this path.  Drop direction.

                        Current range: 0 to 2000."
        DEFVAL         { 1600 }
        ::= { tnMcs8x16PortInfoEntry 15 }

    tnMcs8x16PortInfoDropInsertionLossFromSig7 OBJECT-TYPE
        SYNTAX         Unsigned32
        UNITS          "mB"
        MAX-ACCESS     read-only
        STATUS         current
        DESCRIPTION    "Insertion loss from port SIG7 when disposed
                        to this path.  Drop direction.

                        Current range: 0 to 2000."
        DEFVAL         { 1600 }
        ::= { tnMcs8x16PortInfoEntry 16 }

    tnMcs8x16PortInfoDropInsertionLossFromSig8 OBJECT-TYPE
        SYNTAX         Unsigned32
        UNITS          "mB"
        MAX-ACCESS     read-only
        STATUS         current
        DESCRIPTION    "Insertion loss from port SIG8 when disposed
                        to this path.  Drop direction.

                        Current range: 0 to 2000."
        DEFVAL         { 1600 }
        ::= { tnMcs8x16PortInfoEntry 17 }

--------------------------------------------------------------------------------
-- MSH8-FSM Optical Port Info Scalar
--------------------------------------------------------------------------------
    tnMsh8fsmPortInfoAttributeTotal OBJECT-TYPE
        SYNTAX         Integer32
        MAX-ACCESS     read-only
        STATUS         current
        DESCRIPTION    "."
        ::= { tnOpticalPortInfo 273 }

--------------------------------------------------------------------------------
-- MSH8-FSM Optical Port Info Table
--------------------------------------------------------------------------------
    tnMsh8fsmPortInfoTable OBJECT-TYPE
        SYNTAX         SEQUENCE OF TnMsh8fsmPortInfoEntry
        MAX-ACCESS     not-accessible
        STATUS         current
        DESCRIPTION    "The ports on a MSH8-FSM optical card."
        ::= { tnOpticalPortInfo 274 }

    tnMsh8fsmPortInfoEntry OBJECT-TYPE
        SYNTAX         TnMsh8fsmPortInfoEntry
        MAX-ACCESS     not-accessible
        STATUS         current
        DESCRIPTION    "."
        INDEX { ifIndex }
        ::= { tnMsh8fsmPortInfoTable 1 }

    TnMsh8fsmPortInfoEntry ::=
        SEQUENCE {
            tnMsh8fsmPortInfoFunction   INTEGER
        }

    tnMsh8fsmPortInfoFunction OBJECT-TYPE
        SYNTAX         INTEGER {
                         mpoWssDropIn(1),
                         mpoWssAddOut(2),
                         mpoWssAd(3),
                         expIn(4),
                         expOut(5)
                       }
        MAX-ACCESS     read-only
        STATUS         current
        DESCRIPTION    "Indicates the functional type of this MSH8-FSM port."
        ::= { tnMsh8fsmPortInfoEntry 1 }

--------------------------------------------------------------------------------
-- Multi Cast Switch Port Info Scalar
--------------------------------------------------------------------------------
    tnMcsPortInfoAttributeTotal OBJECT-TYPE
        SYNTAX         Integer32
        MAX-ACCESS     read-only
        STATUS         current
        DESCRIPTION    "."
        ::= { tnOpticalPortInfo 275 }
--------------------------------------------------------------------------------
-- Multi Cast Switch Port Info Table
--------------------------------------------------------------------------------
    tnMcsPortInfoTable OBJECT-TYPE
        SYNTAX         SEQUENCE OF TnMcsPortInfoEntry
        MAX-ACCESS     not-accessible
        STATUS         current
        DESCRIPTION    "Current disposition AD attributes"
        ::= { tnOpticalPortInfo 276 }

    tnMcsPortInfoEntry OBJECT-TYPE
        SYNTAX         TnMcsPortInfoEntry
        MAX-ACCESS     not-accessible
        STATUS         current
        DESCRIPTION    "."
        INDEX { ifIndex }
        ::= { tnMcsPortInfoTable 1 }

    TnMcsPortInfoEntry ::=
        SEQUENCE {
            tnMcsPortInfoCurrentAddDisposition   INTEGER,
            tnMcsPortInfoCurrentDropDisposition  INTEGER,
            tnMcsPortInfoTestingActive           TruthValue,
            tnMcsPortInfoAddInputPower           Integer32
        }

    tnMcsPortInfoCurrentAddDisposition OBJECT-TYPE
        SYNTAX         INTEGER {
                         blocked(1),
                         sig1(2),
                         sig2(3),
                         sig3(4),
                         sig4(5),
                         sig5(6),
                         sig6(7),
                         sig7(8),
                         sig8(9),
                         sig9(10),
                         sig10(11),
                         sig11(12),
                         sig12(13),
                         sig13(14),
                         sig14(15),
                         sig15(16),
                         sig16(17)
                       }
        MAX-ACCESS     read-only
        STATUS         current
        DESCRIPTION    "The current disposition of the port
                        in the AD to SIG direction."
        DEFVAL         { blocked }
        ::= { tnMcsPortInfoEntry 1 }

    tnMcsPortInfoCurrentDropDisposition OBJECT-TYPE
        SYNTAX         INTEGER {
                         blocked(1),
                         sig1(2),
                         sig2(3),
                         sig3(4),
                         sig4(5),
                         sig5(6),
                         sig6(7),
                         sig7(8),
                         sig8(9),
                         sig9(10),
                         sig10(11),
                         sig11(12),
                         sig12(13),
                         sig13(14),
                         sig14(15),
                         sig15(16),
                         sig16(17)
                       }
        MAX-ACCESS     read-only
        STATUS         current
        DESCRIPTION    "The current disposition of the port
                        in the SIG to AD direction."
        DEFVAL         { blocked }
        ::= { tnMcsPortInfoEntry 2 }

    tnMcsPortInfoTestingActive OBJECT-TYPE
        SYNTAX         TruthValue
        MAX-ACCESS     read-only
        STATUS         current
        DESCRIPTION    "Node sets to true when testing in progress
                        on port (logic)."
        DEFVAL         { false }
        ::= { tnMcsPortInfoEntry 3 }

    tnMcsPortInfoAddInputPower OBJECT-TYPE
        SYNTAX         Integer32
        UNITS          "mBm"
        MAX-ACCESS     read-only
        STATUS         current
        DESCRIPTION    "Add Signal Input Power

                        Current range: -9900 to 1000."
        ::= { tnMcsPortInfoEntry 4 }

--------------------------------------------------------------------------------
-- Multi Cast Switch Port Channel Info Scalars
--------------------------------------------------------------------------------
    tnMcsPortChannelInfoAttributeTotal OBJECT-TYPE
        SYNTAX         Integer32
        MAX-ACCESS     read-only
        STATUS         current
        DESCRIPTION    "."
        ::= { tnOpticalPortInfo 277 }
--------------------------------------------------------------------------------
-- Multi Cast Switch Port Channel Info Table
--------------------------------------------------------------------------------
    tnMcsPortChannelInfoTable OBJECT-TYPE
        SYNTAX         SEQUENCE OF TnMcsPortChannelInfoEntry
        MAX-ACCESS     not-accessible
        STATUS         current
        DESCRIPTION    "Current disposition AD attributes."
        ::= { tnOpticalPortInfo 278 }

    tnMcsPortChannelInfoEntry OBJECT-TYPE
        SYNTAX         TnMcsPortChannelInfoEntry
        MAX-ACCESS     not-accessible
        STATUS         current
        DESCRIPTION    "."
        INDEX { ifIndex,
                tnChannel }
        ::= { tnMcsPortChannelInfoTable 1 }

    TnMcsPortChannelInfoEntry ::=
        SEQUENCE {
            tnMcsPortChannelInfoCurrentRoutingAdd INTEGER,
            tnMcsPortChannelInfoCurrentRoutingDrop INTEGER
        }

    tnMcsPortChannelInfoCurrentRoutingAdd OBJECT-TYPE
        SYNTAX         INTEGER {
                         notProvisioned(1),
                         ad1In(2),
                         ad2In(3),
                         ad3In(4),
                         ad4In(5),
                         ad5In(6),
                         ad6In(7),
                         ad7In(8),
                         ad8In(9),
                         ad9In(10),
                         ad10In(11),
                         ad11In(12),
                         ad12In(13),
                         ad13In(14),
                         ad14In(15),
                         ad15In(16),
                         ad16In(17)
                       }
        MAX-ACCESS     read-only
        STATUS         current
        DESCRIPTION    "The current routing of a channel from
                        AD port to SIG.  Value notProvisioned
                        means the channel is not cros-connected
                        at this port."
        DEFVAL         { notProvisioned }
        ::= { tnMcsPortChannelInfoEntry 1 }

    tnMcsPortChannelInfoCurrentRoutingDrop OBJECT-TYPE
        SYNTAX         INTEGER {
                         notProvisioned(1),
                         ad1Out(2),
                         ad2Out(3),
                         ad3Out(4),
                         ad4Out(5),
                         ad5Out(6),
                         ad6Out(7),
                         ad7Out(8),
                         ad8Out(9),
                         ad9Out(10),
                         ad10Out(11),
                         ad11Out(12),
                         ad12Out(13),
                         ad13Out(14),
                         ad14Out(15),
                         ad15Out(16),
                         ad16Out(17)
                       }
        MAX-ACCESS     read-only
        STATUS         current
        DESCRIPTION    "The current routing of a channel from
                        SIG to AD port.  Value notProvisioned
                        means the channel is not cros-connected
                        at this port."
        DEFVAL         { notProvisioned }
        ::= { tnMcsPortChannelInfoEntry 2 }

--------------------------------------------------------------------------------
-- Amplifier ARray (AAR) Optical Port Info Scalar
--------------------------------------------------------------------------------
    tnAarPortInfoAttributeTotal OBJECT-TYPE
        SYNTAX         Integer32
        MAX-ACCESS     read-only
        STATUS         current
        DESCRIPTION    "."
        ::= { tnOpticalPortInfo 279 }

--------------------------------------------------------------------------------
-- Amplifier ARray (AAR) Optical Port Info Table
--------------------------------------------------------------------------------
    tnAarPortInfoTable OBJECT-TYPE
        SYNTAX         SEQUENCE OF TnAarPortInfoEntry
        MAX-ACCESS     not-accessible
        STATUS         current
        DESCRIPTION    "The optical amplifier array attributes."
        ::= { tnOpticalPortInfo 280 }

    tnAarPortInfoEntry OBJECT-TYPE
        SYNTAX         TnAarPortInfoEntry
        MAX-ACCESS     not-accessible
        STATUS         current
        DESCRIPTION    "."
        INDEX { ifIndex }
        ::= { tnAarPortInfoTable 1 }

    TnAarPortInfoEntry ::=
        SEQUENCE {
            tnAarPortInfoTotalPowerIn          Integer32,
            tnAarPortInfoLosThreshold          Integer32,
            tnAarPortInfoLosThresholdTolerance Unsigned32,
            tnAarPortInfoLosMode               INTEGER,
            tnAarPortInfoTotalPowerOut         Integer32,
            tnAarPortInfoSignalPowerOut        Integer32,
            tnAarPortInfoOAPumpBiasCurrent     Integer32,
            tnAarPortInfoOAPumpTemperature     Integer32,
            tnAarPortInfoTestingActive         TruthValue,
            tnAarPortInfoOAPump1BiasCurrent    Integer32,
            tnAarPortInfoOAPump2BiasCurrent    Integer32,
            tnAarPortInfoOAPump1Temperature    Integer32,
            tnAarPortInfoOAPump2Temperature    Integer32
        }

    tnAarPortInfoTotalPowerIn OBJECT-TYPE
        SYNTAX         Integer32
        UNITS          "mBm"
        MAX-ACCESS     read-only
        STATUS         current
        DESCRIPTION    "The total input power.

                        Current range: -9900, read from module."
        DEFVAL         { -9900 }
        ::= { tnAarPortInfoEntry 1 }

    tnAarPortInfoLosThreshold OBJECT-TYPE
        SYNTAX         Integer32
        UNITS          "mBm"
        MAX-ACCESS     read-only
        STATUS         current
        DESCRIPTION    "The threshold for going into LOS shutdown.

                        Current range: -2700 to 0."
        DEFVAL         { -2500 }
        ::= { tnAarPortInfoEntry 2 }

    tnAarPortInfoLosThresholdTolerance OBJECT-TYPE
        SYNTAX         Unsigned32
        UNITS          "mB"
        MAX-ACCESS     read-only
        STATUS         current
        DESCRIPTION    "The tolerance for clearing LOS shutdown,above the set
                        threshold.

                        Current range: 0 to 1000."
        DEFVAL         { 100 }
        ::= { tnAarPortInfoEntry 3 }

    tnAarPortInfoLosMode OBJECT-TYPE
        SYNTAX         INTEGER {
                         losA(1),
                         losN(2)
                       }
        MAX-ACCESS     read-only
        STATUS         current
        DESCRIPTION    "The LOS mode of the amplifier.
                        LOS A: Amplifier pumps become idle under loss of input
                               signal.
                        LOS N: Amplifier pumps remain enabled under loss of
                               input signal."
        DEFVAL         { losA }
        ::= { tnAarPortInfoEntry 4 }

    tnAarPortInfoTotalPowerOut OBJECT-TYPE
        SYNTAX         Integer32
        UNITS          "mBm"
        MAX-ACCESS     read-only
        STATUS         current
        DESCRIPTION    "The total output power."
        DEFVAL         { -9900 }
        ::= { tnAarPortInfoEntry 5 }

    tnAarPortInfoSignalPowerOut OBJECT-TYPE
        SYNTAX         Integer32
        UNITS          "mBm"
        MAX-ACCESS     read-only
        STATUS         current
        DESCRIPTION    "The signal output power, total power less added ASE."
        DEFVAL         { -9900 }
        ::= { tnAarPortInfoEntry 6 }

    tnAarPortInfoOAPumpBiasCurrent OBJECT-TYPE
        SYNTAX         Integer32
        UNITS          "mA"
        MAX-ACCESS     read-only
        STATUS         current
        DESCRIPTION    "The pump laser bias current."
        ::= { tnAarPortInfoEntry 7 }

    tnAarPortInfoOAPumpTemperature OBJECT-TYPE
        SYNTAX         Integer32
        UNITS          "Celcius"
        MAX-ACCESS     read-only
        STATUS         current
        DESCRIPTION    "The pump temperature."
        ::= { tnAarPortInfoEntry 8 }

    tnAarPortInfoTestingActive OBJECT-TYPE
        SYNTAX         TruthValue
        MAX-ACCESS     read-only
        STATUS         current
        DESCRIPTION    "Node sets to true when testing in progress on port
                        (logic)."
        DEFVAL         { false }
        ::= { tnAarPortInfoEntry 9 }

    tnAarPortInfoOAPump1BiasCurrent OBJECT-TYPE
        SYNTAX         Integer32
        UNITS          "mA"
        MAX-ACCESS     read-only
        STATUS         current
        DESCRIPTION    "The pump1 laser bias current."
        ::= { tnAarPortInfoEntry 10 }

    tnAarPortInfoOAPump2BiasCurrent OBJECT-TYPE
        SYNTAX         Integer32
        UNITS          "mA"
        MAX-ACCESS     read-only
        STATUS         current
        DESCRIPTION    "The pump2 laser bias current."
        ::= { tnAarPortInfoEntry 11 }

    tnAarPortInfoOAPump1Temperature OBJECT-TYPE
        SYNTAX         Integer32
        UNITS          "Celcius"
        MAX-ACCESS     read-only
        STATUS         current
        DESCRIPTION    "The pump1 temperature."
        ::= { tnAarPortInfoEntry 12 }

    tnAarPortInfoOAPump2Temperature OBJECT-TYPE
        SYNTAX         Integer32
        UNITS          "Celcius"
        MAX-ACCESS     read-only
        STATUS         current
        DESCRIPTION    "The pump2 temperature."
        ::= { tnAarPortInfoEntry 13 }

--------------------------------------------------------------------------------
-- WR20-TFM  Port Channel Info Scalars
--------------------------------------------------------------------------------
    tnWr20tfmPortChannelInfoAttributeTotal OBJECT-TYPE
        SYNTAX         Integer32
        MAX-ACCESS     read-only
        STATUS         current
        DESCRIPTION    "."
        ::= { tnOpticalPortInfo 281 }

--------------------------------------------------------------------------------
-- WR20-TFM  Port Channel Info Table
--------------------------------------------------------------------------------
    tnWr20tfmPortChannelInfoTable OBJECT-TYPE
        SYNTAX         SEQUENCE OF TnWr20tfmPortChannelInfoEntry
        MAX-ACCESS     not-accessible
        STATUS         current
        DESCRIPTION    "The current channel disposition in add/drop
                        direction on WR20-TFM optical card."
        ::= { tnOpticalPortInfo 282 }

    tnWr20tfmPortChannelInfoEntry OBJECT-TYPE
        SYNTAX         TnWr20tfmPortChannelInfoEntry
        MAX-ACCESS     not-accessible
        STATUS         current
        DESCRIPTION    "."
        INDEX { ifIndex,
                tnChannel }
        ::= { tnWr20tfmPortChannelInfoTable 1 }

    TnWr20tfmPortChannelInfoEntry ::=
        SEQUENCE {
            tnWr20tfmPortChannelInfoDropDisposition AluWdmWRChannelCurrentAddDropDisposition,
            tnWr20tfmPortChannelInfoAddDisposition  AluWdmWRChannelCurrentAddDropDisposition
        }

    tnWr20tfmPortChannelInfoDropDisposition OBJECT-TYPE
        SYNTAX         AluWdmWRChannelCurrentAddDropDisposition
        MAX-ACCESS     read-only
        STATUS         current
        DESCRIPTION    "The current channel disposition in the drop direction."
        DEFVAL         { blocked }
        ::= { tnWr20tfmPortChannelInfoEntry 1 }

    tnWr20tfmPortChannelInfoAddDisposition OBJECT-TYPE
        SYNTAX         AluWdmWRChannelCurrentAddDropDisposition
        MAX-ACCESS     read-only
        STATUS         current
        DESCRIPTION    "The current channel disposition in the add direction."
        DEFVAL         { blocked }
        ::= { tnWr20tfmPortChannelInfoEntry 2 }

--------------------------------------------------------------------------------
-- MPO Port Info Scalar
--------------------------------------------------------------------------------
    tnMpoPortInfoAttributeTotal OBJECT-TYPE
        SYNTAX         Integer32
        MAX-ACCESS     read-only
        STATUS         current
        DESCRIPTION    "."
        ::= { tnOpticalPortInfo 283 }

--------------------------------------------------------------------------------
-- MPO Port Info Table
--------------------------------------------------------------------------------
    tnMpoPortInfoTable OBJECT-TYPE
        SYNTAX         SEQUENCE OF TnMpoPortInfoEntry
        MAX-ACCESS     not-accessible
        STATUS         current
        DESCRIPTION    "MPO Port Direction of Signals"
        ::= { tnOpticalPortInfo 284 }

    tnMpoPortInfoEntry OBJECT-TYPE
        SYNTAX         TnMpoPortInfoEntry
        MAX-ACCESS     not-accessible
        STATUS         current
        DESCRIPTION    "."
        INDEX { ifIndex }
        ::= { tnMpoPortInfoTable 1 }

    TnMpoPortInfoEntry ::=
        SEQUENCE {
            tnMpoPortInfoSignalDirection INTEGER
        }

    tnMpoPortInfoSignalDirection OBJECT-TYPE
        SYNTAX         INTEGER {
                         in(1),
                         out(2),
                         bi(3)
                       }
        MAX-ACCESS     read-only
        STATUS         current
        DESCRIPTION    "Indicates if the multi-fiber connector carries
                        signals in, out, or bidirectionally at the port.
                        In: signals are received by the port at all
                            used positions.
                        Out: signals are sent from the port at all
                            used positions.
                        Bi: signals are carried in both directions;
                            some positions in, some positions out."
        ::= { tnMpoPortInfoEntry 1 }


--------------------------------------------------------------------------------
-- MPO Port Multi Position Info Scalars
--------------------------------------------------------------------------------
    tnMpoPortMultiPositionInfoAttributeTotal OBJECT-TYPE
        SYNTAX         Integer32
        MAX-ACCESS     read-only
        STATUS         current
        DESCRIPTION    "."
        ::= { tnOpticalPortInfo 285 }

--------------------------------------------------------------------------------
-- MPO Port Multi Position Info Table
--------------------------------------------------------------------------------
    tnMpoPortMultiPositionInfoTable OBJECT-TYPE
        SYNTAX         SEQUENCE OF TnMpoPortMultiPositionInfoEntry
        MAX-ACCESS     not-accessible
        STATUS         current
        DESCRIPTION    "MPO Port Direction of Signals"
        ::= { tnOpticalPortInfo 286 }

    tnMpoPortMultiPositionInfoEntry OBJECT-TYPE
        SYNTAX         TnMpoPortMultiPositionInfoEntry
        MAX-ACCESS     not-accessible
        STATUS         current
        DESCRIPTION    "."
        INDEX { ifIndex,
                tnPosition }
        ::= { tnMpoPortMultiPositionInfoTable 1 }

    TnMpoPortMultiPositionInfoEntry ::=
        SEQUENCE {
            tnPosition                                        INTEGER,
            tnMpoPortMultiPositionInfoUnderlyingPortUsage     INTEGER,
            tnMpoPortMultiPositionInfoUnderlyingPortIfIndex   InterfaceIndex,
            tnMpoPortMultiPositionInfoUnderlyingPortDirection INTEGER
        }

    tnPosition OBJECT-TYPE
        SYNTAX         INTEGER {
                         position1(1),
                         position2(2),
                         position3(3),
                         position4(4),
                         position5(5),
                         position6(6),
                         position7(7),
                         position8(8),
                         position9(9),
                         position10(10),
                         position11(11),
                         position12(12)
                       }
        MAX-ACCESS     not-accessible
        STATUS         current
        DESCRIPTION    "The position on the multi-fiber connector."
        ::= { tnMpoPortMultiPositionInfoEntry 1 }

    tnMpoPortMultiPositionInfoUnderlyingPortUsage OBJECT-TYPE
        SYNTAX         INTEGER {
                         used(1),
                         notUsed(2),
                         none(3)
                       }
        MAX-ACCESS     read-only
        STATUS         current
        DESCRIPTION    "The usage of the position on the multi-fiber
                        connector.
                        used: Indicates the position is used by an
                              underlying logical port.
                        notUsed: Indicates the position is not used on
                                  the connector.
                        none: Indicates there are no underlying ports
                              for this multi- fiber connector."
        ::= { tnMpoPortMultiPositionInfoEntry 2 }

    tnMpoPortMultiPositionInfoUnderlyingPortIfIndex OBJECT-TYPE
        SYNTAX         InterfaceIndex
        MAX-ACCESS     read-only
        STATUS         current
        DESCRIPTION    "The logical pack port underlying at the position
                        given in INDEX.
                        Use tnMpoPortMultiPositionInfoUnderlyingPortUsage
                        to determine if a value is expected."
        ::= { tnMpoPortMultiPositionInfoEntry 3 }

    tnMpoPortMultiPositionInfoUnderlyingPortDirection OBJECT-TYPE
        SYNTAX         INTEGER {
                         in(1),
                         out(2),
                         notApplicable(3)
                       }
        MAX-ACCESS     read-only
        STATUS         current
        DESCRIPTION    "The direction (in/out) of the logical pack port
                        underling at the position given in INDEX.

                        in:            Signal direction is into the port.
                        out:           Signal direction is from the port.
                        notApplicable: The port is not used, or there is
                                       no underlying logical port for
                                       this multi-fiber connector."
        ::= { tnMpoPortMultiPositionInfoEntry 4 }

--------------------------------------------------------------------------------
-- 4AN100G Optical Port Info Scalar
--------------------------------------------------------------------------------
    tnIo4an100gPortInfoAttributeTotal OBJECT-TYPE
        SYNTAX         Integer32
        MAX-ACCESS     read-only
        STATUS         current
        DESCRIPTION    "."
        ::= { tnOpticalPortInfo 287 }

--------------------------------------------------------------------------------
-- 4AN100G Optical Port Info Table
--------------------------------------------------------------------------------
    tnIo4an100gPortInfoTable OBJECT-TYPE
        SYNTAX         SEQUENCE OF TnIo4an100gPortInfoEntry
        MAX-ACCESS     not-accessible
        STATUS         current
        DESCRIPTION    "The ports on a 4AN100G optical card."
        ::= { tnOpticalPortInfo 288 }

    tnIo4an100gPortInfoEntry OBJECT-TYPE
        SYNTAX         TnIo4an100gPortInfoEntry
        MAX-ACCESS     not-accessible
        STATUS         current
        DESCRIPTION    "."
        INDEX { ifIndex }
        ::= { tnIo4an100gPortInfoTable 1 }

    TnIo4an100gPortInfoEntry ::=
        SEQUENCE {
            tnIo4an100gPortInfoFunction  INTEGER
        }

    tnIo4an100gPortInfoFunction OBJECT-TYPE
        SYNTAX         INTEGER {
                         client(1)
                       }
        MAX-ACCESS     read-only
        STATUS         current
        DESCRIPTION    "Indicates the functional type of this 4AN100G port."
        ::= { tnIo4an100gPortInfoEntry 1 }

--------------------------------------------------------------------------------
-- 30AN10G Optical Port Info Scalar
--------------------------------------------------------------------------------
    tnIo30an10gPortInfoAttributeTotal OBJECT-TYPE
        SYNTAX         Integer32
        MAX-ACCESS     read-only
        STATUS         current
        DESCRIPTION    "."
        ::= { tnOpticalPortInfo 289 }

--------------------------------------------------------------------------------
-- 30AN10G Optical Port Info Table
--------------------------------------------------------------------------------
    tnIo30an10gPortInfoTable OBJECT-TYPE
        SYNTAX         SEQUENCE OF TnIo30an10gPortInfoEntry
        MAX-ACCESS     not-accessible
        STATUS         current
        DESCRIPTION    "The ports on a 30AN10G optical card."
        ::= { tnOpticalPortInfo 290 }

    tnIo30an10gPortInfoEntry OBJECT-TYPE
        SYNTAX         TnIo30an10gPortInfoEntry
        MAX-ACCESS     not-accessible
        STATUS         current
        DESCRIPTION    "."
        INDEX { ifIndex }
        ::= { tnIo30an10gPortInfoTable 1 }

    TnIo30an10gPortInfoEntry ::=
        SEQUENCE {
            tnIo30an10gPortInfoFunction  INTEGER
        }

    tnIo30an10gPortInfoFunction OBJECT-TYPE
        SYNTAX         INTEGER {
                         client(1)
                       }
        MAX-ACCESS     read-only
        STATUS         current
        DESCRIPTION    "Indicates the functional type of this 30AN10G port."
        ::= { tnIo30an10gPortInfoEntry 1 }

--------------------------------------------------------------------------------
-- 30AN300 Optical Port Info Scalar
--------------------------------------------------------------------------------
    tnIo30an300PortInfoAttributeTotal OBJECT-TYPE
        SYNTAX         Integer32
        MAX-ACCESS     read-only
        STATUS         current
        DESCRIPTION    "."
        ::= { tnOpticalPortInfo 291 }

--------------------------------------------------------------------------------
-- 30AN10G Optical Port Info Table
--------------------------------------------------------------------------------
    tnIo30an300PortInfoTable OBJECT-TYPE
        SYNTAX         SEQUENCE OF TnIo30an300PortInfoEntry
        MAX-ACCESS     not-accessible
        STATUS         current
        DESCRIPTION    "The ports on a 30AN300 optical card."
        ::= { tnOpticalPortInfo 292 }

    tnIo30an300PortInfoEntry OBJECT-TYPE
        SYNTAX         TnIo30an300PortInfoEntry
        MAX-ACCESS     not-accessible
        STATUS         current
        DESCRIPTION    "."
        INDEX { ifIndex }
        ::= { tnIo30an300PortInfoTable 1 }

    TnIo30an300PortInfoEntry ::=
        SEQUENCE {
            tnIo30an300PortInfoFunction  INTEGER
        }

    tnIo30an300PortInfoFunction OBJECT-TYPE
        SYNTAX         INTEGER {
                         client(1)
                       }
        MAX-ACCESS     read-only
        STATUS         current
        DESCRIPTION    "Indicates the functional type of this 30AN300 port."
        ::= { tnIo30an300PortInfoEntry 1 }

--------------------------------------------------------------------------------
-- 4AN400 Optical Port Info Scalar
--------------------------------------------------------------------------------
    tnIo4an400PortInfoAttributeTotal OBJECT-TYPE
        SYNTAX         Integer32
        MAX-ACCESS     read-only
        STATUS         current
        DESCRIPTION    "."
        ::= { tnOpticalPortInfo 293 }

--------------------------------------------------------------------------------
-- 4AN400 Optical Port Info Table
--------------------------------------------------------------------------------
    tnIo4an400PortInfoTable OBJECT-TYPE
        SYNTAX         SEQUENCE OF TnIo4an400PortInfoEntry
        MAX-ACCESS     not-accessible
        STATUS         current
        DESCRIPTION    "The ports on a 4AN400 optical card."
        ::= { tnOpticalPortInfo 294 }

    tnIo4an400PortInfoEntry OBJECT-TYPE
        SYNTAX         TnIo4an400PortInfoEntry
        MAX-ACCESS     not-accessible
        STATUS         current
        DESCRIPTION    "."
        INDEX { ifIndex }
        ::= { tnIo4an400PortInfoTable 1 }

    TnIo4an400PortInfoEntry ::=
        SEQUENCE {
            tnIo4an400PortInfoFunction  INTEGER
        }

    tnIo4an400PortInfoFunction OBJECT-TYPE
        SYNTAX         INTEGER {
                         client(1)
                       }
        MAX-ACCESS     read-only
        STATUS         current
        DESCRIPTION    "Indicates the functional type of this 4AN400 port."
        ::= { tnIo4an400PortInfoEntry 1 }

--------------------------------------------------------------------------------
-- 12P120 Optical Port Info Scalar
--------------------------------------------------------------------------------
    tn12p120PortInfoAttributeTotal OBJECT-TYPE
        SYNTAX         Integer32
        MAX-ACCESS     read-only
        STATUS         current
        DESCRIPTION    "."
        ::= { tnOpticalPortInfo 295 }

--------------------------------------------------------------------------------
-- 12P120 Optical Port Info Table
--------------------------------------------------------------------------------
    tn12p120PortInfoTable OBJECT-TYPE
        SYNTAX         SEQUENCE OF Tn12p120PortInfoEntry
        MAX-ACCESS     not-accessible
        STATUS         current
        DESCRIPTION    "The ports on a 12P120 optical card."
        ::= { tnOpticalPortInfo 296 }

    tn12p120PortInfoEntry OBJECT-TYPE
        SYNTAX         Tn12p120PortInfoEntry
        MAX-ACCESS     not-accessible
        STATUS         current
        DESCRIPTION    "."
        INDEX { ifIndex }
        ::= { tn12p120PortInfoTable 1 }

    Tn12p120PortInfoEntry ::=
        SEQUENCE {
            tn12p120PortInfoFunction  INTEGER
        }

    tn12p120PortInfoFunction OBJECT-TYPE
        SYNTAX         INTEGER {
                         network(1),
                         client(2),
                         evoa(3),
                         backplane(4)
                       }
        MAX-ACCESS     read-only
        STATUS         current
        DESCRIPTION    "Indicates the functional type of this 12P120 port."
        ::= { tn12p120PortInfoEntry 1 }

--------------------------------------------------------------------------------
-- 20P200 Optical Port Info Scalar
--------------------------------------------------------------------------------
    tn20p200PortInfoAttributeTotal OBJECT-TYPE
        SYNTAX         Integer32
        MAX-ACCESS     read-only
        STATUS         current
        DESCRIPTION    "."
        ::= { tnOpticalPortInfo 297 }

--------------------------------------------------------------------------------
-- 20P200 Optical Port Info Table
--------------------------------------------------------------------------------
    tn20p200PortInfoTable OBJECT-TYPE
        SYNTAX         SEQUENCE OF Tn20p200PortInfoEntry
        MAX-ACCESS     not-accessible
        STATUS         current
        DESCRIPTION    "The ports on a 20P200 optical card."
        ::= { tnOpticalPortInfo 298 }

    tn20p200PortInfoEntry OBJECT-TYPE
        SYNTAX         Tn20p200PortInfoEntry
        MAX-ACCESS     not-accessible
        STATUS         current
        DESCRIPTION    "."
        INDEX { ifIndex }
        ::= { tn20p200PortInfoTable 1 }

    Tn20p200PortInfoEntry ::=
        SEQUENCE {
            tn20p200PortInfoFunction  INTEGER
        }

    tn20p200PortInfoFunction OBJECT-TYPE
        SYNTAX         INTEGER {
                         network(1),
                         client(2),
                         backplane(3)
                       }
        MAX-ACCESS     read-only
        STATUS         current
        DESCRIPTION    "Indicates the functional type of this 20P200 port."
        ::= { tn20p200PortInfoEntry 1 }

--------------------------------------------------------------------------------
-- 1UD200 Optical Port Info Scalar
--------------------------------------------------------------------------------
    tn1ud200PortInfoAttributeTotal OBJECT-TYPE
        SYNTAX         Integer32
        MAX-ACCESS     read-only
        STATUS         current
        DESCRIPTION    "."
        ::= { tnOpticalPortInfo 299 }

--------------------------------------------------------------------------------
-- 1UD200 Optical Port Info Table
--------------------------------------------------------------------------------
    tn1ud200PortInfoTable OBJECT-TYPE
        SYNTAX         SEQUENCE OF Tn1ud200PortInfoEntry
        MAX-ACCESS     not-accessible
        STATUS         current
        DESCRIPTION    "The ports on a 1UD200 optical card."
        ::= { tnOpticalPortInfo 300 }

    tn1ud200PortInfoEntry OBJECT-TYPE
        SYNTAX         Tn1ud200PortInfoEntry
        MAX-ACCESS     not-accessible
        STATUS         current
        DESCRIPTION    "."
        INDEX { ifIndex }
        ::= { tn1ud200PortInfoTable 1 }

    Tn1ud200PortInfoEntry ::=
        SEQUENCE {
            tn1ud200PortInfoFunction  INTEGER
        }

    tn1ud200PortInfoFunction OBJECT-TYPE
        SYNTAX         INTEGER {
                         network(1),
                         backplane(2)
                       }
        MAX-ACCESS     read-only
        STATUS         current
        DESCRIPTION    "Indicates the functional type of this 1UD200 port."
        ::= { tn1ud200PortInfoEntry 1 }

--------------------------------------------------------------------------------
-- OT130SNQ10 Optical Port Info Scalar
--------------------------------------------------------------------------------
    tnOt130snq10PortInfoAttributeTotal OBJECT-TYPE
        SYNTAX         Integer32
        MAX-ACCESS     read-only
        STATUS         current
        DESCRIPTION    "."
        ::= { tnOpticalPortInfo 301 }

--------------------------------------------------------------------------------
-- OT130SNQ10 Optical Port Info Table
--------------------------------------------------------------------------------
    tnOt130snq10PortInfoTable OBJECT-TYPE
        SYNTAX         SEQUENCE OF TnOt130snq10PortInfoEntry
        MAX-ACCESS     not-accessible
        STATUS         current
        DESCRIPTION    "The ports on a OT130SNQ10 optical card."
        ::= { tnOpticalPortInfo 302 }

    tnOt130snq10PortInfoEntry OBJECT-TYPE
        SYNTAX         TnOt130snq10PortInfoEntry
        MAX-ACCESS     not-accessible
        STATUS         current
        DESCRIPTION    "."
        INDEX { ifIndex }
        ::= { tnOt130snq10PortInfoTable 1 }

    TnOt130snq10PortInfoEntry ::=
        SEQUENCE {
            tnOt130snq10PortInfoFunction  INTEGER
        }

    tnOt130snq10PortInfoFunction OBJECT-TYPE
        SYNTAX         INTEGER {
                         network(1),
                         client(2)
                       }
        MAX-ACCESS     read-only
        STATUS         current
        DESCRIPTION    "Indicates the functional type of this OT130SNQ10 port."
        ::= { tnOt130snq10PortInfoEntry 1 }
--------------------------------------------------------------------------------
-- IROADMV Optical Port Info Scalar
--------------------------------------------------------------------------------
    tnIroadmvPortInfoAttributeTotal OBJECT-TYPE
        SYNTAX         Integer32
        MAX-ACCESS     read-only
        STATUS         current
        DESCRIPTION    "."
        ::= { tnOpticalPortInfo 303 }

--------------------------------------------------------------------------------
-- IROADMV Optical Port Info Table
--------------------------------------------------------------------------------
    tnIroadmvPortInfoTable OBJECT-TYPE
        SYNTAX         SEQUENCE OF TnIroadmvPortInfoEntry
        MAX-ACCESS     not-accessible
        STATUS         current
        DESCRIPTION    "The ports on a IROADMV optical card."
        ::= { tnOpticalPortInfo 304 }

    tnIroadmvPortInfoEntry OBJECT-TYPE
        SYNTAX         TnIroadmvPortInfoEntry
        MAX-ACCESS     not-accessible
        STATUS         current
        DESCRIPTION    "."
        INDEX { ifIndex }
        ::= { tnIroadmvPortInfoTable 1 }

    TnIroadmvPortInfoEntry ::=
        SEQUENCE {
            tnIroadmvPortInfoFunction  INTEGER
        }

    tnIroadmvPortInfoFunction OBJECT-TYPE
        SYNTAX         INTEGER {
                         lineIn(1),
                         inv(2),
                         osc(3),
                         lineOut(4),
                         oscSfp(5),
                         adt(6),
                         dcm(7),
                         custLan(8)
                       }
        MAX-ACCESS     read-only
        STATUS         current
        DESCRIPTION    "Indicates the functional type of this IROADMV port."
        ::= { tnIroadmvPortInfoEntry 1 }

--------------------------------------------------------------------------------
-- IROADMF Optical Port Info Scalar
--------------------------------------------------------------------------------
    tnIroadmfPortInfoAttributeTotal OBJECT-TYPE
        SYNTAX         Integer32
        MAX-ACCESS     read-only
        STATUS         current
        DESCRIPTION    "."
        ::= { tnOpticalPortInfo 305 }

--------------------------------------------------------------------------------
-- IROADMF Optical Port Info Table
--------------------------------------------------------------------------------
    tnIroadmfPortInfoTable OBJECT-TYPE
        SYNTAX         SEQUENCE OF TnIroadmfPortInfoEntry
        MAX-ACCESS     not-accessible
        STATUS         current
        DESCRIPTION    "The ports on a IROADMF optical card."
        ::= { tnOpticalPortInfo 306 }

    tnIroadmfPortInfoEntry OBJECT-TYPE
        SYNTAX         TnIroadmfPortInfoEntry
        MAX-ACCESS     not-accessible
        STATUS         current
        DESCRIPTION    "."
        INDEX { ifIndex }
        ::= { tnIroadmfPortInfoTable 1 }

    TnIroadmfPortInfoEntry ::=
        SEQUENCE {
            tnIroadmfPortInfoFunction  INTEGER
        }

    tnIroadmfPortInfoFunction OBJECT-TYPE
        SYNTAX         INTEGER {
                         lineIn(1),
                         inv(2),
                         osc(3),
                         lineOut(4),
                         oscSfp(5),
                         adt(6),
                         custLan(7)
                       }
        MAX-ACCESS     read-only
        STATUS         current
        DESCRIPTION    "Indicates the functional type of this IROADMF port."
        ::= { tnIroadmfPortInfoEntry 1 }

--------------------------------------------------------------------------------
-- IROADM Optical Port Info Scalar
--------------------------------------------------------------------------------
    tnIroadmPortInfoAttributeTotal OBJECT-TYPE
        SYNTAX         Integer32
        MAX-ACCESS     read-only
        STATUS         current
        DESCRIPTION    "Total no of attributes in
                        tnIroadmPortInfoTable."
        ::= { tnOpticalPortInfo 307 }

--------------------------------------------------------------------------------
-- IROADM Optical Port Info Table
--------------------------------------------------------------------------------
    tnIroadmPortInfoTable OBJECT-TYPE
        SYNTAX         SEQUENCE OF TnIroadmPortInfoEntry
        MAX-ACCESS     not-accessible
        STATUS         current
        DESCRIPTION    "Attributes related to IROADM optical cards."
        ::= { tnOpticalPortInfo 308 }

    tnIroadmPortInfoEntry OBJECT-TYPE
        SYNTAX         TnIroadmPortInfoEntry
        MAX-ACCESS     not-accessible
        STATUS         current
        DESCRIPTION    "."
        INDEX { ifIndex }
        ::= { tnIroadmPortInfoTable 1 }

    TnIroadmPortInfoEntry ::=
        SEQUENCE {
            tnIroadmPortInfoIngressOaPowerIn             Integer32,
            tnIroadmPortInfoIngressOaPowerOut            Integer32,
            tnIroadmPortInfoEgressOaPowerIn              Integer32,
            tnIroadmPortInfoEgressOaPowerOut             Integer32,
            tnIroadmPortInfoIngressOaSignalPowerOut      Integer32,
            tnIroadmPortInfoEgressOaSignalPowerOut       Integer32,
            tnIroadmPortInfoIngressOaInputToOutputGain   Unsigned32,
            tnIroadmPortInfoEgressOaInputToOutputGain    Integer32,
            tnIroadmPortInfoEgressOaMaxFlatGain          Integer32,
            tnIroadmPortInfoIngressOaMaxFlatGain         Integer32,
            tnIroadmPortInfoActualTilt                   Integer32,
            tnIroadmPortInfoDCMInPower                   Integer32,
            tnIroadmPortInfoDCMOutPower                  Integer32,
            tnIroadmPortInfoPowerSpanRepairMargin        Unsigned32,
            tnIroadmPortInfoEnable                       Integer32,
            tnIroadmPortInfoGainTilt                     Integer32,
            tnIroadmPortInfoActOutAtten                  Unsigned32,
            tnIroadmPortInfoOSCVoaAtten                  Unsigned32,
            tnIroadmPortInfoOSCTxPowerIn                 Integer32,
            tnIroadmPortInfoOSCTxPowerOut                Integer32,
            tnIroadmPortInfoOSCRxPowerIn                 Integer32,
            tnIroadmPortInfoOSCSfpTxPowerOut             Integer32,
            tnIroadmPortInfoOSCSfpRxPowerIn              Integer32,
            tnIroadmPortInfoEgressOAPowerGain            Unsigned32,
            tnIroadmPortInfoActOutAttenL                 Unsigned32,
            tnIroadmPortInfoIngressOaPowerInL            Integer32,
            tnIroadmPortInfoIngressOaPowerOutL           Integer32,
            tnIroadmPortInfoEgressOaPowerInL             Integer32,
            tnIroadmPortInfoEgressOaPowerOutL            Integer32,
            tnIroadmPortInfoIngressOaSignalPowerOutL     Integer32,
            tnIroadmPortInfoEgressOaSignalPowerOutL      Integer32,
            tnIroadmPortInfoIngressOaInputToOutputGainL  Unsigned32,
            tnIroadmPortInfoEgressOaInputToOutputGainL   Integer32,
            tnIroadmPortInfoActualTiltL                  Integer32,
            tnIroadmPortInfoGainTiltL                    Integer32,
            tnIroadmPortInfoEgressOAPowerGainL           Unsigned32,
            tnIroadmPortInfoIngressOaMaxFlatGainL        Integer32,
            tnIroadmPortInfoEgressOaMaxFlatGainL         Integer32,
            tnIroadmPortInfoSpanLoss                     Integer32,
            tnIroadmPortInfoAseAmpOn                     TruthValue,
            tnIroadmPortInfoAseAmpOnL                    TruthValue,
            tnIroadmPortInfoAseTotalPowerOut             Integer32,
            tnIroadmPortInfoAseTotalPowerOutL            Integer32,
            tnIroadmPortInfoAseTargetTotalPowerOut       Integer32,
            tnIroadmPortInfoAseTargetTotalPowerOutL      Integer32
        }

    tnIroadmPortInfoIngressOaPowerIn OBJECT-TYPE
        SYNTAX         Integer32
        UNITS          "mBm"
        MAX-ACCESS     read-only
        STATUS         current
        DESCRIPTION    "."
        ::= { tnIroadmPortInfoEntry 1 }

    tnIroadmPortInfoIngressOaPowerOut OBJECT-TYPE
        SYNTAX         Integer32
        UNITS          "mBm"
        MAX-ACCESS     read-only
        STATUS         current
        DESCRIPTION    "."
        ::= { tnIroadmPortInfoEntry 2 }

    tnIroadmPortInfoEgressOaPowerIn OBJECT-TYPE
        SYNTAX         Integer32
        UNITS          "mBm"
        MAX-ACCESS     read-only
        STATUS         current
        DESCRIPTION    "."
        ::= { tnIroadmPortInfoEntry 3 }

    tnIroadmPortInfoEgressOaPowerOut OBJECT-TYPE
        SYNTAX         Integer32
        UNITS          "mBm"
        MAX-ACCESS     read-only
        STATUS         current
        DESCRIPTION    "."
        ::= { tnIroadmPortInfoEntry 4 }

    tnIroadmPortInfoIngressOaSignalPowerOut OBJECT-TYPE
        SYNTAX         Integer32
        UNITS          "mBm"
        MAX-ACCESS     read-only
        STATUS         current
        DESCRIPTION    "."
        ::= { tnIroadmPortInfoEntry 5 }

    tnIroadmPortInfoEgressOaSignalPowerOut OBJECT-TYPE
        SYNTAX         Integer32
        UNITS          "mBm"
        MAX-ACCESS     read-only
        STATUS         current
        DESCRIPTION    "."
        ::= { tnIroadmPortInfoEntry 6 }

    tnIroadmPortInfoIngressOaInputToOutputGain OBJECT-TYPE
        SYNTAX         Unsigned32
        UNITS          "mB"
        MAX-ACCESS     read-only
        STATUS         current
        DESCRIPTION    "Current range:

                       Iroadmv: 1500 to 3100.
                       Iroadmf: 1300 to 1900."
        ::= { tnIroadmPortInfoEntry 7 }

    tnIroadmPortInfoEgressOaInputToOutputGain OBJECT-TYPE
        SYNTAX         Integer32
        UNITS          "mB"
        MAX-ACCESS     read-only
        STATUS         current
        DESCRIPTION    "Current range:

                       Iroadmv: -300 to 2500.
                       Iroadmf: -300 to 2100."
        ::= { tnIroadmPortInfoEntry 8 }

    tnIroadmPortInfoEgressOaMaxFlatGain OBJECT-TYPE
        SYNTAX         Integer32
        UNITS          "mB"
        MAX-ACCESS     read-only
        STATUS         current
        DESCRIPTION    "Default value:

                       Iroadmv:2000
                       Iroadmf:1800."
        ::= { tnIroadmPortInfoEntry 9 }

    tnIroadmPortInfoIngressOaMaxFlatGain OBJECT-TYPE
        SYNTAX         Integer32
        UNITS          "mB"
        MAX-ACCESS     read-only
        STATUS         current
        DESCRIPTION    "Default value:

                       Iroadmv:2500
                       Iroadmf:1600."
        ::= { tnIroadmPortInfoEntry 10 }

    tnIroadmPortInfoActualTilt OBJECT-TYPE
        SYNTAX         Integer32
        UNITS          "mBm"
        MAX-ACCESS     read-only
        STATUS         current
        DESCRIPTION    "Current Range:

                        -1000 to 500."
        ::= { tnIroadmPortInfoEntry 11 }

    tnIroadmPortInfoDCMInPower OBJECT-TYPE
        SYNTAX         Integer32
        UNITS          "mBm"
        MAX-ACCESS     read-only
        STATUS         current
        DESCRIPTION    "."
        ::= { tnIroadmPortInfoEntry 12 }

    tnIroadmPortInfoDCMOutPower OBJECT-TYPE
        SYNTAX         Integer32
        UNITS          "mBm"
        MAX-ACCESS     read-only
        STATUS         current
        DESCRIPTION    "."
        ::= { tnIroadmPortInfoEntry 13 }

    tnIroadmPortInfoPowerSpanRepairMargin OBJECT-TYPE
        SYNTAX         Unsigned32
        UNITS          "mB"
        MAX-ACCESS     read-only
        STATUS         current
        DESCRIPTION    "Current range:

                        1500 to 3100."
        DEFVAL         { 2500 }
        ::= { tnIroadmPortInfoEntry 14 }

    tnIroadmPortInfoEnable OBJECT-TYPE
        SYNTAX         Integer32
        MAX-ACCESS     read-only
        STATUS         current
        DESCRIPTION    "."
        ::= { tnIroadmPortInfoEntry 15 }

    tnIroadmPortInfoGainTilt OBJECT-TYPE
        SYNTAX         Integer32
        UNITS          "mB"
        MAX-ACCESS     read-only
        STATUS         current
        DESCRIPTION    "Current  range: "
        DEFVAL         { 0 }
        ::= { tnIroadmPortInfoEntry 16 }

    tnIroadmPortInfoActOutAtten OBJECT-TYPE
        SYNTAX         Unsigned32 (0..1500)
        UNITS          "mB"
        MAX-ACCESS     read-only
        STATUS         current
        DESCRIPTION    "Actual present VOA attenuation for IROADM Gen 2 packs."
        ::= { tnIroadmPortInfoEntry 17 }

    tnIroadmPortInfoOSCVoaAtten OBJECT-TYPE
        SYNTAX         Unsigned32
        UNITS          "mB"
        MAX-ACCESS     read-only
        STATUS         current
        DESCRIPTION    "Current OSC drop eVOA attenuation.

                        Current configurable range: 0 to 2000."
        ::= { tnIroadmPortInfoEntry 18 }

    tnIroadmPortInfoOSCTxPowerIn OBJECT-TYPE
        SYNTAX         Integer32
        UNITS          "mBm"
        MAX-ACCESS     read-only
        STATUS         current
        DESCRIPTION    "The EDFA module OSC transmitted power input to
                        OSC add.  -9900 indicates no measured power.

                        Current ranges: -9900,-1200 to 1000."

        ::= { tnIroadmPortInfoEntry 19 }

    tnIroadmPortInfoOSCTxPowerOut OBJECT-TYPE
        SYNTAX         Integer32
        UNITS          "mBm"
        MAX-ACCESS     read-only
        STATUS         current
        DESCRIPTION    "The EDFA module OSC transmitted output power from
                        the card.  -9900 indicates no measured power.

                        Current ranges: -9900,-1200 to 1000."
        ::= { tnIroadmPortInfoEntry 20 }

    tnIroadmPortInfoOSCRxPowerIn OBJECT-TYPE
        SYNTAX         Integer32
        UNITS          "mBm"
        MAX-ACCESS     read-only
        STATUS         current
        DESCRIPTION    "The EDFA module OSC received input power to
                        the card.  -9900 indicates no measured power.

                        Current ranges: -9900,-4400 to 1000."
        ::= { tnIroadmPortInfoEntry 21 }

    tnIroadmPortInfoOSCSfpTxPowerOut OBJECT-TYPE
        SYNTAX         Integer32
        UNITS          "mBm"
        MAX-ACCESS     read-only
        STATUS         current
        DESCRIPTION    "The OSCSFP transceiver output power.

                        Current ranges: -9900, -1000 to 1000."

        ::= { tnIroadmPortInfoEntry 22 }

    tnIroadmPortInfoOSCSfpRxPowerIn OBJECT-TYPE
        SYNTAX         Integer32
        UNITS          "mBm"
        MAX-ACCESS     read-only
        STATUS         current
        DESCRIPTION    "The OSCSFP transceiver input power.

                        Current ranges: -9900, -4200 to 1000."
        ::= { tnIroadmPortInfoEntry 23 }

    tnIroadmPortInfoEgressOAPowerGain OBJECT-TYPE
        SYNTAX         Unsigned32
        UNITS          "mB"
        MAX-ACCESS     read-only
        STATUS         current
        DESCRIPTION    "Present actual gain set to the egress OA.

                        IROADM9R, IRDM20 : 1700 to 2300."
        ::= { tnIroadmPortInfoEntry 24 }

    tnIroadmPortInfoActOutAttenL OBJECT-TYPE
        SYNTAX         Unsigned32 (0..1500)
        UNITS          "mB"
        MAX-ACCESS     read-only
        STATUS         current
        DESCRIPTION    "Actual present VOA attenuationL for IROADM Gen 2 packs."
        ::= { tnIroadmPortInfoEntry 25 }

    tnIroadmPortInfoIngressOaPowerInL OBJECT-TYPE
        SYNTAX         Integer32
        UNITS          "mBm"
        MAX-ACCESS     read-only
        STATUS         current
        DESCRIPTION    "."
        ::= { tnIroadmPortInfoEntry 26 }

    tnIroadmPortInfoIngressOaPowerOutL OBJECT-TYPE
        SYNTAX         Integer32
        UNITS          "mBm"
        MAX-ACCESS     read-only
        STATUS         current
        DESCRIPTION    "."
        ::= { tnIroadmPortInfoEntry 27 }

    tnIroadmPortInfoEgressOaPowerInL OBJECT-TYPE
        SYNTAX         Integer32
        UNITS          "mBm"
        MAX-ACCESS     read-only
        STATUS         current
        DESCRIPTION    "."
        ::= { tnIroadmPortInfoEntry 28 }

    tnIroadmPortInfoEgressOaPowerOutL OBJECT-TYPE
        SYNTAX         Integer32
        UNITS          "mBm"
        MAX-ACCESS     read-only
        STATUS         current
        DESCRIPTION    "."
        ::= { tnIroadmPortInfoEntry 29 }

    tnIroadmPortInfoIngressOaSignalPowerOutL OBJECT-TYPE
        SYNTAX         Integer32
        UNITS          "mBm"
        MAX-ACCESS     read-only
        STATUS         current
        DESCRIPTION    "."
        ::= { tnIroadmPortInfoEntry 30 }

    tnIroadmPortInfoEgressOaSignalPowerOutL OBJECT-TYPE
        SYNTAX         Integer32
        UNITS          "mBm"
        MAX-ACCESS     read-only
        STATUS         current
        DESCRIPTION    "."
        ::= { tnIroadmPortInfoEntry 31 }

    tnIroadmPortInfoIngressOaInputToOutputGainL OBJECT-TYPE
        SYNTAX         Unsigned32
        UNITS          "mB"
        MAX-ACCESS     read-only
        STATUS         current
        DESCRIPTION    "."
        ::= { tnIroadmPortInfoEntry 32 }

    tnIroadmPortInfoEgressOaInputToOutputGainL OBJECT-TYPE
        SYNTAX         Integer32
        UNITS          "mB"
        MAX-ACCESS     read-only
        STATUS         current
        DESCRIPTION    "."
        ::= { tnIroadmPortInfoEntry 33 }

    tnIroadmPortInfoActualTiltL OBJECT-TYPE
        SYNTAX         Integer32
        UNITS          "mBm"
        MAX-ACCESS     read-only
        STATUS         current
        DESCRIPTION    "."
        ::= { tnIroadmPortInfoEntry 34 }

    tnIroadmPortInfoGainTiltL OBJECT-TYPE
        SYNTAX         Integer32
        UNITS          "mB"
        MAX-ACCESS     read-only
        STATUS         current
        DESCRIPTION    "."
        DEFVAL         { 0 }
        ::= { tnIroadmPortInfoEntry 35 }

    tnIroadmPortInfoEgressOAPowerGainL OBJECT-TYPE
        SYNTAX         Unsigned32
        UNITS          "mB"
        MAX-ACCESS     read-only
        STATUS         current
        DESCRIPTION    "L Band Present actual gain set to the egress OA."
        ::= { tnIroadmPortInfoEntry 36 }

    tnIroadmPortInfoIngressOaMaxFlatGainL OBJECT-TYPE
        SYNTAX         Integer32
        UNITS          "mB"
        MAX-ACCESS     read-only
        STATUS         current
        DESCRIPTION    "."
        ::= { tnIroadmPortInfoEntry 37 }

    tnIroadmPortInfoEgressOaMaxFlatGainL OBJECT-TYPE
        SYNTAX         Integer32
        UNITS          "mB"
        MAX-ACCESS     read-only
        STATUS         current
        DESCRIPTION    "."
        ::= { tnIroadmPortInfoEntry 38 }

    tnIroadmPortInfoSpanLoss OBJECT-TYPE
        SYNTAX         Integer32
        UNITS          "mB"
        MAX-ACCESS     read-only
        STATUS         current
        DESCRIPTION    "Span loss."
        DEFVAL         { 9900 }
        ::= { tnIroadmPortInfoEntry 39 }

    tnIroadmPortInfoAseAmpOn OBJECT-TYPE
        SYNTAX         TruthValue
        MAX-ACCESS     read-only
        STATUS         current
        DESCRIPTION    "."
        DEFVAL         { false }
        ::= { tnIroadmPortInfoEntry 40 }

    tnIroadmPortInfoAseAmpOnL OBJECT-TYPE
        SYNTAX         TruthValue
        MAX-ACCESS     read-only
        STATUS         current
        DESCRIPTION    "."
        DEFVAL         { false }
        ::= { tnIroadmPortInfoEntry 41 }

    tnIroadmPortInfoAseTotalPowerOut OBJECT-TYPE
        SYNTAX         Integer32
        UNITS          "mBm"
        MAX-ACCESS     read-only
        STATUS         current
        DESCRIPTION    "."
        ::= { tnIroadmPortInfoEntry 42 }

    tnIroadmPortInfoAseTotalPowerOutL OBJECT-TYPE
        SYNTAX         Integer32
        UNITS          "mBm"
        MAX-ACCESS     read-only
        STATUS         current
        DESCRIPTION    "."
        ::= { tnIroadmPortInfoEntry 43 }

    tnIroadmPortInfoAseTargetTotalPowerOut OBJECT-TYPE
        SYNTAX         Integer32
        UNITS          "mBm"
        MAX-ACCESS     read-only
        STATUS         current
        DESCRIPTION    "."
        ::= { tnIroadmPortInfoEntry 44 }

    tnIroadmPortInfoAseTargetTotalPowerOutL OBJECT-TYPE
        SYNTAX         Integer32
        UNITS          "mBm"
        MAX-ACCESS     read-only
        STATUS         current
        DESCRIPTION    "."
        ::= { tnIroadmPortInfoEntry 45 }

--------------------------------------------------------------------------------
-- IROADM Optical Port Channel Info Scalars
--------------------------------------------------------------------------------
    tnIroadmPortChannelInfoAttributeTotal OBJECT-TYPE
        SYNTAX         Integer32
        MAX-ACCESS     read-only
        STATUS         current
        DESCRIPTION    "Total no of attributes in
                        tnIroadmPortChannelInfoTable."
        ::= { tnOpticalPortInfo 309 }

--------------------------------------------------------------------------------
-- IROADM Optical Port Channel Info Table
--------------------------------------------------------------------------------
    tnIroadmPortChannelInfoTable OBJECT-TYPE
        SYNTAX         SEQUENCE OF TnIroadmPortChannelInfoEntry
        MAX-ACCESS     not-accessible
        STATUS         current
        DESCRIPTION    "."
        ::= { tnOpticalPortInfo 310 }

    tnIroadmPortChannelInfoEntry OBJECT-TYPE
        SYNTAX         TnIroadmPortChannelInfoEntry
        MAX-ACCESS     not-accessible
        STATUS         current
        DESCRIPTION    "."
        INDEX { ifIndex,
                tnChannel }
        ::= { tnIroadmPortChannelInfoTable 1 }

    TnIroadmPortChannelInfoEntry ::=
        SEQUENCE {
            tnIroadmPortChannelInfoAddDisposition INTEGER
        }

    tnIroadmPortChannelInfoAddDisposition OBJECT-TYPE
        SYNTAX         INTEGER {
                         blocked(1),
                         adt1(2),
                         adt2(3),
                         adt3(4),
                         adt4(5),
                         adt5(6),
                         adt6(7),
                         adt7(8),
                         adt8(9),
                         adt9(10)
                       }
        MAX-ACCESS     read-only
        STATUS         current
        DESCRIPTION    "."
        DEFVAL         { blocked }
        ::= { tnIroadmPortChannelInfoEntry 1 }

--------------------------------------------------------------------------------
-- WSS REFERENCE LD Info Scalars
--------------------------------------------------------------------------------
    tnWssRefLdInfoAttributeTotal OBJECT-TYPE
        SYNTAX         Integer32
        MAX-ACCESS     read-only
        STATUS         current
        DESCRIPTION    "Total no of attributes present in
                        tnWssRefLdInfoTable."
        ::= { tnOpticalPortInfo 311 }

--------------------------------------------------------------------------------
-- WSS REFERENCE LD Info Table
--------------------------------------------------------------------------------
    tnWssRefLdInfoTable OBJECT-TYPE
        SYNTAX         SEQUENCE OF TnWssRefLdInfoEntry
        MAX-ACCESS     not-accessible
        STATUS         current
        DESCRIPTION    "Through this table, a network operator may
                        read the reference port for WSS control."
        ::= { tnOpticalPortInfo 312 }

    tnWssRefLdInfoEntry OBJECT-TYPE
        SYNTAX         TnWssRefLdInfoEntry
        MAX-ACCESS     not-accessible
        STATUS         current
        DESCRIPTION    "."
        INDEX { ifIndex,
                tnChannel }
        ::= { tnWssRefLdInfoTable 1 }

    TnWssRefLdInfoEntry ::=
        SEQUENCE {
            tnWssRefLdInfoIfIndex        InterfaceIndexOrZero,
            tnWssRefLdInfoApplicability  INTEGER
        }


    tnWssRefLdInfoIfIndex OBJECT-TYPE
        SYNTAX         InterfaceIndexOrZero
        MAX-ACCESS     read-only
        STATUS         current
        DESCRIPTION    "Show the shelf, slot, and port of the LD card
                        that is providing the reference point for WSS
                        adjustments at the SIG port of the WR card.
                        Applies only to cards at level 0 in the
                        configuration."
        ::= { tnWssRefLdInfoEntry 1 }

    tnWssRefLdInfoApplicability OBJECT-TYPE
        SYNTAX         INTEGER {
                         notApplicable(1),
                         applicableAndAvailable(2)
                       }
        MAX-ACCESS     read-only
        STATUS         current
        DESCRIPTION    "Values include:
                        notApplicable - no XC is configured for this
                          channel.
                        applicableAndAvailable - XC is configured for
                          this channel."
        ::= { tnWssRefLdInfoEntry 2 }

--------------------------------------------------------------------------------
-- MON-OCM Optical Port Info Scalar
--------------------------------------------------------------------------------
    tnMonOcmPortInfoAttributeTotal OBJECT-TYPE
        SYNTAX         Integer32
        MAX-ACCESS     read-only
        STATUS         current
        DESCRIPTION    "Total no of attributes in tnMonOcmPortInfoTable."
        ::= { tnOpticalPortInfo 313 }

--------------------------------------------------------------------------------
-- MON-OCM Optical Port Info Table
--------------------------------------------------------------------------------
    tnMonOcmPortInfoTable OBJECT-TYPE
        SYNTAX         SEQUENCE OF TnMonOcmPortInfoEntry
        MAX-ACCESS     not-accessible
        STATUS         current
        DESCRIPTION    "The ports on a MON-OCM card."
        ::= { tnOpticalPortInfo 314 }

    tnMonOcmPortInfoEntry OBJECT-TYPE
        SYNTAX         TnMonOcmPortInfoEntry
        MAX-ACCESS     not-accessible
        STATUS         current
        DESCRIPTION    "."
        INDEX { ifIndex }
        ::= { tnMonOcmPortInfoTable 1 }

    TnMonOcmPortInfoEntry ::=
        SEQUENCE {
            tnMonOcmPortInfoFunction  INTEGER
        }

    tnMonOcmPortInfoFunction OBJECT-TYPE
        SYNTAX         INTEGER {
                         output(1),
                         input(2),
                         monitor(3)
                       }
        MAX-ACCESS     read-only
        STATUS         current
        DESCRIPTION    "Indicates the functional type of this MON-OCM port."
        ::= { tnMonOcmPortInfoEntry 1 }

--------------------------------------------------------------------------------
-- Ul2uc400 Optical Port Info Scalar
--------------------------------------------------------------------------------
    tnUl2uc400PortInfoAttributeTotal OBJECT-TYPE
        SYNTAX         Integer32
        MAX-ACCESS     read-only
        STATUS         current
        DESCRIPTION    "Total no of attributes in  tnUl2uc400PortInfoTable"
        ::= { tnOpticalPortInfo 315 }

--------------------------------------------------------------------------------
-- Ul2uc400 Optical Port Info Table
--------------------------------------------------------------------------------
    tnUl2uc400PortInfoTable OBJECT-TYPE
        SYNTAX         SEQUENCE OF TnUl2uc400PortInfoEntry
        MAX-ACCESS     not-accessible
        STATUS         current
        DESCRIPTION    "The ports on a Ul2uc400 optical card."
        ::= { tnOpticalPortInfo 316 }

    tnUl2uc400PortInfoEntry OBJECT-TYPE
        SYNTAX         TnUl2uc400PortInfoEntry
        MAX-ACCESS     not-accessible
        STATUS         current
        DESCRIPTION    "."
        INDEX { ifIndex }
        ::= { tnUl2uc400PortInfoTable 1 }

    TnUl2uc400PortInfoEntry ::=
        SEQUENCE {
            tnUl2uc400PortInfoFunction  INTEGER
        }

    tnUl2uc400PortInfoFunction OBJECT-TYPE
        SYNTAX         INTEGER {
                         network(1)
                       }
        MAX-ACCESS     read-only
        STATUS         current
        DESCRIPTION    "Indicates the functional type of this Ul2uc400 port."
        ::= { tnUl2uc400PortInfoEntry 1 }


--------------------------------------------------------------------------------
-- Ul4uc400 Optical Port Info Scalar
--------------------------------------------------------------------------------
    tnUl4uc400PortInfoAttributeTotal OBJECT-TYPE
        SYNTAX         Integer32
        MAX-ACCESS     read-only
        STATUS         current
        DESCRIPTION    "Total no of attributes in tnUl4uc400PortInfoTable."
        ::= { tnOpticalPortInfo 317 }

--------------------------------------------------------------------------------
-- Ul4uc400 Optical Port Info Table
--------------------------------------------------------------------------------
    tnUl4uc400PortInfoTable OBJECT-TYPE
        SYNTAX         SEQUENCE OF TnUl4uc400PortInfoEntry
        MAX-ACCESS     not-accessible
        STATUS         current
        DESCRIPTION    "The ports on a Ul4uc400 optical card."
        ::= { tnOpticalPortInfo 318 }

    tnUl4uc400PortInfoEntry OBJECT-TYPE
        SYNTAX         TnUl4uc400PortInfoEntry
        MAX-ACCESS     not-accessible
        STATUS         current
        DESCRIPTION    "."
        INDEX { ifIndex }
        ::= { tnUl4uc400PortInfoTable 1 }

    TnUl4uc400PortInfoEntry ::=
        SEQUENCE {
            tnUl4uc400PortInfoFunction  INTEGER
        }

    tnUl4uc400PortInfoFunction OBJECT-TYPE
        SYNTAX         INTEGER {
                         network(1)
                       }
        MAX-ACCESS     read-only
        STATUS         current
        DESCRIPTION    "Indicates the functional type of this Ul4uc400 port."
        ::= { tnUl4uc400PortInfoEntry 1 }

--------------------------------------------------------------------------------
-- Ul20uc200 Optical Port Info Scalar
--------------------------------------------------------------------------------
    tnUl20uc200PortInfoAttributeTotal OBJECT-TYPE
        SYNTAX         Integer32
        MAX-ACCESS     read-only
        STATUS         current
        DESCRIPTION    "Total no of attributes in tnUl20uc200PortInfoTable."
        ::= { tnOpticalPortInfo 319 }

--------------------------------------------------------------------------------
-- Ul20uc200 Optical Port Info Table
--------------------------------------------------------------------------------
    tnUl20uc200PortInfoTable OBJECT-TYPE
        SYNTAX         SEQUENCE OF TnUl20uc200PortInfoEntry
        MAX-ACCESS     not-accessible
        STATUS         current
        DESCRIPTION    "The ports on a Ul20uc200 optical card."
        ::= { tnOpticalPortInfo 320 }

    tnUl20uc200PortInfoEntry OBJECT-TYPE
        SYNTAX         TnUl20uc200PortInfoEntry
        MAX-ACCESS     not-accessible
        STATUS         current
        DESCRIPTION    "."
        INDEX { ifIndex }
        ::= { tnUl20uc200PortInfoTable 1 }

    TnUl20uc200PortInfoEntry ::=
        SEQUENCE {
            tnUl20uc200PortInfoFunction  INTEGER
        }

    tnUl20uc200PortInfoFunction OBJECT-TYPE
        SYNTAX         INTEGER {
                         network(1)
                       }
        MAX-ACCESS     read-only
        STATUS         current
        DESCRIPTION    "Indicates the functional type of this Ul20uc200 port."
        ::= { tnUl20uc200PortInfoEntry 1 }

--------------------------------------------------------------------------------
-- D5X500 Optical Port Info Scalar
--------------------------------------------------------------------------------
    tnD5x500PortInfoAttributeTotal OBJECT-TYPE
        SYNTAX         Integer32
        MAX-ACCESS     read-only
        STATUS         current
        DESCRIPTION    "."
        ::= { tnOpticalPortInfo 321 }

--------------------------------------------------------------------------------
-- D5X500 Optical Port Info Table
--------------------------------------------------------------------------------
    tnD5x500PortInfoTable OBJECT-TYPE
        SYNTAX         SEQUENCE OF TnD5x500PortInfoEntry
        MAX-ACCESS     not-accessible
        STATUS         current
        DESCRIPTION    "The ports on a D5X500 optical card."
        ::= { tnOpticalPortInfo 322 }

    tnD5x500PortInfoEntry OBJECT-TYPE
        SYNTAX         TnD5x500PortInfoEntry
        MAX-ACCESS     not-accessible
        STATUS         current
        DESCRIPTION    "."
        INDEX { ifIndex }
        ::= { tnD5x500PortInfoTable 1 }

    TnD5x500PortInfoEntry ::=
        SEQUENCE {
            tnD5x500PortInfoFunction INTEGER
        }

    tnD5x500PortInfoFunction OBJECT-TYPE
        SYNTAX         INTEGER {
                         network(1),
                         client(2),
                         backplane(3)
                       }
        MAX-ACCESS     read-only
        STATUS         current
        DESCRIPTION    "Indicates the functional type of this D5X500 port."
        ::= { tnD5x500PortInfoEntry 1 }

--------------------------------------------------------------------------------
-- OtS11M100 Optical Port Info Scalar
--------------------------------------------------------------------------------
    tnOtS11M100PortInfoAttributeTotal OBJECT-TYPE
        SYNTAX         Integer32
        MAX-ACCESS     read-only
        STATUS         current
        DESCRIPTION    "."
        ::= { tnOpticalPortInfo 323 }

--------------------------------------------------------------------------------
-- OtS11M100 Optical Port Info Table
--------------------------------------------------------------------------------
    tnOtS11M100PortInfoTable OBJECT-TYPE
        SYNTAX         SEQUENCE OF TnOtS11M100PortInfoEntry
        MAX-ACCESS     not-accessible
        STATUS         current
        DESCRIPTION    "The ports on a OtS11M100 optical card."
        ::= { tnOpticalPortInfo 324 }

    tnOtS11M100PortInfoEntry OBJECT-TYPE
        SYNTAX         TnOtS11M100PortInfoEntry
        MAX-ACCESS     not-accessible
        STATUS         current
        DESCRIPTION    "."
        INDEX { ifIndex }
        ::= { tnOtS11M100PortInfoTable 1 }

    TnOtS11M100PortInfoEntry ::=
        SEQUENCE {
            tnOtS11M100PortInfoFunction  INTEGER
        }

    tnOtS11M100PortInfoFunction OBJECT-TYPE
        SYNTAX         INTEGER {
                         network(1),
                         client(2)
                       }
        MAX-ACCESS     read-only
        STATUS         current
        DESCRIPTION    "Indicates the functional type of this OtS11M100 port."
        ::= { tnOtS11M100PortInfoEntry 1 }

--------------------------------------------------------------------------------
-- MON-OTDR (MON-Optical Time Domain Reflectometer) Optical Port Info Scalar
--------------------------------------------------------------------------------
    tnMonOtdrPortInfoAttributeTotal OBJECT-TYPE
        SYNTAX         Integer32
        MAX-ACCESS     read-only
        STATUS         current
        DESCRIPTION    "."
        ::= { tnOpticalPortInfo 325 }

--------------------------------------------------------------------------------
-- MON-OTDR (MON-Optical Time Domain Reflectometer) Optical Port Info Table
--------------------------------------------------------------------------------
    tnMonOtdrPortInfoTable OBJECT-TYPE
        SYNTAX         SEQUENCE OF TnMonOtdrPortInfoEntry
        MAX-ACCESS     not-accessible
        STATUS         current
        DESCRIPTION    "The ports on a MON-OTDR optical card."
        ::= { tnOpticalPortInfo 326 }

    tnMonOtdrPortInfoEntry OBJECT-TYPE
        SYNTAX         TnMonOtdrPortInfoEntry
        MAX-ACCESS     not-accessible
        STATUS         current
        DESCRIPTION    "."
        INDEX { ifIndex }
        ::= { tnMonOtdrPortInfoTable 1 }

    TnMonOtdrPortInfoEntry ::=
        SEQUENCE {
            tnMonOtdrPortInfoFunction INTEGER
        }

    tnMonOtdrPortInfoFunction OBJECT-TYPE
        SYNTAX         INTEGER {
                         lineIn(1),
                         otdrRx(2),
                         otdrTx(3),
                         lineOut(4),
                         sigIn(5),
                         sigOut(6)
                       }
        MAX-ACCESS     read-only
        STATUS         current
        DESCRIPTION    "Indicates the functional type of this MON-OTDR port."
        ::= { tnMonOtdrPortInfoEntry 1 }

--------------------------------------------------------------------------------
-- PSS96 Power Filter Port Info Scalar
--------------------------------------------------------------------------------
    tnPSS96PowerFilterPortInfoAttributeTotal OBJECT-TYPE
        SYNTAX         Integer32
        MAX-ACCESS     read-only
        STATUS         current
        DESCRIPTION    "."
        ::= { tnOpticalPortInfo 327 }

--------------------------------------------------------------------------------
-- PSS96Power Filter Port Info Table
--------------------------------------------------------------------------------
    tnPSS96PowerFilterPortInfoTable OBJECT-TYPE
        SYNTAX         SEQUENCE OF TnPSS96PowerFilterPortInfoEntry
        MAX-ACCESS     not-accessible
        STATUS         current
        DESCRIPTION    "The ports on a PSS96PowerFilter optical card."
        ::= { tnOpticalPortInfo 328 }

    tnPSS96PowerFilterPortInfoEntry OBJECT-TYPE
        SYNTAX         TnPSS96PowerFilterPortInfoEntry
        MAX-ACCESS     not-accessible
        STATUS         current
        DESCRIPTION    "."
        INDEX { ifIndex }
        ::= { tnPSS96PowerFilterPortInfoTable 1 }

    TnPSS96PowerFilterPortInfoEntry ::=
        SEQUENCE {
            tnPSS96PowerFilterPortInfoFunction INTEGER
        }

    tnPSS96PowerFilterPortInfoFunction OBJECT-TYPE
        SYNTAX         INTEGER {
                         powerFilterPort1(1),
                         powerFilterPort2(2),
                         powerFilterPort3(3)
                       }
        MAX-ACCESS     read-only
        STATUS         current
        DESCRIPTION    "Indicates the functional type of this PSS96PowerFilter port."
        ::= { tnPSS96PowerFilterPortInfoEntry 1 }

--------------------------------------------------------------------------------
-- 12CE120 Optical Port Info Scalar
--------------------------------------------------------------------------------
    tn12ce120PortInfoAttributeTotal OBJECT-TYPE
        SYNTAX         Integer32
        MAX-ACCESS     read-only
        STATUS         current
        DESCRIPTION    "."
        ::= { tnOpticalPortInfo 329 }

--------------------------------------------------------------------------------
-- 12CE120 Optical Port Info Table
--------------------------------------------------------------------------------
    tn12ce120PortInfoTable OBJECT-TYPE
        SYNTAX         SEQUENCE OF Tn12ce120PortInfoEntry
        MAX-ACCESS     not-accessible
        STATUS         current
        DESCRIPTION    "The ports on a 12CE120 optical card."
        ::= { tnOpticalPortInfo 330 }

    tn12ce120PortInfoEntry OBJECT-TYPE
        SYNTAX         Tn12ce120PortInfoEntry
        MAX-ACCESS     not-accessible
        STATUS         current
        DESCRIPTION    "."
        INDEX { ifIndex }
        ::= { tn12ce120PortInfoTable 1 }

    Tn12ce120PortInfoEntry ::=
        SEQUENCE {
            tn12ce120PortInfoFunction INTEGER
        }

    tn12ce120PortInfoFunction OBJECT-TYPE
        SYNTAX         INTEGER {
                         network(1),
                         client(2),
                         backplane(3),
                         tod(4),
                         ethman(5)
                       }
        MAX-ACCESS     read-only
        STATUS         current
        DESCRIPTION    "Indicates the functional type of this 12CE120 port."
        ::= { tn12ce120PortInfoEntry 1 }

--------------------------------------------------------------------------------
-- 1CE100 Optical Port Info Scalar
--------------------------------------------------------------------------------
    tn1ce100PortInfoAttributeTotal OBJECT-TYPE
        SYNTAX         Integer32
        MAX-ACCESS     read-only
        STATUS         current
        DESCRIPTION    "."
        ::= { tnOpticalPortInfo 331 }

--------------------------------------------------------------------------------
 -- 1CE100 Optical Port Info Table
--------------------------------------------------------------------------------
    tn1ce100PortInfoTable OBJECT-TYPE
        SYNTAX         SEQUENCE OF Tn1ce100PortInfoEntry
        MAX-ACCESS     not-accessible
        STATUS         current
        DESCRIPTION    "The ports on a 1CE100 optical card."
        ::= { tnOpticalPortInfo 332 }

    tn1ce100PortInfoEntry OBJECT-TYPE
        SYNTAX         Tn1ce100PortInfoEntry
        MAX-ACCESS     not-accessible
        STATUS         current
        DESCRIPTION    "."
        INDEX { ifIndex }
        ::= { tn1ce100PortInfoTable 1 }

    Tn1ce100PortInfoEntry ::=
        SEQUENCE {
            tn1ce100PortInfoFunction INTEGER
        }

    tn1ce100PortInfoFunction OBJECT-TYPE
        SYNTAX         INTEGER {
                         client(1),
                         backplane(2),
                         tod(3),
                         ethman(4)
                       }
        MAX-ACCESS     read-only
        STATUS         current
        DESCRIPTION    "Indicates the functional type of this 1CE100 port."
        ::= { tn1ce100PortInfoEntry 1 }

--------------------------------------------------------------------------------
-- LCI1000 Optical Port Info Scalar
--------------------------------------------------------------------------------
    tnLcI1000PortInfoAttributeTotal OBJECT-TYPE
        SYNTAX         Integer32
        MAX-ACCESS     read-only
        STATUS         current
        DESCRIPTION    "."
        ::= { tnOpticalPortInfo 333 }

--------------------------------------------------------------------------------
-- LCI1000 Optical Port Info Table
--------------------------------------------------------------------------------
    tnLcI1000PortInfoTable OBJECT-TYPE
        SYNTAX         SEQUENCE OF TnLcI1000PortInfoEntry
        MAX-ACCESS     not-accessible
        STATUS         current
        DESCRIPTION    "The ports on a LcI1000 optical card."
        ::= { tnOpticalPortInfo 334 }

    tnLcI1000PortInfoEntry OBJECT-TYPE
        SYNTAX         TnLcI1000PortInfoEntry
        MAX-ACCESS     not-accessible
        STATUS         current
        DESCRIPTION    "."
        INDEX { ifIndex }
        ::= { tnLcI1000PortInfoTable 1 }

    TnLcI1000PortInfoEntry ::= SEQUENCE {
        tnLcI1000PortInfoFunction INTEGER
    }

    tnLcI1000PortInfoFunction OBJECT-TYPE
        SYNTAX         INTEGER {
                         network(1),
                         client(2)
                       }
        MAX-ACCESS     read-only
        STATUS         current
        DESCRIPTION    "Indicates the functional type of
                        this LcI1000 port."
        ::= { tnLcI1000PortInfoEntry 1 }

-------------------------------------------------------------------------------
-- AWBEGR Optical Port Info Scalar
-------------------------------------------------------------------------------
    tnAwbegrPortInfoAttributeTotal OBJECT-TYPE
        SYNTAX         Integer32
        MAX-ACCESS     read-only
        STATUS         current
        DESCRIPTION    "."
        ::= { tnOpticalPortInfo 335 }

-------------------------------------------------------------------------------
-- AWBEGR Optical Port Info Table
-------------------------------------------------------------------------------
    tnAwbegrPortInfoTable OBJECT-TYPE
        SYNTAX         SEQUENCE OF TnAwbegrPortInfoEntry
        MAX-ACCESS     not-accessible
        STATUS         current
        DESCRIPTION    "The ports on a AWBEGR optical card."
        ::= { tnOpticalPortInfo 336 }

    tnAwbegrPortInfoEntry OBJECT-TYPE
        SYNTAX         TnAwbegrPortInfoEntry
        MAX-ACCESS     not-accessible
        STATUS         current
        DESCRIPTION    "."
        INDEX { ifIndex }
        ::= { tnAwbegrPortInfoTable 1 }

    TnAwbegrPortInfoEntry ::=
        SEQUENCE {
            tnAwbegrPortInfoFunction INTEGER
        }

    tnAwbegrPortInfoFunction OBJECT-TYPE
        SYNTAX         INTEGER {
                         sigCin(1),
                         sigLin(2),
                         otdrTx(3),
                         lineOut(4),
                         osc(5)
                       }
        MAX-ACCESS     read-only
        STATUS         current
        DESCRIPTION    "Indicates the functional type of this AWBEGR port."
        ::= { tnAwbegrPortInfoEntry 1 }

-------------------------------------------------------------------------------
-- AWBING Optical Port Info Scalar
-------------------------------------------------------------------------------
    tnAwbingPortInfoAttributeTotal OBJECT-TYPE
        SYNTAX         Integer32
        MAX-ACCESS     read-only
        STATUS         current
        DESCRIPTION    "."
        ::= { tnOpticalPortInfo 337 }

-------------------------------------------------------------------------------
-- AWBING Optical Port Info Table
-------------------------------------------------------------------------------
    tnAwbingPortInfoTable OBJECT-TYPE
        SYNTAX         SEQUENCE OF TnAwbingPortInfoEntry
        MAX-ACCESS     not-accessible
        STATUS         current
        DESCRIPTION    "The ports on a AWBING optical card."
        ::= { tnOpticalPortInfo 338 }

    tnAwbingPortInfoEntry OBJECT-TYPE
        SYNTAX         TnAwbingPortInfoEntry
        MAX-ACCESS     not-accessible
        STATUS         current
        DESCRIPTION    "."
        INDEX { ifIndex }
        ::= { tnAwbingPortInfoTable 1 }

    TnAwbingPortInfoEntry ::=
        SEQUENCE {
            tnAwbingPortInfoFunction INTEGER
        }

    tnAwbingPortInfoFunction OBJECT-TYPE
        SYNTAX         INTEGER {
                         lineIn(1),
                         otdrRx(2),
                         sigLout(3),
                         sigCout(4),
                         oscSfp(5),
                         osc(6),
                         custLan(7)
                       }
        MAX-ACCESS     read-only
        STATUS         current
        DESCRIPTION    "Indicates the functional type of this AWBING port."
        ::= { tnAwbingPortInfoEntry 1 }

-------------------------------------------------------------------------------
-- AWBILA Optical Port Info Scalar
-------------------------------------------------------------------------------
    tnAwbilaPortInfoAttributeTotal OBJECT-TYPE
        SYNTAX         Integer32
        MAX-ACCESS     read-only
        STATUS         current
        DESCRIPTION    "."
        ::= { tnOpticalPortInfo 339 }

-------------------------------------------------------------------------------
-- AWBILA Optical Port Info Table
-------------------------------------------------------------------------------
    tnAwbilaPortInfoTable OBJECT-TYPE
        SYNTAX         SEQUENCE OF TnAwbilaPortInfoEntry
        MAX-ACCESS     not-accessible
        STATUS         current
        DESCRIPTION    "The ports on a AWBILA optical card."
        ::= { tnOpticalPortInfo 340 }

    tnAwbilaPortInfoEntry OBJECT-TYPE
        SYNTAX         TnAwbilaPortInfoEntry
        MAX-ACCESS     not-accessible
        STATUS         current
        DESCRIPTION    "."
        INDEX { ifIndex }
        ::= { tnAwbilaPortInfoTable 1 }

    TnAwbilaPortInfoEntry ::=
        SEQUENCE {
            tnAwbilaPortInfoFunction INTEGER
        }

    tnAwbilaPortInfoFunction OBJECT-TYPE
        SYNTAX         INTEGER {
                         lineIn(1),
                         otdrRx(2),
                         otdrTx(3),
                         lineOut(4),
                         oscSfp(5),
                         osc(6),
                         custLan(7)
                       }
        MAX-ACCESS     read-only
        STATUS         current
        DESCRIPTION    "Indicates the functional type of this AWBILA port."
        ::= { tnAwbilaPortInfoEntry 1 }

--------------------------------------------------------------------------------
-- RA5P Optical Port Info Scalar
--------------------------------------------------------------------------------
    tnRa5pPortInfoAttributeTotal OBJECT-TYPE
        SYNTAX         Integer32
        MAX-ACCESS     read-only
        STATUS         current
        DESCRIPTION    "."
        ::= { tnOpticalPortInfo 341 }

--------------------------------------------------------------------------------
-- RA5P Optical Port Info Table
--------------------------------------------------------------------------------
    tnRa5pPortInfoTable OBJECT-TYPE
        SYNTAX         SEQUENCE OF TnRa5pPortInfoEntry
        MAX-ACCESS     not-accessible
        STATUS         current
        DESCRIPTION    "The ports on a RA5P optical card."
        ::= { tnOpticalPortInfo 342 }

    tnRa5pPortInfoEntry OBJECT-TYPE
        SYNTAX         TnRa5pPortInfoEntry
        MAX-ACCESS     not-accessible
        STATUS         current
        DESCRIPTION    "."
        INDEX { ifIndex }
        ::= { tnRa5pPortInfoTable 1 }

    TnRa5pPortInfoEntry ::=
        SEQUENCE {
            tnRa5pPortInfoFunction INTEGER
        }

    tnRa5pPortInfoFunction OBJECT-TYPE
        SYNTAX         INTEGER {
                         lineIn(1),
                         lineOut(2)
                       }
        MAX-ACCESS     read-only
        STATUS         current
        DESCRIPTION    "Indicates the functional type of this RA5P port."
        ::= { tnRa5pPortInfoEntry 1 }

--------------------------------------------------------------------------------
-- IROADM9M Optical Port Info Scalar
--------------------------------------------------------------------------------
    tnIroadm9mPortInfoAttributeTotal OBJECT-TYPE
        SYNTAX         Integer32
        MAX-ACCESS     read-only
        STATUS         current
        DESCRIPTION    "."
        ::= { tnOpticalPortInfo 343 }

--------------------------------------------------------------------------------
-- IROADM9M Optical Port Info Table
--------------------------------------------------------------------------------
    tnIroadm9mPortInfoTable OBJECT-TYPE
        SYNTAX         SEQUENCE OF TnIroadm9mPortInfoEntry
        MAX-ACCESS     not-accessible
        STATUS         current
        DESCRIPTION    "The ports on a IROADM9M optical card."
        ::= { tnOpticalPortInfo 344 }

    tnIroadm9mPortInfoEntry OBJECT-TYPE
        SYNTAX         TnIroadm9mPortInfoEntry
        MAX-ACCESS     not-accessible
        STATUS         current
        DESCRIPTION    "."
        INDEX { ifIndex }
        ::= { tnIroadm9mPortInfoTable 1 }

    TnIroadm9mPortInfoEntry ::=
        SEQUENCE {
            tnIroadm9mPortInfoFunction INTEGER
        }

    tnIroadm9mPortInfoFunction OBJECT-TYPE
        SYNTAX         INTEGER {
                         lineIn(1),
                         inv(2),
                         osc(3),
                         lineOut(4),
                         oscSfp(5),
                         adt(6),
                         dcm(7),
                         custLan(8)
                       }
        MAX-ACCESS     read-only
        STATUS         current
        DESCRIPTION    "Indicates the functional type of this IROADM9M port."
        ::= { tnIroadm9mPortInfoEntry 1 }

--------------------------------------------------------------------------------
-- S13X100 Optical Port Info Scalar
--------------------------------------------------------------------------------
    tnS13x100PortInfoAttributeTotal OBJECT-TYPE
        SYNTAX         Integer32
        MAX-ACCESS     read-only
        STATUS         current
        DESCRIPTION    "."
        ::= { tnOpticalPortInfo 345 }

--------------------------------------------------------------------------------
-- S13X100 Optical Port Info Table
--------------------------------------------------------------------------------
    tnS13x100PortInfoTable OBJECT-TYPE
        SYNTAX         SEQUENCE OF TnS13x100PortInfoEntry
        MAX-ACCESS     not-accessible
        STATUS         current
        DESCRIPTION    "The ports on a S13X100 optical card."
        ::= { tnOpticalPortInfo 346 }

    tnS13x100PortInfoEntry OBJECT-TYPE
        SYNTAX         TnS13x100PortInfoEntry
        MAX-ACCESS     not-accessible
        STATUS         current
        DESCRIPTION    "."
        INDEX { ifIndex }
        ::= { tnS13x100PortInfoTable 1 }

    TnS13x100PortInfoEntry ::=
        SEQUENCE {
            tnS13x100PortInfoFunction INTEGER
        }

    tnS13x100PortInfoFunction OBJECT-TYPE
        SYNTAX         INTEGER {
                         network(1),
                         client(2),
                         backplane(3)
                       }
        MAX-ACCESS     read-only
        STATUS         current
        DESCRIPTION    "Indicates the functional type of this S13X100 port."
        ::= { tnS13x100PortInfoEntry 1 }

--------------------------------------------------------------------------------
-- 12CE121 Optical Port Info Scalar
--------------------------------------------------------------------------------
    tn12ce121PortInfoAttributeTotal OBJECT-TYPE
        SYNTAX         Integer32
        MAX-ACCESS     read-only
        STATUS         current
        DESCRIPTION    "."
        ::= { tnOpticalPortInfo 347 }

--------------------------------------------------------------------------------
-- 12CE121 Optical Port Info Table
--------------------------------------------------------------------------------
    tn12ce121PortInfoTable OBJECT-TYPE
        SYNTAX         SEQUENCE OF Tn12ce121PortInfoEntry
        MAX-ACCESS     not-accessible
        STATUS         current
        DESCRIPTION    "The ports on a 12CE121 optical card."
        ::= { tnOpticalPortInfo 348 }

    tn12ce121PortInfoEntry OBJECT-TYPE
        SYNTAX         Tn12ce121PortInfoEntry
        MAX-ACCESS     not-accessible
        STATUS         current
        DESCRIPTION    "."
        INDEX { ifIndex }
        ::= { tn12ce121PortInfoTable 1 }

    Tn12ce121PortInfoEntry ::=
        SEQUENCE {
            tn12ce121PortInfoFunction INTEGER
        }

    tn12ce121PortInfoFunction OBJECT-TYPE
        SYNTAX         INTEGER {
                         client(1),
                         backplane(2),
                         tod(3),
                         ethman(4)
                       }
        MAX-ACCESS     read-only
        STATUS         current
        DESCRIPTION    "Indicates the functional type of this 12CE121 port."
        ::= { tn12ce121PortInfoEntry 1 }

--------------------------------------------------------------------------------
-- PTPIOCTL Optical Port Info Scalar
--------------------------------------------------------------------------------
    tnPtpioctlPortInfoAttributeTotal OBJECT-TYPE
        SYNTAX         Integer32
        MAX-ACCESS     read-only
        STATUS         current
        DESCRIPTION    "."
        ::= { tnOpticalPortInfo 349 }

--------------------------------------------------------------------------------
-- PTPIOCTL Optical Port Info Table
--------------------------------------------------------------------------------
    tnPtpioctlPortInfoTable OBJECT-TYPE
        SYNTAX         SEQUENCE OF TnPtpioctlPortInfoEntry
        MAX-ACCESS     not-accessible
        STATUS         current
        DESCRIPTION    "The ports on a Ptpioctl optical card."
        ::= { tnOpticalPortInfo 350 }

    tnPtpioctlPortInfoEntry OBJECT-TYPE
        SYNTAX         TnPtpioctlPortInfoEntry
        MAX-ACCESS     not-accessible
        STATUS         current
        DESCRIPTION    "."
        INDEX { ifIndex }
        ::= { tnPtpioctlPortInfoTable 1 }

    TnPtpioctlPortInfoEntry ::=
        SEQUENCE {
            tnPtpioctlPortInfoFunction INTEGER
        }

    tnPtpioctlPortInfoFunction OBJECT-TYPE
        SYNTAX         INTEGER {
                         oscLine(1),
                         oscSig(2),
                         otcLine(3),
                         otcSig(4)
                       }
        MAX-ACCESS     read-only
        STATUS         current
        DESCRIPTION    "Indicates the functional type of this Ptpioctl port."
        ::= { tnPtpioctlPortInfoEntry 1 }
--------------------------------------------------------------------------------
-- AA2DONWB Optical Port Info Scalar
--------------------------------------------------------------------------------
    tnAa2donwbPortInfoAttributeTotal OBJECT-TYPE
        SYNTAX         Integer32
        MAX-ACCESS     read-only
        STATUS         current
        DESCRIPTION    "."
        ::= { tnOpticalPortInfo 351 }

--------------------------------------------------------------------------------
-- AA2DONWB Optical Port Info Table
--------------------------------------------------------------------------------
    tnAa2donwbPortInfoTable OBJECT-TYPE
        SYNTAX         SEQUENCE OF TnAa2donwbPortInfoEntry
        MAX-ACCESS     not-accessible
        STATUS         current
        DESCRIPTION    "The ports on an AA2DONWB optical card."
        ::= { tnOpticalPortInfo 352 }

    tnAa2donwbPortInfoEntry OBJECT-TYPE
        SYNTAX         TnAa2donwbPortInfoEntry
        MAX-ACCESS     not-accessible
        STATUS         current
        DESCRIPTION    "."
        INDEX { ifIndex }
        ::= { tnAa2donwbPortInfoTable 1 }

    TnAa2donwbPortInfoEntry ::=
        SEQUENCE {
            tnAa2donwbPortInfoFunction  INTEGER
        }

    tnAa2donwbPortInfoFunction OBJECT-TYPE
        SYNTAX         INTEGER {
                         line(1),
                         signal(2),
                         inv(3),
                         osc(4),
                         oscSfp(5),
                         evoa(6)
                       }
        MAX-ACCESS     read-only
        STATUS         current
        DESCRIPTION    "Indicates the functional type of this AA2DONWB port."
        ::= { tnAa2donwbPortInfoEntry 1 }

--------------------------------------------------------------------------------
-- OSCTAPR Optical Port Info Scalar
--------------------------------------------------------------------------------
    tnOsctaprPortInfoAttributeTotal OBJECT-TYPE
        SYNTAX         Integer32
        MAX-ACCESS     read-only
        STATUS         current
        DESCRIPTION    "."
        ::= { tnOpticalPortInfo 353 }

--------------------------------------------------------------------------------
-- OSCTAPR Optical Port Info Table
--------------------------------------------------------------------------------
    tnOsctaprPortInfoTable OBJECT-TYPE
        SYNTAX         SEQUENCE OF TnOsctaprPortInfoEntry
        MAX-ACCESS     not-accessible
        STATUS         current
        DESCRIPTION    "The ports on an OSCTARP optical card."
        ::= { tnOpticalPortInfo 354 }

    tnOsctaprPortInfoEntry OBJECT-TYPE
        SYNTAX         TnOsctaprPortInfoEntry
        MAX-ACCESS     not-accessible
        STATUS         current
        DESCRIPTION    "."
        INDEX { ifIndex }
        ::= { tnOsctaprPortInfoTable 1 }

    TnOsctaprPortInfoEntry ::=
        SEQUENCE {
            tnOsctaprPortInfoFunction     INTEGER
        }

    tnOsctaprPortInfoFunction OBJECT-TYPE
        SYNTAX         INTEGER {
                         signal(1),
                         line(2),
                         inv(3),
                         osc(4),
                         oscSfp(5),
                         evoa(6)
                       }
        MAX-ACCESS     read-only
        STATUS         current
        DESCRIPTION    "Indicates the functional type of this OSCTAPR port."
        ::= { tnOsctaprPortInfoEntry 1 }

--------------------------------------------------------------------------------
-- 11QPA4B Optical Port Info Scalar
--------------------------------------------------------------------------------
    tn11qpa4bPortInfoAttributeTotal OBJECT-TYPE
        SYNTAX         Integer32
        MAX-ACCESS     read-only
        STATUS         current
        DESCRIPTION    "."
        ::= { tnOpticalPortInfo 355 }

--------------------------------------------------------------------------------
-- 11QPA4B Optical Port Info Table
--------------------------------------------------------------------------------
    tn11qpa4bPortInfoTable OBJECT-TYPE
        SYNTAX         SEQUENCE OF Tn11qpa4bPortInfoEntry
        MAX-ACCESS     not-accessible
        STATUS         current
        DESCRIPTION    "The ports on a 11QPA4B optical card."
        ::= { tnOpticalPortInfo 356 }

    tn11qpa4bPortInfoEntry OBJECT-TYPE
        SYNTAX         Tn11qpa4bPortInfoEntry
        MAX-ACCESS     not-accessible
        STATUS         current
        DESCRIPTION    "."
        INDEX { ifIndex }
        ::= { tn11qpa4bPortInfoTable 1 }

    Tn11qpa4bPortInfoEntry ::=
        SEQUENCE {
            tn11qpa4bPortInfoFunction INTEGER
        }

    tn11qpa4bPortInfoFunction OBJECT-TYPE
        SYNTAX         INTEGER {
                         network(1),
                         client(2),
                         evoa(3),
                         backplane(4)
                       }
        MAX-ACCESS     read-only
        STATUS         current
        DESCRIPTION    "Indicates the functional type of this 11QPA4B port."
        ::= { tn11qpa4bPortInfoEntry 1 }

--------------------------------------------------------------------------------
-- 1UX100 Optical Port Info Scalar
--------------------------------------------------------------------------------
    tn1ux100PortInfoAttributeTotal OBJECT-TYPE
        SYNTAX         Integer32
        MAX-ACCESS     read-only
        STATUS         current
        DESCRIPTION    "."
        ::= { tnOpticalPortInfo 357 }

--------------------------------------------------------------------------------
-- 1UX100 Optical Port Info Table
--------------------------------------------------------------------------------
    tn1ux100PortInfoTable OBJECT-TYPE
        SYNTAX         SEQUENCE OF Tn1ux100PortInfoEntry
        MAX-ACCESS     not-accessible
        STATUS         current
        DESCRIPTION    "The ports on a 1ux100 optical card."
        ::= { tnOpticalPortInfo 358 }

    tn1ux100PortInfoEntry OBJECT-TYPE
        SYNTAX         Tn1ux100PortInfoEntry
        MAX-ACCESS     not-accessible
        STATUS         current
        DESCRIPTION    "."
        INDEX { ifIndex }
        ::= { tn1ux100PortInfoTable 1 }

    Tn1ux100PortInfoEntry ::= SEQUENCE {
        tn1ux100PortInfoFunction INTEGER
    }

    tn1ux100PortInfoFunction OBJECT-TYPE
        SYNTAX         INTEGER {
                         network(1)
                       }
        MAX-ACCESS     read-only
        STATUS         current
        DESCRIPTION    "Indicates the functional type of
                        this 1ux100 port."
        ::= { tn1ux100PortInfoEntry 1 }

--------------------------------------------------------------------------------
-- 20AX200 Optical Port Info Scalar
--------------------------------------------------------------------------------
    tn20ax200PortInfoAttributeTotal OBJECT-TYPE
        SYNTAX         Integer32
        MAX-ACCESS     read-only
        STATUS         current
        DESCRIPTION    "."
        ::= { tnOpticalPortInfo 359 }

--------------------------------------------------------------------------------
-- 20AX200 Optical Port Info Table
--------------------------------------------------------------------------------
    tn20ax200PortInfoTable OBJECT-TYPE
        SYNTAX         SEQUENCE OF Tn20ax200PortInfoEntry
        MAX-ACCESS     not-accessible
        STATUS         current
        DESCRIPTION    "The ports on a 20ax200 optical card."
        ::= { tnOpticalPortInfo 360 }

    tn20ax200PortInfoEntry OBJECT-TYPE
        SYNTAX         Tn20ax200PortInfoEntry
        MAX-ACCESS     not-accessible
        STATUS         current
        DESCRIPTION    "."
        INDEX { ifIndex }
        ::= { tn20ax200PortInfoTable 1 }

    Tn20ax200PortInfoEntry ::= SEQUENCE {
        tn20ax200PortInfoFunction INTEGER
    }

    tn20ax200PortInfoFunction OBJECT-TYPE
        SYNTAX         INTEGER {
                         port(1)
                       }
        MAX-ACCESS     read-only
        STATUS         current
        DESCRIPTION    "Indicates the functional type of
                        this 20ax200 port."
        ::= { tn20ax200PortInfoEntry 1 }

--------------------------------------------------------------------------------
-- 20MX80 Optical Port Info Scalar
--------------------------------------------------------------------------------
    tn20mx80PortInfoAttributeTotal OBJECT-TYPE
        SYNTAX         Integer32
        MAX-ACCESS     read-only
        STATUS         current
        DESCRIPTION    "."
        ::= { tnOpticalPortInfo 361 }

--------------------------------------------------------------------------------
--  20MX80 Optical Port Info Table
--------------------------------------------------------------------------------
    tn20mx80PortInfoTable OBJECT-TYPE
        SYNTAX         SEQUENCE OF Tn20mx80PortInfoEntry
        MAX-ACCESS     not-accessible
        STATUS         current
        DESCRIPTION    "The ports on a 20mx80 optical card."
        ::= { tnOpticalPortInfo 362 }

    tn20mx80PortInfoEntry OBJECT-TYPE
        SYNTAX         Tn20mx80PortInfoEntry
        MAX-ACCESS     not-accessible
        STATUS         current
        DESCRIPTION    "."
        INDEX { ifIndex }
        ::= { tn20mx80PortInfoTable 1 }

    Tn20mx80PortInfoEntry ::= SEQUENCE {
        tn20mx80PortInfoFunction INTEGER
    }

    tn20mx80PortInfoFunction OBJECT-TYPE
        SYNTAX         INTEGER {
                         port(1)
                       }
        MAX-ACCESS     read-only
        STATUS         current
        DESCRIPTION    "Indicates the functional type of
                        this 20mx80 port."
        ::= { tn20mx80PortInfoEntry 1 }

--------------------------------------------------------------------------------
-- AAR2X-8A Optical Port Info Scalar
--------------------------------------------------------------------------------
    tnAar2x8aPortInfoAttributeTotal OBJECT-TYPE
        SYNTAX         Integer32
        MAX-ACCESS     read-only
        STATUS         current
        DESCRIPTION    "."
        ::= { tnOpticalPortInfo 363 }

--------------------------------------------------------------------------------
-- AAR2X-8A Optical Port Info Table
--------------------------------------------------------------------------------
    tnAar2x8aPortInfoTable OBJECT-TYPE
        SYNTAX         SEQUENCE OF TnAar2x8aPortInfoEntry
        MAX-ACCESS     not-accessible
        STATUS         current
        DESCRIPTION    "The ports on an AAR2X-8A optical card."
        ::= { tnOpticalPortInfo 364 }

    tnAar2x8aPortInfoEntry OBJECT-TYPE
        SYNTAX         TnAar2x8aPortInfoEntry
        MAX-ACCESS     not-accessible
        STATUS         current
        DESCRIPTION    "."
        INDEX { ifIndex }
        ::= { tnAar2x8aPortInfoTable 1 }

    TnAar2x8aPortInfoEntry ::=
        SEQUENCE {
            tnAar2x8aPortInfoFunction   INTEGER
        }

    tnAar2x8aPortInfoFunction OBJECT-TYPE
        SYNTAX         INTEGER {
                         ampIn(1),
                         ampOut(2),
                         mpoFsm(3),
                         mpoMcs(4)
                       }
        MAX-ACCESS     read-only
        STATUS         current
        DESCRIPTION    "Indicates the functional type of this AAR2X-8A port."
        ::= { tnAar2x8aPortInfoEntry 1 }

--------------------------------------------------------------------------------
-- S13X100E Optical Port Info Scalar
--------------------------------------------------------------------------------
    tnS13x100ePortInfoAttributeTotal OBJECT-TYPE
        SYNTAX         Integer32
        MAX-ACCESS     read-only
        STATUS         current
        DESCRIPTION    "."
        ::= { tnOpticalPortInfo 365 }

--------------------------------------------------------------------------------
-- S13X100E Optical Port Info Table
--------------------------------------------------------------------------------
    tnS13x100ePortInfoTable OBJECT-TYPE
        SYNTAX         SEQUENCE OF TnS13x100ePortInfoEntry
        MAX-ACCESS     not-accessible
        STATUS         current
        DESCRIPTION    "The ports on a S13x100e optical card."
        ::= { tnOpticalPortInfo 366 }

    tnS13x100ePortInfoEntry OBJECT-TYPE
        SYNTAX         TnS13x100ePortInfoEntry
        MAX-ACCESS     not-accessible
        STATUS         current
        DESCRIPTION    "."
        INDEX { ifIndex }
        ::= { tnS13x100ePortInfoTable 1 }

    TnS13x100ePortInfoEntry ::=
        SEQUENCE {
            tnS13x100ePortInfoFunction INTEGER
        }

    tnS13x100ePortInfoFunction OBJECT-TYPE
        SYNTAX         INTEGER {
                         network(1),
                         client(2),
                         backplane(3)
                       }
        MAX-ACCESS     read-only
        STATUS         current
        DESCRIPTION    "Indicates the functional type of this S13X100E port."
        ::= { tnS13x100ePortInfoEntry 1 }

--------------------------------------------------------------------------------
-- WTOCMFL Optical Port Info Scalar
--------------------------------------------------------------------------------
    tnWtocmflPortInfoAttributeTotal OBJECT-TYPE
        SYNTAX         Integer32
        MAX-ACCESS     read-only
        STATUS         current
        DESCRIPTION    "."
        ::= { tnOpticalPortInfo 367 }

--------------------------------------------------------------------------------
-- WTOCMFL Optical Port Info Table
--------------------------------------------------------------------------------
    tnWtocmflPortInfoTable OBJECT-TYPE
        SYNTAX         SEQUENCE OF TnWtocmflPortInfoEntry
        MAX-ACCESS     not-accessible
        STATUS         current
        DESCRIPTION    "The ports on a WTOCMFL optical card."
        ::= { tnOpticalPortInfo 368 }

    tnWtocmflPortInfoEntry OBJECT-TYPE
        SYNTAX         TnWtocmflPortInfoEntry
        MAX-ACCESS     not-accessible
        STATUS         current
        DESCRIPTION    "."
        INDEX { ifIndex }
        ::= { tnWtocmflPortInfoTable 1 }

    TnWtocmflPortInfoEntry ::=
        SEQUENCE {
            tnWtocmflPortInfoFunction  INTEGER
        }

    tnWtocmflPortInfoFunction OBJECT-TYPE
        SYNTAX         INTEGER {
                         detect(1)
                       }
        MAX-ACCESS     read-only
        STATUS         current
        DESCRIPTION    "Indicates the functional type of this WTOCMFL port."
        ::= { tnWtocmflPortInfoEntry 1 }

--------------------------------------------------------------------------------
-- AAR2X-8AL Optical Port Info Scalar
--------------------------------------------------------------------------------
    tnAar2x8alPortInfoAttributeTotal OBJECT-TYPE
        SYNTAX         Integer32
        MAX-ACCESS     read-only
        STATUS         current
        DESCRIPTION    "."
        ::= { tnOpticalPortInfo 369 }

--------------------------------------------------------------------------------
-- AAR2X-8AL Optical Port Info Table
--------------------------------------------------------------------------------
    tnAar2x8alPortInfoTable OBJECT-TYPE
        SYNTAX         SEQUENCE OF TnAar2x8alPortInfoEntry
        MAX-ACCESS     not-accessible
        STATUS         current
        DESCRIPTION    "The ports on an AAR2X-8AL optical card."
        ::= { tnOpticalPortInfo 370 }

    tnAar2x8alPortInfoEntry OBJECT-TYPE
        SYNTAX         TnAar2x8alPortInfoEntry
        MAX-ACCESS     not-accessible
        STATUS         current
        DESCRIPTION    "."
        INDEX { ifIndex }
        ::= { tnAar2x8alPortInfoTable 1 }

    TnAar2x8alPortInfoEntry ::=
        SEQUENCE {
            tnAar2x8alPortInfoFunction   INTEGER
        }

    tnAar2x8alPortInfoFunction OBJECT-TYPE
        SYNTAX         INTEGER {
                         ampIn(1),
                         ampOut(2),
                         mpoFsm(3),
                         mpoMcs(4)
                       }
        MAX-ACCESS     read-only
        STATUS         current
        DESCRIPTION    "Indicates the functional type of this AAR2X-8AL port."
        ::= { tnAar2x8alPortInfoEntry 1 }

--------------------------------------------------------------------------------
-- WR20-TFML Optical Port Info Scalar
--------------------------------------------------------------------------------
    tnWr20tfmlPortInfoAttributeTotal OBJECT-TYPE
        SYNTAX         Integer32
        MAX-ACCESS     read-only
        STATUS         current
        DESCRIPTION    "."
        ::= { tnOpticalPortInfo 371 }

--------------------------------------------------------------------------------
-- WR20-TFML Optical Port Info Table
--------------------------------------------------------------------------------
    tnWr20tfmlPortInfoTable OBJECT-TYPE
        SYNTAX         SEQUENCE OF TnWr20tfmlPortInfoEntry
        MAX-ACCESS     not-accessible
        STATUS         current
        DESCRIPTION    "The ports on a WR20-TFML optical card."
        ::= { tnOpticalPortInfo 372 }

    tnWr20tfmlPortInfoEntry OBJECT-TYPE
        SYNTAX         TnWr20tfmlPortInfoEntry
        MAX-ACCESS     not-accessible
        STATUS         current
        DESCRIPTION    "."
        INDEX { ifIndex }
        ::= { tnWr20tfmlPortInfoTable 1 }

    TnWr20tfmlPortInfoEntry ::=
        SEQUENCE {
            tnWr20tfmlPortInfoFunction      INTEGER
        }

    tnWr20tfmlPortInfoFunction OBJECT-TYPE
        SYNTAX         INTEGER {
                         signal(1),
                         adt(2),
                         ad(3),
                         inv(4),
                         mpoDropOut(5),
                         mpoAddIn(6)
                       }
        MAX-ACCESS     read-only
        STATUS         current
        DESCRIPTION    "Indicates the functional type of this WR20-TFML port."
        ::= { tnWr20tfmlPortInfoEntry 1 }

--------------------------------------------------------------------------------
-- MCS8-16L Optical Port Info Scalar
--------------------------------------------------------------------------------
    tnMcs8x16lPortInfoAttributeTotal OBJECT-TYPE
        SYNTAX         Integer32
        MAX-ACCESS     read-only
        STATUS         current
        DESCRIPTION    "."
        ::= { tnOpticalPortInfo 373 }

--------------------------------------------------------------------------------
-- MCS8-16L Optical Port Info Table
--------------------------------------------------------------------------------
    tnMcs8x16lPortInfoTable OBJECT-TYPE
        SYNTAX         SEQUENCE OF TnMcs8x16lPortInfoEntry
        MAX-ACCESS     not-accessible
        STATUS         current
        DESCRIPTION    "The ports on a MCS8-16L optical card."
        ::= { tnOpticalPortInfo 374 }

    tnMcs8x16lPortInfoEntry OBJECT-TYPE
        SYNTAX         TnMcs8x16lPortInfoEntry
        MAX-ACCESS     not-accessible
        STATUS         current
        DESCRIPTION    "."
        INDEX { ifIndex }
        ::= { tnMcs8x16lPortInfoTable 1 }

    TnMcs8x16lPortInfoEntry ::=
        SEQUENCE {
            tnMcs8x16lPortInfoFunction                  INTEGER
        }

    tnMcs8x16lPortInfoFunction OBJECT-TYPE
        SYNTAX         INTEGER {
                         signal(1),
                         ad(2),
                         mpoAar(3)
                       }
        MAX-ACCESS     read-only
        STATUS         current
        DESCRIPTION    "Indicates the functional type of this
                        MCS8-16L port."
        ::= { tnMcs8x16lPortInfoEntry 1 }

--------------------------------------------------------------------------------
-- PSS8x Power Filter Port Info Scalar
--------------------------------------------------------------------------------
    tnPSS8xPowerFilterPortInfoAttributeTotal OBJECT-TYPE
        SYNTAX         Integer32
        MAX-ACCESS     read-only
        STATUS         current
        DESCRIPTION    "."
        ::= { tnOpticalPortInfo 375 }

--------------------------------------------------------------------------------
-- PSS8xPower Filter Port Info Table
--------------------------------------------------------------------------------
    tnPSS8xPowerFilterPortInfoTable OBJECT-TYPE
        SYNTAX         SEQUENCE OF TnPSS8xPowerFilterPortInfoEntry
        MAX-ACCESS     not-accessible
        STATUS         current
        DESCRIPTION    "The ports on a PSS8xPowerFilter optical card."
        ::= { tnOpticalPortInfo 376 }

    tnPSS8xPowerFilterPortInfoEntry OBJECT-TYPE
        SYNTAX         TnPSS8xPowerFilterPortInfoEntry
        MAX-ACCESS     not-accessible
        STATUS         current
        DESCRIPTION    "."
        INDEX { ifIndex }
        ::= { tnPSS8xPowerFilterPortInfoTable 1 }

    TnPSS8xPowerFilterPortInfoEntry ::=
        SEQUENCE {
            tnPSS8xPowerFilterPortInfoFunction INTEGER
        }

    tnPSS8xPowerFilterPortInfoFunction OBJECT-TYPE
        SYNTAX         INTEGER {
                         powerFilterPort1(1)
                       }
        MAX-ACCESS     read-only
        STATUS         current
        DESCRIPTION    "Indicates the functional type of this PSS8xPowerFilter port."
        ::= { tnPSS8xPowerFilterPortInfoEntry 1 }


--------------------------------------------------------------------------------
-- LCI2000 Optical Port Info Scalar
--------------------------------------------------------------------------------
    tnLcI2000PortInfoAttributeTotal OBJECT-TYPE
        SYNTAX         Integer32
        MAX-ACCESS     read-only
        STATUS         current
        DESCRIPTION    "."
        ::= { tnOpticalPortInfo 377 }

--------------------------------------------------------------------------------
-- LCI2000 Optical Port Info Table
--------------------------------------------------------------------------------
    tnLcI2000PortInfoTable OBJECT-TYPE
        SYNTAX         SEQUENCE OF TnLcI2000PortInfoEntry
        MAX-ACCESS     not-accessible
        STATUS         current
        DESCRIPTION    "The ports on a LCI2000 optical card."
        ::= { tnOpticalPortInfo 378 }

    tnLcI2000PortInfoEntry OBJECT-TYPE
        SYNTAX         TnLcI2000PortInfoEntry
        MAX-ACCESS     not-accessible
        STATUS         current
        DESCRIPTION    "."
        INDEX { ifIndex }
        ::= { tnLcI2000PortInfoTable 1 }

    TnLcI2000PortInfoEntry ::= SEQUENCE {
        tnLcI2000PortInfoFunction INTEGER
    }

    tnLcI2000PortInfoFunction OBJECT-TYPE
        SYNTAX         INTEGER {
                         network(1),
                         client(2)
                       }
        MAX-ACCESS     read-only
        STATUS         current
        DESCRIPTION    "Indicates the functional type of this LCI2000 port."
        ::= { tnLcI2000PortInfoEntry 1 }

--------------------------------------------------------------------------------
-- 30SE300 Optical Port Info Scalar
--------------------------------------------------------------------------------
    tn30se300PortInfoAttributeTotal OBJECT-TYPE
        SYNTAX         Integer32
        MAX-ACCESS     read-only
        STATUS         current
        DESCRIPTION    "."
        ::= { tnOpticalPortInfo 379 }

--------------------------------------------------------------------------------
-- 30SE300 Optical Port Info Table
--------------------------------------------------------------------------------
    tn30se300PortInfoTable OBJECT-TYPE
        SYNTAX         SEQUENCE OF Tn30se300PortInfoEntry
        MAX-ACCESS     not-accessible
        STATUS         current
        DESCRIPTION    "The ports on a 30SE300 optical card."
        ::= { tnOpticalPortInfo 380 }

    tn30se300PortInfoEntry OBJECT-TYPE
        SYNTAX         Tn30se300PortInfoEntry
        MAX-ACCESS     not-accessible
        STATUS         current
        DESCRIPTION    "."
        INDEX { ifIndex }
        ::= { tn30se300PortInfoTable 1 }

    Tn30se300PortInfoEntry ::= SEQUENCE {
        tn30se300PortInfoFunction INTEGER
    }

    tn30se300PortInfoFunction OBJECT-TYPE
        SYNTAX         INTEGER {
                         client(1),
                         network(2),
                         backplane(3),
                         tod(4),
                         ethman(5)
                       }
        MAX-ACCESS     read-only
        STATUS         current
        DESCRIPTION    "Indicates the functional type of
                        this 30SE300 port."
        ::= { tn30se300PortInfoEntry 1 }


--------------------------------------------------------------------------------
-- 6SE300 Optical Port Info Scalar
--------------------------------------------------------------------------------
    tn6se300PortInfoAttributeTotal OBJECT-TYPE
        SYNTAX         Integer32
        MAX-ACCESS     read-only
        STATUS         current
        DESCRIPTION    "."
        ::= { tnOpticalPortInfo 381 }

--------------------------------------------------------------------------------
-- 6SE300 Optical Port Info Table
--------------------------------------------------------------------------------
    tn6se300PortInfoTable OBJECT-TYPE
        SYNTAX         SEQUENCE OF Tn6se300PortInfoEntry
        MAX-ACCESS     not-accessible
        STATUS         current
        DESCRIPTION    "The ports on a 6SE300 optical card."
        ::= { tnOpticalPortInfo 382 }

    tn6se300PortInfoEntry OBJECT-TYPE
        SYNTAX         Tn6se300PortInfoEntry
        MAX-ACCESS     not-accessible
        STATUS         current
        DESCRIPTION    "."
        INDEX { ifIndex }
        ::= { tn6se300PortInfoTable 1 }

    Tn6se300PortInfoEntry ::= SEQUENCE {
        tn6se300PortInfoFunction INTEGER
    }

    tn6se300PortInfoFunction OBJECT-TYPE
        SYNTAX         INTEGER {
                         client(1),
                         network(2),
                         backplane(3),
                         tod(4),
                         ethman(5)
                       }
        MAX-ACCESS     read-only
        STATUS         current
        DESCRIPTION    "Indicates the functional type of
                        this 6SE300 port."
        ::= { tn6se300PortInfoEntry 1 }

--------------------------------------------------------------------------------
-- OTDRWB (Optical Time Domain Reflectometer WB) Optical Port Info Scalar
--------------------------------------------------------------------------------
    tnOtdrwbPortInfoAttributeTotal OBJECT-TYPE
        SYNTAX         Integer32
        MAX-ACCESS     read-only
        STATUS         current
        DESCRIPTION    "."
        ::= { tnOpticalPortInfo 383 }

--------------------------------------------------------------------------------
-- OTDRWB (Optical Time Domain Reflectometer WB) Optical Port Info Table
--------------------------------------------------------------------------------
    tnOtdrwbPortInfoTable OBJECT-TYPE
        SYNTAX         SEQUENCE OF TnOtdrwbPortInfoEntry
        MAX-ACCESS     not-accessible
        STATUS         current
        DESCRIPTION    "The ports on an OTDRWB optical card."
        ::= { tnOpticalPortInfo 384 }

    tnOtdrwbPortInfoEntry OBJECT-TYPE
        SYNTAX         TnOtdrwbPortInfoEntry
        MAX-ACCESS     not-accessible
        STATUS         current
        DESCRIPTION    "."
        INDEX { ifIndex }
        ::= { tnOtdrwbPortInfoTable 1 }

    TnOtdrwbPortInfoEntry ::=
        SEQUENCE {
            tnOtdrwbPortInfoFunction INTEGER
        }

    tnOtdrwbPortInfoFunction OBJECT-TYPE
        SYNTAX         INTEGER {
                         px(1)
                       }
        MAX-ACCESS     read-only
        STATUS         current
        DESCRIPTION    "Indicates the functional type of this OTDRWB port."
        ::= { tnOtdrwbPortInfoEntry 1 }

--------------------------------------------------------------------------------
-- 8DC30T Optical Port Info Scalar
--------------------------------------------------------------------------------
    tn8dc30tPortInfoAttributeTotal OBJECT-TYPE
        SYNTAX         Integer32
        MAX-ACCESS     read-only
        STATUS         current
        DESCRIPTION    "."
        ::= { tnOpticalPortInfo 385 }

--------------------------------------------------------------------------------
-- 8DC30T Optical Port Info Table
--------------------------------------------------------------------------------
    tn8dc30tPortInfoTable OBJECT-TYPE
        SYNTAX         SEQUENCE OF Tn8dc30tPortInfoEntry
        MAX-ACCESS     not-accessible
        STATUS         current
        DESCRIPTION    "The ports on a 8DC30T optical card."
        ::= { tnOpticalPortInfo 386 }

    tn8dc30tPortInfoEntry OBJECT-TYPE
        SYNTAX         Tn8dc30tPortInfoEntry
        MAX-ACCESS     not-accessible
        STATUS         current
        DESCRIPTION    "."
        INDEX { ifIndex }
        ::= { tn8dc30tPortInfoTable 1 }

    Tn8dc30tPortInfoEntry ::= SEQUENCE {
        tn8dc30tPortInfoFunction INTEGER
    }

    tn8dc30tPortInfoFunction OBJECT-TYPE
        SYNTAX         INTEGER {
                         timing(1)
                       }
        MAX-ACCESS     read-only
        STATUS         current
        DESCRIPTION    "Indicates the functional type of
                        this 8DC30T port."
        ::= { tn8dc30tPortInfoEntry 1 }

--------------------------------------------------------------------------------
-- 16DC65T Optical Port Info Scalar
--------------------------------------------------------------------------------
    tn16dc65tPortInfoAttributeTotal OBJECT-TYPE
        SYNTAX         Integer32
        MAX-ACCESS     read-only
        STATUS         current
        DESCRIPTION    "."
        ::= { tnOpticalPortInfo 387 }

--------------------------------------------------------------------------------
-- 16DC65T Optical Port Info Table
--------------------------------------------------------------------------------
    tn16dc65tPortInfoTable OBJECT-TYPE
        SYNTAX         SEQUENCE OF Tn16dc65tPortInfoEntry
        MAX-ACCESS     not-accessible
        STATUS         current
        DESCRIPTION    "The ports on a 16DC65T optical card."
        ::= { tnOpticalPortInfo 388 }

    tn16dc65tPortInfoEntry OBJECT-TYPE
        SYNTAX         Tn16dc65tPortInfoEntry
        MAX-ACCESS     not-accessible
        STATUS         current
        DESCRIPTION    "."
        INDEX { ifIndex }
        ::= { tn16dc65tPortInfoTable 1 }

    Tn16dc65tPortInfoEntry ::= SEQUENCE {
        tn16dc65tPortInfoFunction INTEGER
    }

    tn16dc65tPortInfoFunction OBJECT-TYPE
        SYNTAX         INTEGER {
                         timing(1),
                         tod(2),
                         bits(3)
                       }
        MAX-ACCESS     read-only
        STATUS         current
        DESCRIPTION    "Indicates the functional type of
                        this 16DC65T port."
        ::= { tn16dc65tPortInfoEntry 1 }

--------------------------------------------------------------------------------
-- D5X500L Optical Port Info Scalar
--------------------------------------------------------------------------------
    tnD5x500lPortInfoAttributeTotal OBJECT-TYPE
        SYNTAX         Integer32
        MAX-ACCESS     read-only
        STATUS         current
        DESCRIPTION    "."
        ::= { tnOpticalPortInfo 389 }

--------------------------------------------------------------------------------
-- D5X500L Optical Port Info Table
--------------------------------------------------------------------------------
    tnD5x500lPortInfoTable OBJECT-TYPE
        SYNTAX         SEQUENCE OF TnD5x500lPortInfoEntry
        MAX-ACCESS     not-accessible
        STATUS         current
        DESCRIPTION    "The ports on a D5X500L optical card."
        ::= { tnOpticalPortInfo 390 }

    tnD5x500lPortInfoEntry OBJECT-TYPE
        SYNTAX         TnD5x500lPortInfoEntry
        MAX-ACCESS     not-accessible
        STATUS         current
        DESCRIPTION    "."
        INDEX { ifIndex }
        ::= { tnD5x500lPortInfoTable 1 }

    TnD5x500lPortInfoEntry ::=
        SEQUENCE {
            tnD5x500lPortInfoFunction INTEGER
        }

    tnD5x500lPortInfoFunction OBJECT-TYPE
        SYNTAX         INTEGER {
                         network(1),
                         client(2),
                         backplane(3)
                       }
        MAX-ACCESS     read-only
        STATUS         current
        DESCRIPTION    "Indicates the functional type of this D5X500L port."
        ::= { tnD5x500lPortInfoEntry 1 }

--------------------------------------------------------------------------------
-- LCI2000L Optical Port Info Scalar
--------------------------------------------------------------------------------
    tnLcI2000lPortInfoAttributeTotal OBJECT-TYPE
        SYNTAX         Integer32
        MAX-ACCESS     read-only
        STATUS         current
        DESCRIPTION    "."
        ::= { tnOpticalPortInfo 391 }

--------------------------------------------------------------------------------
-- LCI2000L Optical Port Info Table
--------------------------------------------------------------------------------
    tnLcI2000lPortInfoTable OBJECT-TYPE
        SYNTAX         SEQUENCE OF TnLcI2000lPortInfoEntry
        MAX-ACCESS     not-accessible
        STATUS         current
        DESCRIPTION    "The ports on a LCI2000L optical card."
        ::= { tnOpticalPortInfo 392 }

    tnLcI2000lPortInfoEntry OBJECT-TYPE
        SYNTAX         TnLcI2000lPortInfoEntry
        MAX-ACCESS     not-accessible
        STATUS         current
        DESCRIPTION    "."
        INDEX { ifIndex }
        ::= { tnLcI2000lPortInfoTable 1 }

    TnLcI2000lPortInfoEntry ::= SEQUENCE {
        tnLcI2000lPortInfoFunction INTEGER
    }

    tnLcI2000lPortInfoFunction OBJECT-TYPE
        SYNTAX         INTEGER {
                         network(1),
                         client(2)
                       }
        MAX-ACCESS     read-only
        STATUS         current
        DESCRIPTION    "Indicates the functional type of this LCI2000L port."
        ::= { tnLcI2000lPortInfoEntry 1 }

--------------------------------------------------------------------------------
-- IROADM9R Optical Port Info Scalar
--------------------------------------------------------------------------------
    tnIroadm9rPortInfoAttributeTotal OBJECT-TYPE
        SYNTAX         Integer32
        MAX-ACCESS     read-only
        STATUS         current
        DESCRIPTION    "."
        ::= { tnOpticalPortInfo 393 }

--------------------------------------------------------------------------------
-- IROADM9R Optical Port Info Table
--------------------------------------------------------------------------------
    tnIroadm9rPortInfoTable OBJECT-TYPE
        SYNTAX         SEQUENCE OF TnIroadm9rPortInfoEntry
        MAX-ACCESS     not-accessible
        STATUS         current
        DESCRIPTION    "The ports on a IROADM9R optical card."
        ::= { tnOpticalPortInfo 394 }

    tnIroadm9rPortInfoEntry OBJECT-TYPE
        SYNTAX         TnIroadm9rPortInfoEntry
        MAX-ACCESS     not-accessible
        STATUS         current
        DESCRIPTION    "."
        INDEX { ifIndex }
        ::= { tnIroadm9rPortInfoTable 1 }

    TnIroadm9rPortInfoEntry ::=
        SEQUENCE {
            tnIroadm9rPortInfoFunction INTEGER
        }

    tnIroadm9rPortInfoFunction OBJECT-TYPE
        SYNTAX         INTEGER {
                         lineIn(1),
                         inv(2),
                         osc(3),
                         lineOut(4),
                         oscSfp(5),
                         adt(6),
                         otdrRx(7),
                         otdrTx(8),
                         custLan(9)
                       }
        MAX-ACCESS     read-only
        STATUS         current
        DESCRIPTION    "Indicates the functional type of this IROADM9R port."
        ::= { tnIroadm9rPortInfoEntry 1 }

--------------------------------------------------------------------------------
-- RA2P96 Optical Port Info Scalar
--------------------------------------------------------------------------------
    tnRa2p96PortInfoAttributeTotal OBJECT-TYPE
        SYNTAX         Integer32
        MAX-ACCESS     read-only
        STATUS         current
        DESCRIPTION    "."
        ::= { tnOpticalPortInfo 395 }

--------------------------------------------------------------------------------
-- RA2P96 Optical Port Info Table
--------------------------------------------------------------------------------
    tnRa2p96PortInfoTable OBJECT-TYPE
        SYNTAX         SEQUENCE OF TnRa2p96PortInfoEntry
        MAX-ACCESS     not-accessible
        STATUS         current
        DESCRIPTION    "The ports on a RA2P96 optical card."
        ::= { tnOpticalPortInfo 396 }

    tnRa2p96PortInfoEntry OBJECT-TYPE
        SYNTAX         TnRa2p96PortInfoEntry
        MAX-ACCESS     not-accessible
        STATUS         current
        DESCRIPTION    "."
        INDEX { ifIndex }
        ::= { tnRa2p96PortInfoTable 1 }

    TnRa2p96PortInfoEntry ::=
        SEQUENCE {
            tnRa2p96PortInfoFunction INTEGER
        }

    tnRa2p96PortInfoFunction OBJECT-TYPE
        SYNTAX         INTEGER {
                         lineIn(1),
                         lineOut(2),
                         oscOut(3),
                         otdrRx(4)
                       }
        MAX-ACCESS     read-only
        STATUS         current
        DESCRIPTION    "Indicates the functional type of this Ra2p96 port."
        ::= { tnRa2p96PortInfoEntry 1 }

--------------------------------------------------------------------------------
-- OTDRM (Optical Time Domain Reflectometer) Optical Port Info Scalar
--------------------------------------------------------------------------------
    tnOtdrmPortInfoAttributeTotal OBJECT-TYPE
        SYNTAX         Integer32
        MAX-ACCESS     read-only
        STATUS         current
        DESCRIPTION    "."
        ::= { tnOpticalPortInfo 397 }

--------------------------------------------------------------------------------
-- OTDRM (Optical Time Domain Reflectometer) Optical Port Info Table
--------------------------------------------------------------------------------
    tnOtdrmPortInfoTable OBJECT-TYPE
        SYNTAX         SEQUENCE OF TnOtdrmPortInfoEntry
        MAX-ACCESS     not-accessible
        STATUS         current
        DESCRIPTION    "The ports on an OTDRM optical card."
        ::= { tnOpticalPortInfo 398 }

    tnOtdrmPortInfoEntry OBJECT-TYPE
        SYNTAX         TnOtdrmPortInfoEntry
        MAX-ACCESS     not-accessible
        STATUS         current
        DESCRIPTION    "."
        INDEX { ifIndex }
        ::= { tnOtdrmPortInfoTable 1 }

    TnOtdrmPortInfoEntry ::=
        SEQUENCE {
            tnOtdrmPortInfoFunction INTEGER
        }

    tnOtdrmPortInfoFunction OBJECT-TYPE
        SYNTAX         INTEGER {
                         px(1)
                       }
        MAX-ACCESS     read-only
        STATUS         current
        DESCRIPTION    "Indicates the functional type of this OTDRM port."
        ::= { tnOtdrmPortInfoEntry 1 }

--------------------------------------------------------------------------------
-- Ethernet to TDM Port Association Info Scalars
--------------------------------------------------------------------------------
    tnEthToTDMPortAssocInfoAttributeTotal OBJECT-TYPE
        SYNTAX         Integer32
        MAX-ACCESS     read-only
        STATUS         current
        DESCRIPTION    "."
        ::= { tnOpticalPortInfo 399 }

--------------------------------------------------------------------------------
--  Ethernet to TDM Port Association Table
--------------------------------------------------------------------------------
    tnEthToTDMPortAssocInfoTable OBJECT-TYPE
        SYNTAX         SEQUENCE OF TnEthToTDMPortAssocInfoEntry
        MAX-ACCESS     not-accessible
        STATUS         current
        DESCRIPTION    "Returns the TDM service type for a given Ethernet port.
                        The TDM service type is dependent on the TDM Module
                        provisioned.  If no module is provisioned or the
                        provisioned module is not a TDM module, no entry is
                        returned."
        ::= { tnOpticalPortInfo 400 }

    tnEthToTDMPortAssocInfoEntry OBJECT-TYPE
        SYNTAX         TnEthToTDMPortAssocInfoEntry
        MAX-ACCESS     not-accessible
        STATUS         current
        DESCRIPTION    "."
        INDEX { ifIndex }
        ::= { tnEthToTDMPortAssocInfoTable 1 }

    TnEthToTDMPortAssocInfoEntry ::=
        SEQUENCE {
            tnTDMModuleType      INTEGER,
            tnTDMModuleRate      INTEGER
        }

    tnTDMModuleType OBJECT-TYPE
        SYNTAX         INTEGER {
                         tpop(1),
                         csop(2),
                         tsop(3)
                       }
        MAX-ACCESS     read-only
        STATUS         current
        DESCRIPTION    "Indicates the type of TDM Module provisioned.  If the
                        moduletype is unprovisioned or not a TDM module, no
                        entry is returned."
        ::= { tnEthToTDMPortAssocInfoEntry 1 }

    tnTDMModuleRate OBJECT-TYPE
        SYNTAX         INTEGER {
                         e1(1),
                         t1(2),
                         stm1-Channelized(3),
                         stm1-OC3(4),
                         stm4-OC12(5)
                       }
        MAX-ACCESS     read-only
        STATUS         current
        DESCRIPTION    "Indicates the speed of TDM Module provisioned.  If
                        the moduletype is unprovisioned or not a TDM module,
                        no entry is returned."
        ::= { tnEthToTDMPortAssocInfoEntry 2 }

--------------------------------------------------------------------------------
-- 20AN80 Optical Port Info Scalar
--------------------------------------------------------------------------------
    tn20an80PortInfoAttributeTotal OBJECT-TYPE
        SYNTAX         Integer32
        MAX-ACCESS     read-only
        STATUS         current
        DESCRIPTION    "."
        ::= { tnOpticalPortInfo 401 }

--------------------------------------------------------------------------------
--  20AN80 Optical Port Info Table
--------------------------------------------------------------------------------
    tn20an80PortInfoTable OBJECT-TYPE
        SYNTAX         SEQUENCE OF Tn20an80PortInfoEntry
        MAX-ACCESS     not-accessible
        STATUS         current
        DESCRIPTION    "The ports on a 20an80 optical card."
        ::= { tnOpticalPortInfo 402 }

    tn20an80PortInfoEntry OBJECT-TYPE
        SYNTAX         Tn20an80PortInfoEntry
        MAX-ACCESS     not-accessible
        STATUS         current
        DESCRIPTION    "."
        INDEX { ifIndex }
        ::= { tn20an80PortInfoTable 1 }

    Tn20an80PortInfoEntry ::= SEQUENCE {
        tn20an80PortInfoFunction INTEGER
    }

    tn20an80PortInfoFunction OBJECT-TYPE
        SYNTAX         INTEGER {
                         port(1)
                       }
        MAX-ACCESS     read-only
        STATUS         current
        DESCRIPTION    "Indicates the functional type of
                        this 20an80 port."
        ::= { tn20an80PortInfoEntry 1 }

--------------------------------------------------------------------------------
-- 10AN400 Optical Port Info Scalar
--------------------------------------------------------------------------------
    tn10an400PortInfoAttributeTotal OBJECT-TYPE
        SYNTAX         Integer32
        MAX-ACCESS     read-only
        STATUS         current
        DESCRIPTION    "."
        ::= { tnOpticalPortInfo 403 }

--------------------------------------------------------------------------------
--  10AN400 Optical Port Info Table
--------------------------------------------------------------------------------
    tn10an400PortInfoTable OBJECT-TYPE
        SYNTAX         SEQUENCE OF Tn10an400PortInfoEntry
        MAX-ACCESS     not-accessible
        STATUS         current
        DESCRIPTION    "The ports on a 10an400 optical card."
        ::= { tnOpticalPortInfo 404 }

    tn10an400PortInfoEntry OBJECT-TYPE
        SYNTAX         Tn10an400PortInfoEntry
        MAX-ACCESS     not-accessible
        STATUS         current
        DESCRIPTION    "."
        INDEX { ifIndex }
        ::= { tn10an400PortInfoTable 1 }

    Tn10an400PortInfoEntry ::= SEQUENCE {
        tn10an400PortInfoFunction INTEGER
    }

    tn10an400PortInfoFunction OBJECT-TYPE
        SYNTAX         INTEGER {
                         port(1)
                       }
        MAX-ACCESS     read-only
        STATUS         current
        DESCRIPTION    "Indicates the functional type of
                        this 10an400 port."
        ::= { tn10an400PortInfoEntry 1 }

--------------------------------------------------------------------------------
-- 8P20 Optical Port Info Scalar
--------------------------------------------------------------------------------
    tn8p20PortInfoAttributeTotal OBJECT-TYPE
        SYNTAX         Integer32
        MAX-ACCESS     read-only
        STATUS         current
        DESCRIPTION    "."
        ::= { tnOpticalPortInfo 405 }

--------------------------------------------------------------------------------
-- 8P20 Optical Port Info Table
--------------------------------------------------------------------------------
    tn8p20PortInfoTable OBJECT-TYPE
        SYNTAX         SEQUENCE OF Tn8p20PortInfoEntry
        MAX-ACCESS     not-accessible
        STATUS         current
        DESCRIPTION    "The ports on a 8P20 optical card."
        ::= { tnOpticalPortInfo 406 }

    tn8p20PortInfoEntry OBJECT-TYPE
        SYNTAX         Tn8p20PortInfoEntry
        MAX-ACCESS     not-accessible
        STATUS         current
        DESCRIPTION    "."
        INDEX { ifIndex }
        ::= { tn8p20PortInfoTable 1 }

    Tn8p20PortInfoEntry ::=
        SEQUENCE {
            tn8p20PortInfoFunction INTEGER
        }

    tn8p20PortInfoFunction OBJECT-TYPE
        SYNTAX         INTEGER {
                         network(1),
                         client(2),
                         evoa(3),
                         backplane(4)
                       }
        MAX-ACCESS     read-only
        STATUS         current
        DESCRIPTION    "Indicates the functional type of this 8P20 port."
        ::= { tn8p20PortInfoEntry 1 }

--------------------------------------------------------------------------------
-- OPSFLEX Optical Port Info Scalar
--------------------------------------------------------------------------------
    tnOpsflexPortInfoAttributeTotal OBJECT-TYPE
        SYNTAX         Integer32
        MAX-ACCESS     read-only
        STATUS         current
        DESCRIPTION    "."
        ::= { tnOpticalPortInfo 407 }

--------------------------------------------------------------------------------
-- OPSFLEX Optical Port Info Table
--------------------------------------------------------------------------------
    tnOpsflexPortInfoTable OBJECT-TYPE
        SYNTAX         SEQUENCE OF TnOpsflexPortInfoEntry
        MAX-ACCESS     not-accessible
        STATUS         current
        DESCRIPTION    "The ports on an OPSFLEX optical card."
        ::= { tnOpticalPortInfo 408 }

    tnOpsflexPortInfoEntry OBJECT-TYPE
        SYNTAX         TnOpsflexPortInfoEntry
        MAX-ACCESS     not-accessible
        STATUS         current
        DESCRIPTION    "."
        INDEX { ifIndex }
        ::= { tnOpsflexPortInfoTable 1 }

    TnOpsflexPortInfoEntry ::=
        SEQUENCE {
            tnOpsflexPortInfoFunction     INTEGER
        }

    tnOpsflexPortInfoFunction OBJECT-TYPE
        SYNTAX         INTEGER {
                         signal(1),
                         workingProtected(2)
                       }
        MAX-ACCESS     read-only
        STATUS         current
        DESCRIPTION    "Indicates the functional type of this Opsflex port."
        ::= { tnOpsflexPortInfoEntry 1 }

--------------------------------------------------------------------------------
-- D5X500Q Optical Port Info Scalar
--------------------------------------------------------------------------------
    tnD5x500qPortInfoAttributeTotal OBJECT-TYPE
        SYNTAX         Integer32
        MAX-ACCESS     read-only
        STATUS         current
        DESCRIPTION    "."
        ::= { tnOpticalPortInfo 409 }

--------------------------------------------------------------------------------
-- D5X500Q Optical Port Info Table
--------------------------------------------------------------------------------
    tnD5x500qPortInfoTable OBJECT-TYPE
        SYNTAX         SEQUENCE OF TnD5x500qPortInfoEntry
        MAX-ACCESS     not-accessible
        STATUS         current
        DESCRIPTION    "The ports on a D5X500Q optical card."
        ::= { tnOpticalPortInfo 410 }

    tnD5x500qPortInfoEntry OBJECT-TYPE
        SYNTAX         TnD5x500qPortInfoEntry
        MAX-ACCESS     not-accessible
        STATUS         current
        DESCRIPTION    "."
        INDEX { ifIndex }
        ::= { tnD5x500qPortInfoTable 1 }

    TnD5x500qPortInfoEntry ::=
        SEQUENCE {
            tnD5x500qPortInfoFunction INTEGER
        }

    tnD5x500qPortInfoFunction OBJECT-TYPE
        SYNTAX         INTEGER {
                         network(1),
                         client(2),
                         backplane(3)
                       }
        MAX-ACCESS     read-only
        STATUS         current
        DESCRIPTION    "Indicates the functional type of this D5x500q port."
        ::= { tnD5x500qPortInfoEntry 1 }

--------------------------------------------------------------------------------
-- 18P40 Optical Port Info Scalar
--------------------------------------------------------------------------------
    tn18p40PortInfoAttributeTotal OBJECT-TYPE
        SYNTAX         Integer32
        MAX-ACCESS     read-only
        STATUS         current
        DESCRIPTION    "."
        ::= { tnOpticalPortInfo 411 }

--------------------------------------------------------------------------------
-- 18P40 Optical Port Info Table
--------------------------------------------------------------------------------
    tn18p40PortInfoTable OBJECT-TYPE
        SYNTAX         SEQUENCE OF Tn18p40PortInfoEntry
        MAX-ACCESS     not-accessible
        STATUS         current
        DESCRIPTION    "The ports on a 18P40 optical card."
        ::= { tnOpticalPortInfo 412 }

    tn18p40PortInfoEntry OBJECT-TYPE
        SYNTAX         Tn18p40PortInfoEntry
        MAX-ACCESS     not-accessible
        STATUS         current
        DESCRIPTION    "."
        INDEX { ifIndex }
        ::= { tn18p40PortInfoTable 1 }

    Tn18p40PortInfoEntry ::=
        SEQUENCE {
            tn18p40PortInfoFunction INTEGER
        }

    tn18p40PortInfoFunction OBJECT-TYPE
        SYNTAX         INTEGER {
                         network(1),
                         client(2),
                         evoa(3),
                         backplane(4)
                       }
        MAX-ACCESS     read-only
        STATUS         current
        DESCRIPTION    "Indicates the functional type of this 18P40 port."
        ::= { tn18p40PortInfoEntry 1 }

--------------------------------------------------------------------------------
-- DA2C4 Optical Port Info Scalar
--------------------------------------------------------------------------------
    tnDa2c4PortInfoAttributeTotal OBJECT-TYPE
        SYNTAX         Integer32
        MAX-ACCESS     read-only
        STATUS         current
        DESCRIPTION    "."
        ::= { tnOpticalPortInfo 413 }

--------------------------------------------------------------------------------
-- DA2C4 Optical Port Info Table
--------------------------------------------------------------------------------
    tnDa2c4PortInfoTable OBJECT-TYPE
        SYNTAX         SEQUENCE OF TnDa2c4PortInfoEntry
        MAX-ACCESS     not-accessible
        STATUS         current
        DESCRIPTION    "The ports on a Da2c4 optical card."
        ::= { tnOpticalPortInfo 414 }

    tnDa2c4PortInfoEntry OBJECT-TYPE
        SYNTAX         TnDa2c4PortInfoEntry
        MAX-ACCESS     not-accessible
        STATUS         current
        DESCRIPTION    "."
        INDEX { ifIndex }
        ::= { tnDa2c4PortInfoTable 1 }

    TnDa2c4PortInfoEntry ::=
        SEQUENCE {
            tnDa2c4PortInfoFunction INTEGER
        }
    tnDa2c4PortInfoFunction OBJECT-TYPE
        SYNTAX         INTEGER {
                         network(1),
                         client(2)
                       }
        MAX-ACCESS     read-only
        STATUS         current
        DESCRIPTION    "Indicates the functional type of this Da2c4 port."
        ::= { tnDa2c4PortInfoEntry 1 }

--------------------------------------------------------------------------------
-- 130SLA1 Optical Port Info Scalar
--------------------------------------------------------------------------------
    tn130sla1PortInfoAttributeTotal OBJECT-TYPE
        SYNTAX         Integer32
        MAX-ACCESS     read-only
        STATUS         current
        DESCRIPTION    "."
        ::= { tnOpticalPortInfo 415 }

--------------------------------------------------------------------------------
-- 130SLA1 Optical Port Info Table
--------------------------------------------------------------------------------
    tn130sla1PortInfoTable OBJECT-TYPE
        SYNTAX         SEQUENCE OF Tn130sla1PortInfoEntry
        MAX-ACCESS     not-accessible
        STATUS         current
        DESCRIPTION    "The ports on a 130SLA1 optical card."
        ::= { tnOpticalPortInfo 416 }

    tn130sla1PortInfoEntry OBJECT-TYPE
        SYNTAX         Tn130sla1PortInfoEntry
        MAX-ACCESS     not-accessible
        STATUS         current
        DESCRIPTION    "."
        INDEX { ifIndex }
        ::= { tn130sla1PortInfoTable 1 }

    Tn130sla1PortInfoEntry ::=
        SEQUENCE {
            tn130sla1PortInfoFunction INTEGER
        }

    tn130sla1PortInfoFunction OBJECT-TYPE
        SYNTAX         INTEGER {
                         network(1),
                         client(2)
                       }
        MAX-ACCESS     read-only
        STATUS         current
        DESCRIPTION    "Indicates the functional type of this 130SLA1 port."
        ::= { tn130sla1PortInfoEntry 1 }

--------------------------------------------------------------------------------
-- 130SLX10 Optical Port Info Scalar
--------------------------------------------------------------------------------
    tn130slx10PortInfoAttributeTotal OBJECT-TYPE
        SYNTAX         Integer32
        MAX-ACCESS     read-only
        STATUS         current
        DESCRIPTION    "."
        ::= { tnOpticalPortInfo 417 }

--------------------------------------------------------------------------------
-- 130SLX10 Optical Port Info Table
--------------------------------------------------------------------------------
    tn130slx10PortInfoTable OBJECT-TYPE
        SYNTAX         SEQUENCE OF Tn130slx10PortInfoEntry
        MAX-ACCESS     not-accessible
        STATUS         current
        DESCRIPTION    "The ports on a 130SLX10 optical card."
        ::= { tnOpticalPortInfo 418 }

    tn130slx10PortInfoEntry OBJECT-TYPE
        SYNTAX         Tn130slx10PortInfoEntry
        MAX-ACCESS     not-accessible
        STATUS         current
        DESCRIPTION    "."
        INDEX { ifIndex }
        ::= { tn130slx10PortInfoTable 1 }

    Tn130slx10PortInfoEntry ::=
        SEQUENCE {
            tn130slx10PortInfoFunction  INTEGER
        }

    tn130slx10PortInfoFunction OBJECT-TYPE
        SYNTAX         INTEGER {
                         network(1),
                         client(2)
                       }
        MAX-ACCESS     read-only
        STATUS         current
        DESCRIPTION    "Indicates the functional type of this 130SLX10 port."
        ::= { tn130slx10PortInfoEntry 1 }

--------------------------------------------------------------------------------
-- PSS12x Power Filter Port Info Scalar
--------------------------------------------------------------------------------
    tnPSS12xPowerFilterPortInfoAttributeTotal OBJECT-TYPE
        SYNTAX         Integer32
        MAX-ACCESS     read-only
        STATUS         current
        DESCRIPTION    "."
        ::= { tnOpticalPortInfo 419 }

--------------------------------------------------------------------------------
-- PSS12xPower Filter Port Info Table
--------------------------------------------------------------------------------
    tnPSS12xPowerFilterPortInfoTable OBJECT-TYPE
        SYNTAX         SEQUENCE OF TnPSS12xPowerFilterPortInfoEntry
        MAX-ACCESS     not-accessible
        STATUS         current
        DESCRIPTION    "The ports on a PSS12xPowerFilter optical card."
        ::= { tnOpticalPortInfo 420 }

    tnPSS12xPowerFilterPortInfoEntry OBJECT-TYPE
        SYNTAX         TnPSS12xPowerFilterPortInfoEntry
        MAX-ACCESS     not-accessible
        STATUS         current
        DESCRIPTION    "."
        INDEX { ifIndex }
        ::= { tnPSS12xPowerFilterPortInfoTable 1 }

    TnPSS12xPowerFilterPortInfoEntry ::=
        SEQUENCE {
            tnPSS12xPowerFilterPortInfoFunction INTEGER
        }

    tnPSS12xPowerFilterPortInfoFunction OBJECT-TYPE
        SYNTAX         INTEGER {
                         powerFilterPort1(1),
                         powerFilterPort2(2),
                         powerFilterPort3(3)
                       }
        MAX-ACCESS     read-only
        STATUS         current
        DESCRIPTION    "Indicates the functional type of this PSS12xPowerFilter port."
        ::= { tnPSS12xPowerFilterPortInfoEntry 1 }

--------------------------------------------------------------------------------
-- IROADM20 Optical Port Info Scalar
--------------------------------------------------------------------------------
    tnIroadm20PortInfoAttributeTotal OBJECT-TYPE
        SYNTAX         Integer32
        MAX-ACCESS     read-only
        STATUS         current
        DESCRIPTION    "."
        ::= { tnOpticalPortInfo 421 }

--------------------------------------------------------------------------------
-- IROADM20 Optical Port Info Table
--------------------------------------------------------------------------------
    tnIroadm20PortInfoTable OBJECT-TYPE
        SYNTAX         SEQUENCE OF TnIroadm20PortInfoEntry
        MAX-ACCESS     not-accessible
        STATUS         current
        DESCRIPTION    "The ports on a IROADM20 optical card."
        ::= { tnOpticalPortInfo 422 }

    tnIroadm20PortInfoEntry OBJECT-TYPE
        SYNTAX         TnIroadm20PortInfoEntry
        MAX-ACCESS     not-accessible
        STATUS         current
        DESCRIPTION    "."
        INDEX { ifIndex }
        ::= { tnIroadm20PortInfoTable 1 }

    TnIroadm20PortInfoEntry ::=
        SEQUENCE {
            tnIroadm20PortInfoFunction INTEGER
        }

    tnIroadm20PortInfoFunction OBJECT-TYPE
        SYNTAX         INTEGER {
                         lineIn(1),
                         inv(2),
                         osc(3),
                         lineOut(4),
                         oscSfp(5),
                         adt(6),
                         otdrRx(7),
                         otdrTx(8),
                         custLan(9),
                         testLaser(10),
                         mpoAddDrop(11)
                       }
        MAX-ACCESS     read-only
        STATUS         current
        DESCRIPTION    "Indicates the functional type of this IROADM20 port."
        ::= { tnIroadm20PortInfoEntry 1 }

--------------------------------------------------------------------------------
-- S2AD200 Optical Port Info Scalar
--------------------------------------------------------------------------------
    tnS2ad200PortInfoAttributeTotal OBJECT-TYPE
        SYNTAX         Integer32
        MAX-ACCESS     read-only
        STATUS         current
        DESCRIPTION    "."
        ::= { tnOpticalPortInfo 423 }

--------------------------------------------------------------------------------
-- S2AD200 Optical Port Info Table
--------------------------------------------------------------------------------
    tnS2ad200PortInfoTable OBJECT-TYPE
        SYNTAX         SEQUENCE OF TnS2ad200PortInfoEntry
        MAX-ACCESS     not-accessible
        STATUS         current
        DESCRIPTION    "The ports on a S2AD200 optical card."
        ::= { tnOpticalPortInfo 424 }

    tnS2ad200PortInfoEntry OBJECT-TYPE
        SYNTAX         TnS2ad200PortInfoEntry
        MAX-ACCESS     not-accessible
        STATUS         current
        DESCRIPTION    "."
        INDEX { ifIndex }
        ::= { tnS2ad200PortInfoTable 1 }

    TnS2ad200PortInfoEntry ::=
        SEQUENCE {
            tnS2ad200PortInfoFunction INTEGER
        }

    tnS2ad200PortInfoFunction OBJECT-TYPE
        SYNTAX         INTEGER {
                         network(1),
                         client(2)
                       }
        MAX-ACCESS     read-only
        STATUS         current
        DESCRIPTION    "Indicates the functional type of this S2AD200 port."
        ::= { tnS2ad200PortInfoEntry 1 }

--------------------------------------------------------------------------------
-- MSH4-FSB Optical Port Info Scalar
--------------------------------------------------------------------------------
    tnMsh4fsbPortInfoAttributeTotal OBJECT-TYPE
        SYNTAX         Integer32
        MAX-ACCESS     read-only
        STATUS         current
        DESCRIPTION    "."
        ::= { tnOpticalPortInfo 425 }

--------------------------------------------------------------------------------
-- MSH4-FSB Optical Port Info Table
--------------------------------------------------------------------------------
    tnMsh4fsbPortInfoTable OBJECT-TYPE
        SYNTAX         SEQUENCE OF TnMsh4fsbPortInfoEntry
        MAX-ACCESS     not-accessible
        STATUS         current
        DESCRIPTION    "The ports on a MSH4-FSB optical card."
        ::= { tnOpticalPortInfo 426 }

    tnMsh4fsbPortInfoEntry OBJECT-TYPE
        SYNTAX         TnMsh4fsbPortInfoEntry
        MAX-ACCESS     not-accessible
        STATUS         current
        DESCRIPTION    "."
        INDEX { ifIndex }
        ::= { tnMsh4fsbPortInfoTable 1 }

    TnMsh4fsbPortInfoEntry ::=
        SEQUENCE {
            tnMsh4fsbPortInfoFunction   INTEGER
        }

    tnMsh4fsbPortInfoFunction OBJECT-TYPE
        SYNTAX         INTEGER {
                         mpoWss(1),
                         mpoAde(2),
                         mpoAdm(3)
                       }
        MAX-ACCESS     read-only
        STATUS         current
        DESCRIPTION    "Indicates the functional type of this MSH4-FSB port."
        ::= { tnMsh4fsbPortInfoEntry 1 }

--------------------------------------------------------------------------------
-- 2UX200 Optical Port Info Scalar
--------------------------------------------------------------------------------
    tn2ux200PortInfoAttributeTotal OBJECT-TYPE
        SYNTAX         Integer32
        MAX-ACCESS     read-only
        STATUS         current
        DESCRIPTION    "."
        ::= { tnOpticalPortInfo 427 }

--------------------------------------------------------------------------------
-- 2UX200 Optical Port Info Table
--------------------------------------------------------------------------------
    tn2ux200PortInfoTable OBJECT-TYPE
        SYNTAX         SEQUENCE OF Tn2ux200PortInfoEntry
        MAX-ACCESS     not-accessible
        STATUS         current
        DESCRIPTION    "The ports on a 2UX200 optical card."
        ::= { tnOpticalPortInfo 428 }

    tn2ux200PortInfoEntry OBJECT-TYPE
        SYNTAX         Tn2ux200PortInfoEntry
        MAX-ACCESS     not-accessible
        STATUS         current
        DESCRIPTION    "."
        INDEX { ifIndex }
        ::= { tn2ux200PortInfoTable 1 }

    Tn2ux200PortInfoEntry ::=
        SEQUENCE {
            tn2ux200PortInfoFunction INTEGER
        }

    tn2ux200PortInfoFunction OBJECT-TYPE
        SYNTAX         INTEGER {
                         network(1)
                       }
        MAX-ACCESS     read-only
        STATUS         current
        DESCRIPTION    "Indicates the functional type of this 2UX200 port."
        ::= { tn2ux200PortInfoEntry 1 }

--------------------------------------------------------------------------------
-- 4MX200 Optical Port Info Scalar
--------------------------------------------------------------------------------
    tn4mx200PortInfoAttributeTotal OBJECT-TYPE
        SYNTAX         Integer32
        MAX-ACCESS     read-only
        STATUS         current
        DESCRIPTION    "."
        ::= { tnOpticalPortInfo 429 }

--------------------------------------------------------------------------------
-- 4MX200 Optical Port Info Table
--------------------------------------------------------------------------------
    tn4mx200PortInfoTable OBJECT-TYPE
        SYNTAX         SEQUENCE OF Tn4mx200PortInfoEntry
        MAX-ACCESS     not-accessible
        STATUS         current
        DESCRIPTION    "The ports on a 4MX200 optical card."
        ::= { tnOpticalPortInfo 430 }

    tn4mx200PortInfoEntry OBJECT-TYPE
        SYNTAX         Tn4mx200PortInfoEntry
        MAX-ACCESS     not-accessible
        STATUS         current
        DESCRIPTION    "."
        INDEX { ifIndex }
        ::= { tn4mx200PortInfoTable 1 }

    Tn4mx200PortInfoEntry ::=
        SEQUENCE {
            tn4mx200PortInfoFunction INTEGER
        }

    tn4mx200PortInfoFunction OBJECT-TYPE
        SYNTAX         INTEGER {
                         client(1)
                       }
        MAX-ACCESS     read-only
        STATUS         current
        DESCRIPTION    "Indicates the functional type of this 4MX200 port."
        ::= { tn4mx200PortInfoEntry 1 }

--------------------------------------------------------------------------------
-- OPSB5 Optical Port Info Scalar
--------------------------------------------------------------------------------
    tnOpsb5PortInfoAttributeTotal OBJECT-TYPE
        SYNTAX         Integer32
        MAX-ACCESS     read-only
        STATUS         current
        DESCRIPTION    "."
        ::= { tnOpticalPortInfo 431 }

--------------------------------------------------------------------------------
-- OPSB5 Optical Port Info Table
--------------------------------------------------------------------------------
    tnOpsb5PortInfoTable OBJECT-TYPE
        SYNTAX         SEQUENCE OF TnOpsb5PortInfoEntry
        MAX-ACCESS     not-accessible
        STATUS         current
        DESCRIPTION    "The ports on an OPSB5 optical card."
        ::= { tnOpticalPortInfo 432 }

    tnOpsb5PortInfoEntry OBJECT-TYPE
        SYNTAX         TnOpsb5PortInfoEntry
        MAX-ACCESS     not-accessible
        STATUS         current
        DESCRIPTION    "."
        INDEX { ifIndex }
        ::= { tnOpsb5PortInfoTable 1 }

    TnOpsb5PortInfoEntry ::=
        SEQUENCE {
            tnOpsb5PortInfoFunction     INTEGER
        }

    tnOpsb5PortInfoFunction OBJECT-TYPE
        SYNTAX         INTEGER {
                         signal(1),
                         workingProtected(2)
                       }
        MAX-ACCESS     read-only
        STATUS         current
        DESCRIPTION    "Indicates the functional type of this OPSB5 port."
        ::= { tnOpsb5PortInfoEntry 1 }

--------------------------------------------------------------------------------
-- ASWG-L Optical Port Info Scalar
--------------------------------------------------------------------------------
    tnAswglPortInfoAttributeTotal OBJECT-TYPE
        SYNTAX         Integer32
        MAX-ACCESS     read-only
        STATUS         current
        DESCRIPTION    "."
        ::= { tnOpticalPortInfo 433 }

--------------------------------------------------------------------------------
-- ASWG-L Optical Port Info Table
--------------------------------------------------------------------------------
    tnAswglPortInfoTable OBJECT-TYPE
        SYNTAX         SEQUENCE OF TnAswglPortInfoEntry
        MAX-ACCESS     not-accessible
        STATUS         current
        DESCRIPTION    "The ports on a ASWG-L optical card."
        ::= { tnOpticalPortInfo 434 }

    tnAswglPortInfoEntry OBJECT-TYPE
        SYNTAX         TnAswglPortInfoEntry
        MAX-ACCESS     not-accessible
        STATUS         current
        DESCRIPTION    "."
        INDEX { ifIndex }
        ::= { tnAswglPortInfoTable 1 }

    TnAswglPortInfoEntry ::=
        SEQUENCE {
            tnAswglPortInfoFunction  INTEGER
        }

    tnAswglPortInfoFunction OBJECT-TYPE
        SYNTAX         INTEGER {
                         lineIn(1),
                         otdrRx(2),
                         otdrTx(3),
                         lineOut(4),
                         oscSfp(5),
                         osc(6),
                         custLan(7)
                       }
        MAX-ACCESS     read-only
        STATUS         current
        DESCRIPTION    "Indicates the functional type of this ASWG-L port."
        ::= { tnAswglPortInfoEntry 1 }

--------------------------------------------------------------------------------
-- IPREAMP Optical Port Info Scalar
--------------------------------------------------------------------------------
    tnIpreampPortInfoAttributeTotal OBJECT-TYPE
        SYNTAX         Integer32
        MAX-ACCESS     read-only
        STATUS         current
        DESCRIPTION    "."
        ::= { tnOpticalPortInfo 435 }

--------------------------------------------------------------------------------
-- IPREAMP Optical Port Info Table
--------------------------------------------------------------------------------
    tnIpreampPortInfoTable OBJECT-TYPE
        SYNTAX         SEQUENCE OF TnIpreampPortInfoEntry
        MAX-ACCESS     not-accessible
        STATUS         current
        DESCRIPTION    "The ports on a IPREAMP optical card."
        ::= { tnOpticalPortInfo 436 }

    tnIpreampPortInfoEntry OBJECT-TYPE
        SYNTAX         TnIpreampPortInfoEntry
        MAX-ACCESS     not-accessible
        STATUS         current
        DESCRIPTION    "."
        INDEX { ifIndex }
        ::= { tnIpreampPortInfoTable 1 }

    TnIpreampPortInfoEntry ::=
        SEQUENCE {
            tnIpreampPortInfoFunction INTEGER
        }
    tnIpreampPortInfoFunction OBJECT-TYPE
        SYNTAX         INTEGER {
                         lineIn(1),
                         sigOut(2),
                         sigIn(3),
                         lineOut(4),
                         oscSfp(5),
                         osc(6),
                         otdrRx(7),
                         otdrTx(8),
                         custLan(9)
                       }
        MAX-ACCESS     read-only
        STATUS         current
        DESCRIPTION    "Indicates the functional type of this IPREAMP port."
        ::= { tnIpreampPortInfoEntry 1 }

--    obsolete
--    tn40cx800PortInfoAttributeTotal OBJECT-TYPE ::= { tnOpticalPortInfo 437 }
--    tn40cx800PortInfoTable          OBJECT-TYPE ::= { tnOpticalPortInfo 438 }

--------------------------------------------------------------------------------
-- IRDM32 Optical Port Info Scalar
--------------------------------------------------------------------------------
    tnIrdm32PortInfoAttributeTotal OBJECT-TYPE
        SYNTAX         Integer32
        MAX-ACCESS     read-only
        STATUS         current
        DESCRIPTION    "."
        ::= { tnOpticalPortInfo 439 }

--------------------------------------------------------------------------------
-- IRDM32 Optical Port Info Table
--------------------------------------------------------------------------------
    tnIrdm32PortInfoTable OBJECT-TYPE
        SYNTAX         SEQUENCE OF TnIrdm32PortInfoEntry
        MAX-ACCESS     not-accessible
        STATUS         current
        DESCRIPTION    "The ports on a IRDM32 optical card."
        ::= { tnOpticalPortInfo 440 }

    tnIrdm32PortInfoEntry OBJECT-TYPE
        SYNTAX         TnIrdm32PortInfoEntry
        MAX-ACCESS     not-accessible
        STATUS         current
        DESCRIPTION    "."
        INDEX { ifIndex }
        ::= { tnIrdm32PortInfoTable 1 }

    TnIrdm32PortInfoEntry ::=
        SEQUENCE {
            tnIrdm32PortInfoFunction INTEGER
        }

    tnIrdm32PortInfoFunction OBJECT-TYPE
        SYNTAX         INTEGER {
                         lineIn(1),
                         inv(2),
                         osc(3),
                         lineOut(4),
                         oscSfp(5),
                         adt(6),
                         lineLoading(7),
                         otdrRx(8),
                         otdrTx(9),
                         custLan(10),
                         testLaser(11),
                         mpoFs(12),
                         oscLan(13)
                       }
        MAX-ACCESS     read-only
        STATUS         current
        DESCRIPTION    "Indicates the functional type of this IRDM32 port."
        ::= { tnIrdm32PortInfoEntry 1 }

--------------------------------------------------------------------------------
-- RA4P Optical Port Info Scalar
--------------------------------------------------------------------------------
    tnRa4pPortInfoAttributeTotal OBJECT-TYPE
        SYNTAX         Integer32
        MAX-ACCESS     read-only
        STATUS         current
        DESCRIPTION    "."
        ::= { tnOpticalPortInfo 441 }

--------------------------------------------------------------------------------
-- RA4P Optical Port Info Table
--------------------------------------------------------------------------------
    tnRa4pPortInfoTable OBJECT-TYPE
        SYNTAX         SEQUENCE OF TnRa4pPortInfoEntry
        MAX-ACCESS     not-accessible
        STATUS         current
        DESCRIPTION    "The ports on a RA4P optical card."
        ::= { tnOpticalPortInfo 442 }

    tnRa4pPortInfoEntry OBJECT-TYPE
        SYNTAX         TnRa4pPortInfoEntry
        MAX-ACCESS     not-accessible
        STATUS         current
        DESCRIPTION    "."
        INDEX { ifIndex }
        ::= { tnRa4pPortInfoTable 1 }

    TnRa4pPortInfoEntry ::=
        SEQUENCE {
            tnRa4pPortInfoFunction INTEGER
        }

    tnRa4pPortInfoFunction OBJECT-TYPE
        SYNTAX         INTEGER {
                         lineIn(1),
                         lineOut(2),
                         oscOut(3)
                       }
        MAX-ACCESS     read-only
        STATUS         current
        DESCRIPTION    "Indicates the functional type of this RA4P port."
        ::= { tnRa4pPortInfoEntry 1 }

-------------------------------------------------------------------------------
-- EILA Optical Port Info Scalar
-------------------------------------------------------------------------------
    tnEilaPortInfoAttributeTotal OBJECT-TYPE
        SYNTAX         Integer32
        MAX-ACCESS     read-only
        STATUS         current
        DESCRIPTION    "."
        ::= { tnOpticalPortInfo 443 }

-------------------------------------------------------------------------------
-- EILA Optical Port Info Table
-------------------------------------------------------------------------------
    tnEilaPortInfoTable OBJECT-TYPE
        SYNTAX         SEQUENCE OF TnEilaPortInfoEntry
        MAX-ACCESS     not-accessible
        STATUS         current
        DESCRIPTION    "The ports on a EILA optical card."
        ::= { tnOpticalPortInfo 444 }

    tnEilaPortInfoEntry OBJECT-TYPE
        SYNTAX         TnEilaPortInfoEntry
        MAX-ACCESS     not-accessible
        STATUS         current
        DESCRIPTION    "."
        INDEX { ifIndex }
        ::= { tnEilaPortInfoTable 1 }

    TnEilaPortInfoEntry ::=
        SEQUENCE {
            tnEilaPortInfoFunction INTEGER
        }


    tnEilaPortInfoFunction OBJECT-TYPE
        SYNTAX         INTEGER {
                         lineIn(1),
                         otdrRx(2),
                         otdrTx(3),
                         lineOut(4),
                         oscSfp(5),
                         osc(6),
                         custLan(7),
                         inv(8),
                         oscLan(9)
                       }
        MAX-ACCESS     read-only
        STATUS         current
        DESCRIPTION    "Indicates the functional type of this EILA port."
        ::= { tnEilaPortInfoEntry 1 }

--    obsolete
--    tn8cx800PortInfoAttributeTotal OBJECT-TYPE ::= { tnOpticalPortInfo 445 }
--    tn8cx800PortInfoTable          OBJECT-TYPE ::= { tnOpticalPortInfo 446 }
--    tn6px800PortInfoAttributeTotal OBJECT-TYPE ::= { tnOpticalPortInfo 447 }
--    tn6px800PortInfoTable          OBJECT-TYPE ::= { tnOpticalPortInfo 448 }

--------------------------------------------------------------------------------
-- MCS16x15 Optical Port Info Scalar
--------------------------------------------------------------------------------
    tnMcs16x15PortInfoAttributeTotal OBJECT-TYPE
        SYNTAX         Integer32
        MAX-ACCESS     read-only
        STATUS         current
        DESCRIPTION    "."
        ::= { tnOpticalPortInfo 449 }

--------------------------------------------------------------------------------
-- MCS16x15 Optical Port Info Table
--------------------------------------------------------------------------------
    tnMcs16x15PortInfoTable OBJECT-TYPE
        SYNTAX         SEQUENCE OF TnMcs16x15PortInfoEntry
        MAX-ACCESS     not-accessible
        STATUS         current
        DESCRIPTION    "The ports on a MCS16x15 optical card."
        ::= { tnOpticalPortInfo 450 }

    tnMcs16x15PortInfoEntry OBJECT-TYPE
        SYNTAX         TnMcs16x15PortInfoEntry
        MAX-ACCESS     not-accessible
        STATUS         current
        DESCRIPTION    "."
        INDEX { ifIndex }
        ::= { tnMcs16x15PortInfoTable 1 }

    TnMcs16x15PortInfoEntry ::=
        SEQUENCE {
            tnMcs16x15PortInfoFunction                       INTEGER,
            tnMcs16x15PortInfoAddInsertionLossToSig1         Unsigned32,
            tnMcs16x15PortInfoAddInsertionLossToSig2         Unsigned32,
            tnMcs16x15PortInfoAddInsertionLossToSig3         Unsigned32,
            tnMcs16x15PortInfoAddInsertionLossToSig4         Unsigned32,
            tnMcs16x15PortInfoAddInsertionLossToSig5         Unsigned32,
            tnMcs16x15PortInfoAddInsertionLossToSig6         Unsigned32,
            tnMcs16x15PortInfoAddInsertionLossToSig7         Unsigned32,
            tnMcs16x15PortInfoAddInsertionLossToSig8         Unsigned32,
            tnMcs16x15PortInfoAddInsertionLossToSig9         Unsigned32,
            tnMcs16x15PortInfoAddInsertionLossToSig10        Unsigned32,
            tnMcs16x15PortInfoAddInsertionLossToSig11        Unsigned32,
            tnMcs16x15PortInfoAddInsertionLossToSig12        Unsigned32,
            tnMcs16x15PortInfoAddInsertionLossToSig13        Unsigned32,
            tnMcs16x15PortInfoAddInsertionLossToSig14        Unsigned32,
            tnMcs16x15PortInfoAddInsertionLossToSig15        Unsigned32,
            tnMcs16x15PortInfoAddInsertionLossToSig16        Unsigned32,
            tnMcs16x15PortInfoDropInsertionLossFromSig1      Unsigned32,
            tnMcs16x15PortInfoDropInsertionLossFromSig2      Unsigned32,
            tnMcs16x15PortInfoDropInsertionLossFromSig3      Unsigned32,
            tnMcs16x15PortInfoDropInsertionLossFromSig4      Unsigned32,
            tnMcs16x15PortInfoDropInsertionLossFromSig5      Unsigned32,
            tnMcs16x15PortInfoDropInsertionLossFromSig6      Unsigned32,
            tnMcs16x15PortInfoDropInsertionLossFromSig7      Unsigned32,
            tnMcs16x15PortInfoDropInsertionLossFromSig8      Unsigned32,
            tnMcs16x15PortInfoDropInsertionLossFromSig9      Unsigned32,
            tnMcs16x15PortInfoDropInsertionLossFromSig10     Unsigned32,
            tnMcs16x15PortInfoDropInsertionLossFromSig11     Unsigned32,
            tnMcs16x15PortInfoDropInsertionLossFromSig12     Unsigned32,
            tnMcs16x15PortInfoDropInsertionLossFromSig13     Unsigned32,
            tnMcs16x15PortInfoDropInsertionLossFromSig14     Unsigned32,
            tnMcs16x15PortInfoDropInsertionLossFromSig15     Unsigned32,
            tnMcs16x15PortInfoDropInsertionLossFromSig16     Unsigned32
        }

    tnMcs16x15PortInfoFunction OBJECT-TYPE
        SYNTAX         INTEGER {
                         signal(1),
                         ad(2),
                         mpoAar(3)
                       }
        MAX-ACCESS     read-only
        STATUS         current
        DESCRIPTION    "Indicates the functional type of this MCS16x15 port."
        ::= { tnMcs16x15PortInfoEntry 1 }

    tnMcs16x15PortInfoAddInsertionLossToSig1 OBJECT-TYPE
        SYNTAX         Unsigned32
        UNITS          "mB"
        MAX-ACCESS     read-only
        STATUS         current
        DESCRIPTION    "Insertion loss to port SIG1 when disposed to this path.
                        Add direction.

                        Current range: 0 to 2000."
        DEFVAL         { 1700 }
        ::= { tnMcs16x15PortInfoEntry 2 }

    tnMcs16x15PortInfoAddInsertionLossToSig2 OBJECT-TYPE
        SYNTAX         Unsigned32
        UNITS          "mB"
        MAX-ACCESS     read-only
        STATUS         current
        DESCRIPTION    "Insertion loss to port SIG2 when disposed to this path.
                        Add direction.

                        Current range: 0 to 2000."
        DEFVAL         { 1700 }
        ::= { tnMcs16x15PortInfoEntry 3 }

    tnMcs16x15PortInfoAddInsertionLossToSig3 OBJECT-TYPE
        SYNTAX         Unsigned32
        UNITS          "mB"
        MAX-ACCESS     read-only
        STATUS         current
        DESCRIPTION    "Insertion loss to port SIG3 when disposed to this path.
                        Add direction.  Applies to NxM MCS where N >= 3.

                        Current range: 0 to 2000."
        DEFVAL         { 1700 }
        ::= { tnMcs16x15PortInfoEntry 4 }

    tnMcs16x15PortInfoAddInsertionLossToSig4 OBJECT-TYPE
        SYNTAX         Unsigned32
        UNITS          "mB"
        MAX-ACCESS     read-only
        STATUS         current
        DESCRIPTION    "Insertion loss to port SIG4 when disposed to this path.
                        Add direction.  Applies to NxM MCS where N >= 4.

                        Current range: 0 to 2000."
        DEFVAL         { 1700 }
        ::= { tnMcs16x15PortInfoEntry 5 }

    tnMcs16x15PortInfoAddInsertionLossToSig5 OBJECT-TYPE
        SYNTAX         Unsigned32
        UNITS          "mB"
        MAX-ACCESS     read-only
        STATUS         current
        DESCRIPTION    "Insertion loss to port SIG5 when disposed to this path.
                        Add direction.  Applies to NxM MCS where N >= 5.

                        Current range: 0 to 2000."
        DEFVAL         { 1700 }
        ::= { tnMcs16x15PortInfoEntry 6 }

    tnMcs16x15PortInfoAddInsertionLossToSig6 OBJECT-TYPE
        SYNTAX         Unsigned32
        UNITS          "mB"
        MAX-ACCESS     read-only
        STATUS         current
        DESCRIPTION    "Insertion loss to port SIG6 when disposed to this path.
                        Add direction.  Applies to NxM MCS where N >= 6.

                        Current range: 0 to 2000."
        DEFVAL         { 1700 }
        ::= { tnMcs16x15PortInfoEntry 7 }

    tnMcs16x15PortInfoAddInsertionLossToSig7 OBJECT-TYPE
        SYNTAX         Unsigned32
        UNITS          "mB"
        MAX-ACCESS     read-only
        STATUS         current
        DESCRIPTION    "Insertion loss to port SIG7 when disposed to this path.
                        Add direction.  Applies to NxM MCS where N >= 7.

                        Current range: 0 to 2000."
        DEFVAL         { 1700 }
        ::= { tnMcs16x15PortInfoEntry 8 }

    tnMcs16x15PortInfoAddInsertionLossToSig8 OBJECT-TYPE
        SYNTAX         Unsigned32
        UNITS          "mB"
        MAX-ACCESS     read-only
        STATUS         current
        DESCRIPTION    "Insertion loss to port SIG8 when disposed to this path.
                        Add direction.  Applies to NxM MCS where N >= 8.

                        Current range: 0 to 2000."
        DEFVAL         { 1700 }
        ::= { tnMcs16x15PortInfoEntry 9 }

    tnMcs16x15PortInfoAddInsertionLossToSig9 OBJECT-TYPE
        SYNTAX         Unsigned32
        UNITS          "mB"
        MAX-ACCESS     read-only
        STATUS         current
        DESCRIPTION    "Insertion loss to port SIG8 when disposed to this path.
                        Add direction.  Applies to NxM MCS where N >= 8.

                        Current range: 0 to 2000."
        DEFVAL         { 1700 }
        ::= { tnMcs16x15PortInfoEntry 10 }

    tnMcs16x15PortInfoAddInsertionLossToSig10 OBJECT-TYPE
        SYNTAX         Unsigned32
        UNITS          "mB"
        MAX-ACCESS     read-only
        STATUS         current
        DESCRIPTION    "Insertion loss to port SIG8 when disposed to this path.
                        Add direction.  Applies to NxM MCS where N >= 8.

                        Current range: 0 to 2000."
        DEFVAL         { 1700 }
        ::= { tnMcs16x15PortInfoEntry 11 }

    tnMcs16x15PortInfoAddInsertionLossToSig11 OBJECT-TYPE
        SYNTAX         Unsigned32
        UNITS          "mB"
        MAX-ACCESS     read-only
        STATUS         current
        DESCRIPTION    "Insertion loss to port SIG8 when disposed to this path.
                        Add direction.  Applies to NxM MCS where N >= 8.

                        Current range: 0 to 2000."
        DEFVAL         { 1700 }
        ::= { tnMcs16x15PortInfoEntry 12 }

    tnMcs16x15PortInfoAddInsertionLossToSig12 OBJECT-TYPE
        SYNTAX         Unsigned32
        UNITS          "mB"
        MAX-ACCESS     read-only
        STATUS         current
        DESCRIPTION    "Insertion loss to port SIG8 when disposed to this path.
                        Add direction.  Applies to NxM MCS where N >= 8.

                        Current range: 0 to 2000."
        DEFVAL         { 1700 }
        ::= { tnMcs16x15PortInfoEntry 13 }

    tnMcs16x15PortInfoAddInsertionLossToSig13 OBJECT-TYPE
        SYNTAX         Unsigned32
        UNITS          "mB"
        MAX-ACCESS     read-only
        STATUS         current
        DESCRIPTION    "Insertion loss to port SIG8 when disposed to this path.
                        Add direction.  Applies to NxM MCS where N >= 8.

                        Current range: 0 to 2000."
        DEFVAL         { 1700 }
        ::= { tnMcs16x15PortInfoEntry 14 }

    tnMcs16x15PortInfoAddInsertionLossToSig14 OBJECT-TYPE
        SYNTAX         Unsigned32
        UNITS          "mB"
        MAX-ACCESS     read-only
        STATUS         current
        DESCRIPTION    "Insertion loss to port SIG8 when disposed to this path.
                        Add direction.  Applies to NxM MCS where N >= 8.

                        Current range: 0 to 2000."
        DEFVAL         { 1700 }
        ::= { tnMcs16x15PortInfoEntry 15 }

    tnMcs16x15PortInfoAddInsertionLossToSig15 OBJECT-TYPE
        SYNTAX         Unsigned32
        UNITS          "mB"
        MAX-ACCESS     read-only
        STATUS         current
        DESCRIPTION    "Insertion loss to port SIG8 when disposed to this path.
                        Add direction.  Applies to NxM MCS where N >= 8.

                        Current range: 0 to 2000."
        DEFVAL         { 1700 }
        ::= { tnMcs16x15PortInfoEntry 16 }

    tnMcs16x15PortInfoAddInsertionLossToSig16 OBJECT-TYPE
        SYNTAX         Unsigned32
        UNITS          "mB"
        MAX-ACCESS     read-only
        STATUS         current
        DESCRIPTION    "Insertion loss to port SIG8 when disposed to this path.
                        Add direction.  Applies to NxM MCS where N >= 8.

                        Current range: 0 to 2000."
        DEFVAL         { 1700 }
        ::= { tnMcs16x15PortInfoEntry 17 }

    tnMcs16x15PortInfoDropInsertionLossFromSig1 OBJECT-TYPE
        SYNTAX         Unsigned32
        UNITS          "mB"
        MAX-ACCESS     read-only
        STATUS         current
        DESCRIPTION    "Insertion loss from port SIG1 when disposed to this path.
                        Drop direction.

                        Current range: 0 to 2000."
        DEFVAL         { 1700 }
        ::= { tnMcs16x15PortInfoEntry 18 }

    tnMcs16x15PortInfoDropInsertionLossFromSig2 OBJECT-TYPE
        SYNTAX         Unsigned32
        UNITS          "mB"
        MAX-ACCESS     read-only
        STATUS         current
        DESCRIPTION    "Insertion loss from port SIG2 when disposed to this path.
                        Drop direction.

                        Current range: 0 to 2000."
        DEFVAL         { 1700 }
        ::= { tnMcs16x15PortInfoEntry 19 }

    tnMcs16x15PortInfoDropInsertionLossFromSig3 OBJECT-TYPE
        SYNTAX         Unsigned32
        UNITS          "mB"
        MAX-ACCESS     read-only
        STATUS         current
        DESCRIPTION    "Insertion loss from port SIG3 when disposed to this path.
                        Drop direction.

                        Current range: 0 to 2000."
        DEFVAL         { 1700 }
        ::= { tnMcs16x15PortInfoEntry 20 }

    tnMcs16x15PortInfoDropInsertionLossFromSig4 OBJECT-TYPE
        SYNTAX         Unsigned32
        UNITS          "mB"
        MAX-ACCESS     read-only
        STATUS         current
        DESCRIPTION    "Insertion loss from port SIG4 when disposed to this path.
                        Drop direction.

                        Current range: 0 to 2000."
        DEFVAL         { 1700 }
        ::= { tnMcs16x15PortInfoEntry 21 }

    tnMcs16x15PortInfoDropInsertionLossFromSig5 OBJECT-TYPE
        SYNTAX         Unsigned32
        UNITS          "mB"
        MAX-ACCESS     read-only
        STATUS         current
        DESCRIPTION    "Insertion loss from port SIG5 when disposed to this path.
                        Drop direction.

                        Current range: 0 to 2000."
        DEFVAL         { 1700 }
        ::= { tnMcs16x15PortInfoEntry 22 }

    tnMcs16x15PortInfoDropInsertionLossFromSig6 OBJECT-TYPE
        SYNTAX         Unsigned32
        UNITS          "mB"
        MAX-ACCESS     read-only
        STATUS         current
        DESCRIPTION    "Insertion loss from port SIG6 when disposed to this path.
                        Drop direction.

                        Current range: 0 to 2000."
        DEFVAL         { 1700 }
        ::= { tnMcs16x15PortInfoEntry 23 }

    tnMcs16x15PortInfoDropInsertionLossFromSig7 OBJECT-TYPE
        SYNTAX         Unsigned32
        UNITS          "mB"
        MAX-ACCESS     read-only
        STATUS         current
        DESCRIPTION    "Insertion loss from port SIG7 when disposed to this path.
                        Drop direction.

                        Current range: 0 to 2000."
        DEFVAL         { 1700 }
        ::= { tnMcs16x15PortInfoEntry 24 }

    tnMcs16x15PortInfoDropInsertionLossFromSig8 OBJECT-TYPE
        SYNTAX         Unsigned32
        UNITS          "mB"
        MAX-ACCESS     read-only
        STATUS         current
        DESCRIPTION    "Insertion loss from port SIG8 when disposed to this path.
                        Drop direction.

                        Current range: 0 to 2000."
        DEFVAL         { 1700 }
        ::= { tnMcs16x15PortInfoEntry 25 }

    tnMcs16x15PortInfoDropInsertionLossFromSig9 OBJECT-TYPE
        SYNTAX         Unsigned32
        UNITS          "mB"
        MAX-ACCESS     read-only
        STATUS         current
        DESCRIPTION    "Insertion loss from port SIG8 when disposed to this path.
                        Drop direction.

                        Current range: 0 to 2000."
        DEFVAL         { 1700 }
        ::= { tnMcs16x15PortInfoEntry 26 }

    tnMcs16x15PortInfoDropInsertionLossFromSig10 OBJECT-TYPE
        SYNTAX         Unsigned32
        UNITS          "mB"
        MAX-ACCESS     read-only
        STATUS         current
        DESCRIPTION    "Insertion loss from port SIG8 when disposed to this path.
                        Drop direction.

                        Current range: 0 to 2000."
        DEFVAL         { 1700 }
        ::= { tnMcs16x15PortInfoEntry 27 }

    tnMcs16x15PortInfoDropInsertionLossFromSig11 OBJECT-TYPE
        SYNTAX         Unsigned32
        UNITS          "mB"
        MAX-ACCESS     read-only
        STATUS         current
        DESCRIPTION    "Insertion loss from port SIG8 when disposed to this path.
                        Drop direction.

                        Current range: 0 to 2000."
        DEFVAL         { 1700 }
        ::= { tnMcs16x15PortInfoEntry 28 }

    tnMcs16x15PortInfoDropInsertionLossFromSig12 OBJECT-TYPE
        SYNTAX         Unsigned32
        UNITS          "mB"
        MAX-ACCESS     read-only
        STATUS         current
        DESCRIPTION    "Insertion loss from port SIG8 when disposed to this path.
                        Drop direction.

                        Current range: 0 to 2000."
        DEFVAL         { 1700 }
        ::= { tnMcs16x15PortInfoEntry 29 }

    tnMcs16x15PortInfoDropInsertionLossFromSig13 OBJECT-TYPE
        SYNTAX         Unsigned32
        UNITS          "mB"
        MAX-ACCESS     read-only
        STATUS         current
        DESCRIPTION    "Insertion loss from port SIG8 when disposed to this path.
                        Drop direction.

                        Current range: 0 to 2000."
        DEFVAL         { 1700 }
        ::= { tnMcs16x15PortInfoEntry 30 }

    tnMcs16x15PortInfoDropInsertionLossFromSig14 OBJECT-TYPE
        SYNTAX         Unsigned32
        UNITS          "mB"
        MAX-ACCESS     read-only
        STATUS         current
        DESCRIPTION    "Insertion loss from port SIG8 when disposed to this path.
                        Drop direction.

                        Current range: 0 to 2000."
        DEFVAL         { 1700 }
        ::= { tnMcs16x15PortInfoEntry 31 }

    tnMcs16x15PortInfoDropInsertionLossFromSig15 OBJECT-TYPE
        SYNTAX         Unsigned32
        UNITS          "mB"
        MAX-ACCESS     read-only
        STATUS         current
        DESCRIPTION    "Insertion loss from port SIG8 when disposed to this path.
                        Drop direction.

                        Current range: 0 to 2000."
        DEFVAL         { 1700 }
        ::= { tnMcs16x15PortInfoEntry 32 }

    tnMcs16x15PortInfoDropInsertionLossFromSig16 OBJECT-TYPE
        SYNTAX         Unsigned32
        UNITS          "mB"
        MAX-ACCESS     read-only
        STATUS         current
        DESCRIPTION    "Insertion loss from port SIG8 when disposed to this path.
                        Drop direction.

                        Current range: 0 to 2000."
        DEFVAL         { 1700 }
        ::= { tnMcs16x15PortInfoEntry 33 }

--------------------------------------------------------------------------------
-- 10AN1T Optical Port Info Scalar
--------------------------------------------------------------------------------
    tn10an1tPortInfoAttributeTotal OBJECT-TYPE
        SYNTAX         Integer32
        MAX-ACCESS     read-only
        STATUS         current
        DESCRIPTION    "."
        ::= { tnOpticalPortInfo 451 }

--------------------------------------------------------------------------------
-- 10AN1T Optical Port Info Table
--------------------------------------------------------------------------------
    tn10an1tPortInfoTable OBJECT-TYPE
        SYNTAX         SEQUENCE OF Tn10an1tPortInfoEntry
        MAX-ACCESS     not-accessible
        STATUS         current
        DESCRIPTION    "The ports on a 10AN1T optical card."
        ::= { tnOpticalPortInfo 452 }

    tn10an1tPortInfoEntry OBJECT-TYPE
        SYNTAX         Tn10an1tPortInfoEntry
        MAX-ACCESS     not-accessible
        STATUS         current
        DESCRIPTION    "."
        INDEX { ifIndex }
        ::= { tn10an1tPortInfoTable 1 }

    Tn10an1tPortInfoEntry ::=
        SEQUENCE {
            tn10an1tPortInfoFunction INTEGER
        }

    tn10an1tPortInfoFunction OBJECT-TYPE
        SYNTAX         INTEGER {
                         client(1)
                       }
        MAX-ACCESS     read-only
        STATUS         current
        DESCRIPTION    "Indicates the functional type of this 10AN1T port."
        ::= { tn10an1tPortInfoEntry 1 }

--------------------------------------------------------------------------------
-- 8UC1T Optical Port Info Scalar
--------------------------------------------------------------------------------
    tn8uc1tPortInfoAttributeTotal OBJECT-TYPE
        SYNTAX         Integer32
        MAX-ACCESS     read-only
        STATUS         current
        DESCRIPTION    "."
        ::= { tnOpticalPortInfo 453 }

--------------------------------------------------------------------------------
-- 8UC1T Optical Port Info Table
--------------------------------------------------------------------------------
    tn8uc1tPortInfoTable OBJECT-TYPE
        SYNTAX         SEQUENCE OF Tn8uc1tPortInfoEntry
        MAX-ACCESS     not-accessible
        STATUS         current
        DESCRIPTION    "The ports on a 8UC1T optical card."
        ::= { tnOpticalPortInfo 454 }

    tn8uc1tPortInfoEntry OBJECT-TYPE
        SYNTAX         Tn8uc1tPortInfoEntry
        MAX-ACCESS     not-accessible
        STATUS         current
        DESCRIPTION    "."
        INDEX { ifIndex }
        ::= { tn8uc1tPortInfoTable 1 }

    Tn8uc1tPortInfoEntry ::=
        SEQUENCE {
            tn8uc1tPortInfoFunction INTEGER
        }

    tn8uc1tPortInfoFunction OBJECT-TYPE
        SYNTAX         INTEGER {
                         network(1)
                       }
        MAX-ACCESS     read-only
        STATUS         current
        DESCRIPTION    "Indicates the functional type of this 8UC1T port."
        ::= { tn8uc1tPortInfoEntry 1 }

--------------------------------------------------------------------------------
-- DFC12 Optical Port Info Scalar
--------------------------------------------------------------------------------
    tnDfc12PortInfoAttributeTotal OBJECT-TYPE
        SYNTAX         Integer32
        MAX-ACCESS     read-only
        STATUS         current
        DESCRIPTION    "."
        ::= { tnOpticalPortInfo 455 }

--------------------------------------------------------------------------------
-- DFC12 Optical Port Info Table
--------------------------------------------------------------------------------
    tnDfc12PortInfoTable OBJECT-TYPE
        SYNTAX         SEQUENCE OF TnDfc12PortInfoEntry
        MAX-ACCESS     not-accessible
        STATUS         current
        DESCRIPTION    "The ports on a Dfc12 optical card."
        ::= { tnOpticalPortInfo 456 }

    tnDfc12PortInfoEntry OBJECT-TYPE
        SYNTAX         TnDfc12PortInfoEntry
        MAX-ACCESS     not-accessible
        STATUS         current
        DESCRIPTION    "."
        INDEX { ifIndex }
        ::= { tnDfc12PortInfoTable 1 }

    TnDfc12PortInfoEntry ::=
        SEQUENCE {
            tnDfc12PortInfoFunction INTEGER
        }
    tnDfc12PortInfoFunction OBJECT-TYPE
        SYNTAX         INTEGER {
                         network(1),
                         client(2)
                       }
        MAX-ACCESS     read-only
        STATUS         current
        DESCRIPTION    "Indicates the functional type of this Dfc12 port."
        ::= { tnDfc12PortInfoEntry 1 }

--------------------------------------------------------------------------------
-- IRDM32L Optical Port Info Scalar
--------------------------------------------------------------------------------
    tnIrdm32lPortInfoAttributeTotal OBJECT-TYPE
        SYNTAX         Integer32
        MAX-ACCESS     read-only
        STATUS         current
        DESCRIPTION    "."
        ::= { tnOpticalPortInfo 457 }

--------------------------------------------------------------------------------
-- IRDM32L Optical Port Info Table
--------------------------------------------------------------------------------
    tnIrdm32lPortInfoTable OBJECT-TYPE
        SYNTAX         SEQUENCE OF TnIrdm32lPortInfoEntry
        MAX-ACCESS     not-accessible
        STATUS         current
        DESCRIPTION    "The ports on a IRDM32L optical card."
        ::= { tnOpticalPortInfo 458 }

    tnIrdm32lPortInfoEntry OBJECT-TYPE
        SYNTAX         TnIrdm32lPortInfoEntry
        MAX-ACCESS     not-accessible
        STATUS         current
        DESCRIPTION    "."
        INDEX { ifIndex }
        ::= { tnIrdm32lPortInfoTable 1 }

    TnIrdm32lPortInfoEntry ::=
        SEQUENCE {
            tnIrdm32lPortInfoFunction     INTEGER
        }

    tnIrdm32lPortInfoFunction OBJECT-TYPE
        SYNTAX         INTEGER {
                         lineIn(1),
                         inv(2),
                         osc(3),
                         lineOut(4),
                         oscSfp(5),
                         adt(6),
                         lineLoading(7),
                         otdrRx(8),
                         otdrTx(9),
                         custLan(10),
                         testLaser(11),
                         mpoFs(12),
                         oscLan(13)
                       }
        MAX-ACCESS     read-only
        STATUS         current
        DESCRIPTION    "Indicates the functional type of this IRDM32L port."
        ::= { tnIrdm32lPortInfoEntry 1 }

--------------------------------------------------------------------------------
-- S4X400 Optical Port Info Scalar
--------------------------------------------------------------------------------
    tnS4x400PortInfoAttributeTotal OBJECT-TYPE
        SYNTAX         Integer32
        MAX-ACCESS     read-only
        STATUS         current
        DESCRIPTION    "."
        ::= { tnOpticalPortInfo 459 }

--------------------------------------------------------------------------------
-- S4X400 Optical Port Info Table
--------------------------------------------------------------------------------
    tnS4x400PortInfoTable OBJECT-TYPE
        SYNTAX         SEQUENCE OF TnS4x400PortInfoEntry
        MAX-ACCESS     not-accessible
        STATUS         current
        DESCRIPTION    "The ports on a S4x400 optical card."
        ::= { tnOpticalPortInfo 460 }

    tnS4x400PortInfoEntry OBJECT-TYPE
        SYNTAX         TnS4x400PortInfoEntry
        MAX-ACCESS     not-accessible
        STATUS         current
        DESCRIPTION    "."
        INDEX { ifIndex }
        ::= { tnS4x400PortInfoTable 1 }

    TnS4x400PortInfoEntry ::=
        SEQUENCE {
            tnS4x400PortInfoFunction     INTEGER
        }

    tnS4x400PortInfoFunction OBJECT-TYPE
        SYNTAX         INTEGER {
                         network(1),
                         client(2),
                         backplane(3)
                       }
        MAX-ACCESS     read-only
        STATUS         current
        DESCRIPTION    "Indicates the functional type of this S4X400 port."
        ::= { tnS4x400PortInfoEntry 1 }

--------------------------------------------------------------------------------
-- 1830 TPS-24 PS1 Optical Port Info Scalar
--------------------------------------------------------------------------------
    tnTPS24PS1PortInfoAttributeTotal OBJECT-TYPE
        SYNTAX         Integer32
        MAX-ACCESS     read-only
        STATUS         current
        DESCRIPTION    "."
        ::= { tnOpticalPortInfo 461 }

--------------------------------------------------------------------------------
-- 1830 TPS-24 PS1 Optical Port Info Table
--------------------------------------------------------------------------------
    tnTPS24PS1PortInfoTable OBJECT-TYPE
        SYNTAX         SEQUENCE OF TnTPS24PS1PortInfoEntry
        MAX-ACCESS     not-accessible
        STATUS         current
        DESCRIPTION    "The ports on a 1830 TPS-24 PS1 optical card."
        ::= { tnOpticalPortInfo 462 }

    tnTPS24PS1PortInfoEntry OBJECT-TYPE
        SYNTAX         TnTPS24PS1PortInfoEntry
        MAX-ACCESS     not-accessible
        STATUS         current
        DESCRIPTION    "."
        INDEX { ifIndex }
        ::= { tnTPS24PS1PortInfoTable 1 }

    TnTPS24PS1PortInfoEntry ::=
        SEQUENCE {
            tnTPS24PS1PortInfoFunction     INTEGER
        }

    tnTPS24PS1PortInfoFunction OBJECT-TYPE
        SYNTAX         INTEGER {
                         network(1),
                         client(2),
                         tod(3),
                         bits(4),
                         otc(5),
                         ethman(6)
                       }
        MAX-ACCESS     read-only
        STATUS         current
        DESCRIPTION    "Indicates the functional type of this 1830 TPS-24 PS1 port."
        ::= { tnTPS24PS1PortInfoEntry 1 }

--------------------------------------------------------------------------------
-- 1830 TPS-24 PS2 Optical Port Info Scalar
--------------------------------------------------------------------------------
    tnTPS24PS2PortInfoAttributeTotal OBJECT-TYPE
        SYNTAX         Integer32
        MAX-ACCESS     read-only
        STATUS         current
        DESCRIPTION    "."
        ::= { tnOpticalPortInfo 463 }

--------------------------------------------------------------------------------
-- 1830 TPS-24 PS2 Optical Port Info Table
--------------------------------------------------------------------------------
    tnTPS24PS2PortInfoTable OBJECT-TYPE
        SYNTAX         SEQUENCE OF TnTPS24PS2PortInfoEntry
        MAX-ACCESS     not-accessible
        STATUS         current
        DESCRIPTION    "The ports on a 1830 TPS-24 PS2 optical card."
        ::= { tnOpticalPortInfo 464 }

    tnTPS24PS2PortInfoEntry OBJECT-TYPE
        SYNTAX         TnTPS24PS2PortInfoEntry
        MAX-ACCESS     not-accessible
        STATUS         current
        DESCRIPTION    "."
        INDEX { ifIndex }
        ::= { tnTPS24PS2PortInfoTable 1 }

    TnTPS24PS2PortInfoEntry ::=
        SEQUENCE {
            tnTPS24PS2PortInfoFunction     INTEGER
        }

    tnTPS24PS2PortInfoFunction OBJECT-TYPE
        SYNTAX         INTEGER {
                         network(1),
                         client(2),
                         tod(3),
                         bits(4),
                         otc(5),
                         ethman(6)
                       }
        MAX-ACCESS     read-only
        STATUS         current
        DESCRIPTION    "Indicates the functional type of this 1830 TPS-24 PS2 port."
        ::= { tnTPS24PS2PortInfoEntry 1 }

--------------------------------------------------------------------------------
-- 1830 TPS-12 PS Optical Port Info Scalar
--------------------------------------------------------------------------------
    tnTPS12PSPortInfoAttributeTotal OBJECT-TYPE
        SYNTAX         Integer32
        MAX-ACCESS     read-only
        STATUS         current
        DESCRIPTION    "."
        ::= { tnOpticalPortInfo 465 }

--------------------------------------------------------------------------------
-- 1830 TPS-12 PS Optical Port Info Table
--------------------------------------------------------------------------------
    tnTPS12PSPortInfoTable OBJECT-TYPE
        SYNTAX         SEQUENCE OF TnTPS12PSPortInfoEntry
        MAX-ACCESS     not-accessible
        STATUS         current
        DESCRIPTION    "The ports on a 1830 TPS-12 PS optical card."
        ::= { tnOpticalPortInfo 466 }

    tnTPS12PSPortInfoEntry OBJECT-TYPE
        SYNTAX         TnTPS12PSPortInfoEntry
        MAX-ACCESS     not-accessible
        STATUS         current
        DESCRIPTION    "."
        INDEX { ifIndex }
        ::= { tnTPS12PSPortInfoTable 1 }

    TnTPS12PSPortInfoEntry ::=
        SEQUENCE {
            tnTPS12PSPortInfoFunction     INTEGER
        }

    tnTPS12PSPortInfoFunction OBJECT-TYPE
        SYNTAX         INTEGER {
                         network(1),
                         client(2),
                         tod(3),
                         otc(4),
                         ethman(5)
                       }
        MAX-ACCESS     read-only
        STATUS         current
        DESCRIPTION    "Indicates the functional type of this 1830 TPS-12 PS port."
        ::= { tnTPS12PSPortInfoEntry 1 }

-------------------------------------------------------------------------------
-- Esre Optical Port Info Scalar
-------------------------------------------------------------------------------
    tnEsrePortInfoAttributeTotal OBJECT-TYPE
        SYNTAX         Integer32
        MAX-ACCESS     read-only
        STATUS         current
        DESCRIPTION    "."
        ::= { tnOpticalPortInfo 467 }

-------------------------------------------------------------------------------
-- Esre Optical Port Info Table
-------------------------------------------------------------------------------
    tnEsrePortInfoTable OBJECT-TYPE
        SYNTAX         SEQUENCE OF TnEsrePortInfoEntry
        MAX-ACCESS     not-accessible
        STATUS         current
        DESCRIPTION    "The ports on an Esre optical card."
        ::= { tnOpticalPortInfo 468 }

    tnEsrePortInfoEntry OBJECT-TYPE
        SYNTAX         TnEsrePortInfoEntry
        MAX-ACCESS     not-accessible
        STATUS         current
        DESCRIPTION    "."
        INDEX { ifIndex }
        ::= { tnEsrePortInfoTable 1 }

    TnEsrePortInfoEntry ::=
        SEQUENCE {
            tnEsrePortInfoFunction     INTEGER
        }

    tnEsrePortInfoFunction OBJECT-TYPE
        SYNTAX         INTEGER {
                         oes1(1),
                         ees1(2),
                         oes2(3),
                         ees2(4)
                       }
        MAX-ACCESS     read-only
        STATUS         current
        DESCRIPTION    "Indicates the functional type of this Esre port."
        ::= { tnEsrePortInfoEntry 1 }

------------------------------------------------------------------------------
-- Generic Optical Port Info Scalar
-------------------------------------------------------------------------------
    tnGenericOtPortInfoAttributeTotal OBJECT-TYPE
        SYNTAX         Integer32
        MAX-ACCESS     read-only
        STATUS         current
        DESCRIPTION    "."
        ::= { tnOpticalPortInfo 469 }

-------------------------------------------------------------------------------
-- Generic Optical Port Info Table
-------------------------------------------------------------------------------
    tnGenericOtPortInfoTable OBJECT-TYPE
        SYNTAX         SEQUENCE OF TnGenericPortInfoEntry
        MAX-ACCESS     not-accessible
        STATUS         current
        DESCRIPTION    "The ports on a Generic optical card."
        ::= { tnOpticalPortInfo 470 }

    tnGenericOtPortInfoEntry OBJECT-TYPE
        SYNTAX         TnGenericPortInfoEntry
        MAX-ACCESS     not-accessible
        STATUS         current
        DESCRIPTION    "."
        INDEX { ifIndex }
        ::= { tnGenericOtPortInfoTable 1 }

    TnGenericPortInfoEntry ::=
        SEQUENCE {
            tnGenericOtPortInfoFunction     INTEGER
        }

    tnGenericOtPortInfoFunction OBJECT-TYPE
        SYNTAX         INTEGER {
                         network(1),
                         client(2),
                         backplane(3)
                       }
        MAX-ACCESS     read-only
        STATUS         current
        DESCRIPTION    "Indicates the functional type of this Generic port."
        ::= { tnGenericOtPortInfoEntry 1 }

-------------------------------------------------------------------------------
-- 1ety100 Optical Port Info Scalar
-------------------------------------------------------------------------------
    tn1ety100PortInfoAttributeTotal OBJECT-TYPE
        SYNTAX         Integer32
        MAX-ACCESS     read-only
        STATUS         current
        DESCRIPTION    "."
        ::= { tnOpticalPortInfo 471 }

-------------------------------------------------------------------------------
-- 1ety100 Optical Port Info Table
-------------------------------------------------------------------------------
    tn1ety100PortInfoTable OBJECT-TYPE
        SYNTAX         SEQUENCE OF Tn1ety100PortInfoEntry
        MAX-ACCESS     not-accessible
        STATUS         current
        DESCRIPTION    "The ports on an 1ety100 card."
        ::= { tnOpticalPortInfo 472 }

    tn1ety100PortInfoEntry OBJECT-TYPE
        SYNTAX         Tn1ety100PortInfoEntry
        MAX-ACCESS     not-accessible
        STATUS         current
        DESCRIPTION    "."
        INDEX { ifIndex }
        ::= { tn1ety100PortInfoTable 1 }

    Tn1ety100PortInfoEntry ::=
        SEQUENCE {
            tn1ety100PortInfoFunction     INTEGER
        }

    tn1ety100PortInfoFunction OBJECT-TYPE
        SYNTAX         INTEGER {
                         network(1),
                         backplane(2)
                       }
        MAX-ACCESS     read-only
        STATUS         current
        DESCRIPTION    "Indicates the functional type of this 1ety100 port."
        ::= { tn1ety100PortInfoEntry 1 }

--    obsolete
--    tnD1ad400qPortInfoAttributeTotal OBJECT-TYPE ::= { tnOpticalPortInfo 473 }
--    tnD1ad400qPortInfoTable          OBJECT-TYPE ::= { tnOpticalPortInfo 474 }

-------------------------------------------------------------------------------
-- Omdcl Optical Port Info Scalar
-------------------------------------------------------------------------------
    tnOmdclPortInfoAttributeTotal OBJECT-TYPE
        SYNTAX         Integer32
        MAX-ACCESS     read-only
        STATUS         current
        DESCRIPTION    "."
        ::= { tnOpticalPortInfo 475 }

-------------------------------------------------------------------------------
-- Omdcl Optical Port Info Table
-------------------------------------------------------------------------------
    tnOmdclPortInfoTable OBJECT-TYPE
        SYNTAX         SEQUENCE OF TnOmdclPortInfoEntry
        MAX-ACCESS     not-accessible
        STATUS         current
        DESCRIPTION    "The ports on an Omdcl card."
        ::= { tnOpticalPortInfo 476 }

    tnOmdclPortInfoEntry OBJECT-TYPE
        SYNTAX         TnOmdclPortInfoEntry
        MAX-ACCESS     not-accessible
        STATUS         current
        DESCRIPTION    "."
        INDEX { ifIndex }
        ::= { tnOmdclPortInfoTable 1 }

    TnOmdclPortInfoEntry ::=
        SEQUENCE {
            tnOmdclPortInfoFunction                                INTEGER,
            tnOmdclPortInfoOSCSfpRxPowerIn                         Integer32,
            tnOmdclPortInfoOSCSfpTxPowerOut                        Integer32,
            tnOmdclPortInfoOSCTxPowerIn                            Integer32,
            tnOmdclPortInfoOSCTxPowerOut                           Integer32,
            tnOmdclPortInfoTotalInputPower                         Integer32,
            tnOmdclPortInfoTotalInputPowerL                        Integer32,
            tnOmdclPortInfoInsertionLossSigC1IntoLine1Out          Integer32,
            tnOmdclPortInfoInsertionLossSigC2IntoLine2Out          Integer32,
            tnOmdclPortInfoInsertionLossSigL1IntoLine1OutL         Integer32,
            tnOmdclPortInfoInsertionLossSigL2IntoLine2OutL         Integer32,
            tnOmdclPortInfoInsertionLosstoSigC1OutFromLine1In      Integer32,
            tnOmdclPortInfoInsertionLosstoSigC2OutFromLine2In      Integer32,
            tnOmdclPortInfoInsertionLosstoSigL1OutFromLine1InL     Integer32,
            tnOmdclPortInfoInsertionLosstoSigL2OutFromLine2InL     Integer32,
            tnOmdclPortInfoTotalOutputPower                        Integer32,
            tnOmdclPortInfoTotalOutputPowerL                       Integer32,
            tnOmdclPortInfoTotalOutputPowerCplusL                  Integer32,
            tnOmdclPortInfoSpanLoss                                Integer32
        }

    tnOmdclPortInfoFunction OBJECT-TYPE
        SYNTAX         INTEGER {
                         lineIn(1),
                         lineOut(2),
                         sigcIn(3),
                         sigcOut(4),
                         siglIn(5),
                         siglOut(6),
                         oscsfp(7),
                         osc(8),
                         custlan(9),
                         osclan(10)
                       }
        MAX-ACCESS     read-only
        STATUS         current
        DESCRIPTION    "Indicates the functional type of this Omdcl port."
        ::= { tnOmdclPortInfoEntry 1 }

    tnOmdclPortInfoOSCSfpRxPowerIn OBJECT-TYPE
        SYNTAX         Integer32
        UNITS          "mBm"
        MAX-ACCESS     read-only
        STATUS         current
        DESCRIPTION    "The OSCSFP transceiver input power."
        ::= { tnOmdclPortInfoEntry 2 }

    tnOmdclPortInfoOSCSfpTxPowerOut OBJECT-TYPE
        SYNTAX         Integer32
        UNITS          "mBm"
        MAX-ACCESS     read-only
        STATUS         current
        DESCRIPTION    "The OSCSFP transceiver output power."
        ::= { tnOmdclPortInfoEntry 3 }

    tnOmdclPortInfoOSCTxPowerIn OBJECT-TYPE
        SYNTAX         Integer32
        UNITS          "mBm"
        MAX-ACCESS     read-only
        STATUS         current
        DESCRIPTION    "."
        ::= { tnOmdclPortInfoEntry 4 }

    tnOmdclPortInfoOSCTxPowerOut OBJECT-TYPE
        SYNTAX         Integer32
        UNITS          "mBm"
        MAX-ACCESS     read-only
        STATUS         current
        DESCRIPTION    "."
        ::= { tnOmdclPortInfoEntry 5 }

    tnOmdclPortInfoTotalInputPower OBJECT-TYPE
        SYNTAX         Integer32
        UNITS          "mBm"
        MAX-ACCESS     read-only
        STATUS         current
        DESCRIPTION    "OMDCL Total input power C band."
        ::= { tnOmdclPortInfoEntry 6 }

    tnOmdclPortInfoTotalInputPowerL OBJECT-TYPE
        SYNTAX         Integer32
        UNITS          "mBm"
        MAX-ACCESS     read-only
        STATUS         current
        DESCRIPTION    "OMDCL Total input power L band."
        ::= { tnOmdclPortInfoEntry 7 }

    tnOmdclPortInfoInsertionLossSigC1IntoLine1Out OBJECT-TYPE
        SYNTAX         Integer32
        UNITS          "mB"
        MAX-ACCESS     read-only
        STATUS         current
        DESCRIPTION    "Egress Insertion Loss to Line1Out."
        DEFVAL         { 100 }
        ::= { tnOmdclPortInfoEntry 8 }

    tnOmdclPortInfoInsertionLossSigC2IntoLine2Out OBJECT-TYPE
        SYNTAX         Integer32
        UNITS          "mB"
        MAX-ACCESS     read-only
        STATUS         current
        DESCRIPTION    "Egress Insertion Loss to Line2Out."
        DEFVAL         { 100 }
        ::= { tnOmdclPortInfoEntry 9 }

    tnOmdclPortInfoInsertionLossSigL1IntoLine1OutL OBJECT-TYPE
        SYNTAX         Integer32
        UNITS          "mB"
        MAX-ACCESS     read-only
        STATUS         current
        DESCRIPTION    "Egress Insertion Loss to Line1Out L band."
        DEFVAL         { 100 }
        ::= { tnOmdclPortInfoEntry 10 }

    tnOmdclPortInfoInsertionLossSigL2IntoLine2OutL OBJECT-TYPE
        SYNTAX         Integer32
        UNITS          "mB"
        MAX-ACCESS     read-only
        STATUS         current
        DESCRIPTION    "Egress Insertion Loss to Line2Out L band."
        DEFVAL         { 100 }
        ::= { tnOmdclPortInfoEntry 11 }

    tnOmdclPortInfoInsertionLosstoSigC1OutFromLine1In OBJECT-TYPE
        SYNTAX         Integer32
        UNITS          "mB"
        MAX-ACCESS     read-only
        STATUS         current
        DESCRIPTION    "Ingress Insertion Loss from Line1In."
        DEFVAL         { 80 }
        ::= { tnOmdclPortInfoEntry 12 }

    tnOmdclPortInfoInsertionLosstoSigC2OutFromLine2In OBJECT-TYPE
        SYNTAX         Integer32
        UNITS          "mB"
        MAX-ACCESS     read-only
        STATUS         current
        DESCRIPTION    "Ingress Insertion Loss from Line2In."
        DEFVAL         { 80 }
        ::= { tnOmdclPortInfoEntry 13 }

    tnOmdclPortInfoInsertionLosstoSigL1OutFromLine1InL OBJECT-TYPE
        SYNTAX         Integer32
        UNITS          "mB"
        MAX-ACCESS     read-only
        STATUS         current
        DESCRIPTION    "Ingress Insertion Loss from Line1In L Band."
        DEFVAL         { 80 }
        ::= { tnOmdclPortInfoEntry 14 }

    tnOmdclPortInfoInsertionLosstoSigL2OutFromLine2InL OBJECT-TYPE
        SYNTAX         Integer32
        UNITS          "mB"
        MAX-ACCESS     read-only
        STATUS         current
        DESCRIPTION    "Ingress Insertion Loss from Line2In L Band."
        DEFVAL         { 80 }
        ::= { tnOmdclPortInfoEntry 15 }

    tnOmdclPortInfoTotalOutputPower OBJECT-TYPE
        SYNTAX         Integer32
        UNITS          "mBm"
        MAX-ACCESS     read-only
        STATUS         current
        DESCRIPTION    "Total Output Power C band."
        DEFVAL         { -9900 }
        ::= { tnOmdclPortInfoEntry 16 }

    tnOmdclPortInfoTotalOutputPowerL OBJECT-TYPE
        SYNTAX         Integer32
        UNITS          "mBm"
        MAX-ACCESS     read-only
        STATUS         current
        DESCRIPTION    "Total Output Power L band."
        DEFVAL         { -9900 }
        ::= { tnOmdclPortInfoEntry 17 }

    tnOmdclPortInfoTotalOutputPowerCplusL OBJECT-TYPE
        SYNTAX         Integer32
        UNITS          "mBm"
        MAX-ACCESS     read-only
        STATUS         current
        DESCRIPTION    "Total Output Power C + L bands."
        ::= { tnOmdclPortInfoEntry 18 }

    tnOmdclPortInfoSpanLoss OBJECT-TYPE
        SYNTAX         Integer32
        UNITS          "mB"
        MAX-ACCESS     read-only
        STATUS         current
        DESCRIPTION    "Span loss."
        DEFVAL         { 9900 }
        ::= { tnOmdclPortInfoEntry 19 }

--------------------------------------------------------------------------------
-- MCS16-15L Optical Port Info Scalar
--------------------------------------------------------------------------------
    tnMcs16x15lPortInfoAttributeTotal OBJECT-TYPE
        SYNTAX         Integer32
        MAX-ACCESS     read-only
        STATUS         current
        DESCRIPTION    "."
        ::= { tnOpticalPortInfo 477 }

--------------------------------------------------------------------------------
-- MCS16-15L Optical Port Info Table
--------------------------------------------------------------------------------
    tnMcs16x15lPortInfoTable OBJECT-TYPE
        SYNTAX         SEQUENCE OF TnMcs16x15lPortInfoEntry
        MAX-ACCESS     not-accessible
        STATUS         current
        DESCRIPTION    "The ports on a MCS16-15L optical card."
        ::= { tnOpticalPortInfo 478 }

    tnMcs16x15lPortInfoEntry OBJECT-TYPE
        SYNTAX         TnMcs16x15lPortInfoEntry
        MAX-ACCESS     not-accessible
        STATUS         current
        DESCRIPTION    "."
        INDEX { ifIndex }
        ::= { tnMcs16x15lPortInfoTable 1 }

    TnMcs16x15lPortInfoEntry ::=
        SEQUENCE {
            tnMcs16x15lPortInfoFunction                  INTEGER
        }

    tnMcs16x15lPortInfoFunction OBJECT-TYPE
        SYNTAX         INTEGER {
                         signal(1),
                         ad(2),
                         mpoAar(3)
                       }
        MAX-ACCESS     read-only
        STATUS         current
        DESCRIPTION    "Indicates the functional type of this
                        MCS16-15L port."
        ::= { tnMcs16x15lPortInfoEntry 1 }
-------------------------------------------------------------------------------
-- EILAL Optical Port Info Scalar
-------------------------------------------------------------------------------
    tnEilalPortInfoAttributeTotal OBJECT-TYPE
        SYNTAX         Integer32
        MAX-ACCESS     read-only
        STATUS         current
        DESCRIPTION    "."
        ::= { tnOpticalPortInfo 479 }

-------------------------------------------------------------------------------
-- EILAL Optical Port Info Table
-------------------------------------------------------------------------------
    tnEilalPortInfoTable OBJECT-TYPE
        SYNTAX         SEQUENCE OF TnEilalPortInfoEntry
        MAX-ACCESS     not-accessible
        STATUS         current
        DESCRIPTION    "The ports on a EILAL optical card."
        ::= { tnOpticalPortInfo 480 }

    tnEilalPortInfoEntry OBJECT-TYPE
        SYNTAX         TnEilalPortInfoEntry
        MAX-ACCESS     not-accessible
        STATUS         current
        DESCRIPTION    "."
        INDEX { ifIndex }
        ::= { tnEilalPortInfoTable 1 }

    TnEilalPortInfoEntry ::=
        SEQUENCE {
            tnEilalPortInfoFunction INTEGER
        }


    tnEilalPortInfoFunction OBJECT-TYPE
        SYNTAX         INTEGER {
                         lineIn(1),
                         otdrRx(2),
                         otdrTx(3),
                         lineOut(4),
                         oscSfp(5),
                         osc(6),
                         custLan(7),
                         inv(8),
                         oscLan(9)
                       }
        MAX-ACCESS     read-only
        STATUS         current
        DESCRIPTION    "Indicates the functional type of this EILAL port."
        ::= { tnEilalPortInfoEntry 1 }

--------------------------------------------------------------------------------
-- RA5PB Optical Port Info Scalar
--------------------------------------------------------------------------------
    tnRa5pbPortInfoAttributeTotal OBJECT-TYPE
        SYNTAX         Integer32
        MAX-ACCESS     read-only
        STATUS         current
        DESCRIPTION    "."
        ::= { tnOpticalPortInfo 481 }

--------------------------------------------------------------------------------
-- RA5PB Optical Port Info Table
--------------------------------------------------------------------------------
    tnRa5pbPortInfoTable OBJECT-TYPE
        SYNTAX         SEQUENCE OF TnRa5pbPortInfoEntry
        MAX-ACCESS     not-accessible
        STATUS         current
        DESCRIPTION    "The ports on a RA5PB optical card."
        ::= { tnOpticalPortInfo 482 }

    tnRa5pbPortInfoEntry OBJECT-TYPE
        SYNTAX         TnRa5pbPortInfoEntry
        MAX-ACCESS     not-accessible
        STATUS         current
        DESCRIPTION    "."
        INDEX { ifIndex }
        ::= { tnRa5pbPortInfoTable 1 }

    TnRa5pbPortInfoEntry ::=
        SEQUENCE {
            tnRa5pbPortInfoFunction INTEGER
        }

    tnRa5pbPortInfoFunction OBJECT-TYPE
        SYNTAX         INTEGER {
                         lineIn(1),
                         lineOut(2)
                       }
        MAX-ACCESS     read-only
        STATUS         current
        DESCRIPTION    "Indicates the functional type of this RA5PB port."
        ::= { tnRa5pbPortInfoEntry 1 }

--------------------------------------------------------------------------------
-- MLFSB Optical Port Info Scalar
--------------------------------------------------------------------------------
    tnMlfsbPortInfoAttributeTotal OBJECT-TYPE
        SYNTAX         Integer32
        MAX-ACCESS     read-only
        STATUS         current
        DESCRIPTION    "."
        ::= { tnOpticalPortInfo 483 }

--------------------------------------------------------------------------------
-- MLFSB Optical Port Info Table
--------------------------------------------------------------------------------
    tnMlfsbPortInfoTable OBJECT-TYPE
        SYNTAX         SEQUENCE OF TnMlfsbPortInfoEntry
        MAX-ACCESS     not-accessible
        STATUS         current
        DESCRIPTION    "The ports on a MLFSB optical card."
        ::= { tnOpticalPortInfo 484 }

    tnMlfsbPortInfoEntry OBJECT-TYPE
        SYNTAX         TnMlfsbPortInfoEntry
        MAX-ACCESS     not-accessible
        STATUS         current
        DESCRIPTION    "."
        INDEX { ifIndex }
        ::= { tnMlfsbPortInfoTable 1 }

    TnMlfsbPortInfoEntry ::=
        SEQUENCE {
            tnMlfsbPortInfoFunction     INTEGER
        }

    tnMlfsbPortInfoFunction OBJECT-TYPE
        SYNTAX         INTEGER {
                         mpoMx(1),
                         mpoLc(2)
                       }
        MAX-ACCESS     read-only
        STATUS         current
        DESCRIPTION    "Indicates the functional type of this MLFSB port."
        ::= { tnMlfsbPortInfoEntry 1 }

--------------------------------------------------------------------------------
-- 1830 Optical Port LPT Info Scalars
--------------------------------------------------------------------------------
    tnPortLptInfoAttributeTotal OBJECT-TYPE
        SYNTAX         Integer32
        MAX-ACCESS     read-only
        STATUS         current
        DESCRIPTION    "."
        ::= { tnOpticalPortInfo 485 }

--------------------------------------------------------------------------------
-- 1830 Optical Port LPT Info Table
--------------------------------------------------------------------------------
    tnPortLptInfoTable OBJECT-TYPE
        SYNTAX         SEQUENCE OF TnPortLptInfoEntry
        MAX-ACCESS     not-accessible
        STATUS         current
        DESCRIPTION    "The LPT functon on a ports in a 1830 card."
        ::= { tnOpticalPortInfo 486 }

    tnPortLptInfoEntry OBJECT-TYPE
        SYNTAX         TnPortLptInfoEntry
        MAX-ACCESS     not-accessible
        STATUS         current
        DESCRIPTION    "."
        INDEX { ifIndex }
        ::= { tnPortLptInfoTable 1 }

    TnPortLptInfoEntry ::=
        SEQUENCE {
            tnPortLptInfoCons               INTEGER,
            tnPortLptInfoFlsDelayTime       Integer32,
            tnPortLptInfoTxDisDelayTime     Integer32,
            tnPortLptInfoExtensionTime      Integer32
        }

    tnPortLptInfoCons OBJECT-TYPE
        SYNTAX         INTEGER {
                         disable(1),
                         fls(2),
                         cpritxdis(3)
                       }
        MAX-ACCESS     read-only
        STATUS         current
        DESCRIPTION    "Configure LPT Consequent Action on port basis at local
                        client port, when CSF/SSF is detected on network side.
                        This parameter applies only to the LPT CA enabled/disabled
                        by the user (i.e., aCPRITxDis, and aFLS), but does not
                        apply to the LPT CA non configurable by the user (i.e.,
                        aAllZeroBits, aLoPattern). It is applied for cpri-obsai
                        port only."
        ::= { tnPortLptInfoEntry 1 }

    tnPortLptInfoFlsDelayTime OBJECT-TYPE
        SYNTAX         Integer32 (0..300000)
        MAX-ACCESS     read-only
        STATUS         current
        DESCRIPTION    "The LPT SSF CA FLS delay time on port basis at local
                        LAN port.  Delay time on LAN port is used to postpone
                        the consequent actions on LAN port to take effect, in
                        order to avoid the conflicts with server protection,
                        valid for cpri-obsai only.  Range is 0 - 300000 ms, in
                        a unit of ms."
        ::= { tnPortLptInfoEntry 2 }

    tnPortLptInfoTxDisDelayTime OBJECT-TYPE
        SYNTAX         Integer32 (0..300000)
        MAX-ACCESS     read-only
        STATUS         current
        DESCRIPTION    "the LPT CA CPRITxDis delay time on port basis at local
                        LAN port.  Delay time on LAN port is used to postpone
                        the consequent actions on LAN port to take effect, in
                        order to avoid the conflicts with server protection,
                        valid for cpri-obsai only.  Range is 0 - 300000 ms, in
                        a unit of ms."
        ::= { tnPortLptInfoEntry 3 }

    tnPortLptInfoExtensionTime OBJECT-TYPE
        SYNTAX         Integer32 (0..300000)
        MAX-ACCESS     read-only
        STATUS         current
        DESCRIPTION    "The LPT SSF/CSF CA extension time on port basis at
                        local LAN port.  The consequent action is extended to
                        be at least extension time long enough to trigger the
                        reset or restart calibration at BBU/RU, valid for
                        cpri-obsai only.  Range is 0 - 300000 ms, in a unit
                        of ms."
        ::= { tnPortLptInfoEntry 4 }

--------------------------------------------------------------------------------
-- 1830 Optical Port Info Scalar
--------------------------------------------------------------------------------
    tnPortInfoAttributeTotal OBJECT-TYPE
        SYNTAX         Integer32
        MAX-ACCESS     read-only
        STATUS         current
        DESCRIPTION    "."
        ::= { tnOpticalPortInfo 487 }

--------------------------------------------------------------------------------
-- 1830 Optical Port Info Table
--------------------------------------------------------------------------------
    tnPortInfoTable OBJECT-TYPE
        SYNTAX         SEQUENCE OF TnPortInfoEntry
        MAX-ACCESS     not-accessible
        STATUS         current
        DESCRIPTION    "The ports on a 1830 optical card."
        ::= { tnOpticalPortInfo 488 }

    tnPortInfoEntry OBJECT-TYPE
        SYNTAX         TnPortInfoEntry
        MAX-ACCESS     not-accessible
        STATUS         current
        DESCRIPTION    "."
        INDEX { ifIndex }
        ::= { tnPortInfoTable 1 }

    TnPortInfoEntry ::=
        SEQUENCE {
            tnPortInfoFunction     INTEGER
        }

    tnPortInfoFunction OBJECT-TYPE
        SYNTAX         INTEGER {
                         network(1),
                         client(2),
                         ethman(3),
                         cit(4),
                         lan(5),
                         otc(6),
                         tod(7),
                         bits(8),
                         ppstest(9)
                       }
        MAX-ACCESS     read-only
        STATUS         current
        DESCRIPTION    "Indicates the functional type of this 1830 port."
        ::= { tnPortInfoEntry 1 }

--------------------------------------------------------------------------------
-- 18P400 Optical Port Info Scalar
--------------------------------------------------------------------------------
    tn18P400PortInfoAttributeTotal OBJECT-TYPE
        SYNTAX         Integer32
        MAX-ACCESS     read-only
        STATUS         current
        DESCRIPTION    "."
        ::= { tnOpticalPortInfo 489 }

--------------------------------------------------------------------------------
-- 18P400 Optical Port Info Table
--------------------------------------------------------------------------------
    tn18P400PortInfoTable OBJECT-TYPE
        SYNTAX         SEQUENCE OF Tn18P400PortInfoEntry
        MAX-ACCESS     not-accessible
        STATUS         current
        DESCRIPTION    "The ports on a 18P400 optical card."
        ::= { tnOpticalPortInfo 490 }

    tn18P400PortInfoEntry OBJECT-TYPE
        SYNTAX         Tn18P400PortInfoEntry
        MAX-ACCESS     not-accessible
        STATUS         current
        DESCRIPTION    "."
        INDEX { ifIndex }
        ::= { tn18P400PortInfoTable 1 }

    Tn18P400PortInfoEntry ::=
        SEQUENCE {
            tn18P400PortInfoFunction INTEGER
        }

    tn18P400PortInfoFunction OBJECT-TYPE
        SYNTAX         INTEGER {
                         client(1),
                         backplane(2)
                       }
        MAX-ACCESS     read-only
        STATUS         current
        DESCRIPTION    "Indicates the functional type of this 18P400 port."
        ::= { tn18P400PortInfoEntry 1 }

--------------------------------------------------------------------------------
-- 4UC1T Optical Port Info Scalar
--------------------------------------------------------------------------------
    tn4uc1tPortInfoAttributeTotal OBJECT-TYPE
        SYNTAX         Integer32
        MAX-ACCESS     read-only
        STATUS         current
        DESCRIPTION    "."
        ::= { tnOpticalPortInfo 491 }

--------------------------------------------------------------------------------
-- 4UC1T Optical Port Info Table
--------------------------------------------------------------------------------
    tn4uc1tPortInfoTable OBJECT-TYPE
        SYNTAX         SEQUENCE OF Tn4uc1tPortInfoEntry
        MAX-ACCESS     not-accessible
        STATUS         current
        DESCRIPTION    "The ports on a 4UC1T optical card."
        ::= { tnOpticalPortInfo 492 }

    tn4uc1tPortInfoEntry OBJECT-TYPE
        SYNTAX         Tn4uc1tPortInfoEntry
        MAX-ACCESS     not-accessible
        STATUS         current
        DESCRIPTION    "."
        INDEX { ifIndex }
        ::= { tn4uc1tPortInfoTable 1 }

    Tn4uc1tPortInfoEntry ::=
        SEQUENCE {
            tn4uc1tPortInfoFunction INTEGER
        }

    tn4uc1tPortInfoFunction OBJECT-TYPE
        SYNTAX         INTEGER {
                         network(1)
                       }
        MAX-ACCESS     read-only
        STATUS         current
        DESCRIPTION    "Indicates the functional type of this 4UC1T port."
        ::= { tn4uc1tPortInfoEntry 1 }

--------------------------------------------------------------------------------
-- ASG Optical Port Info Scalar
--------------------------------------------------------------------------------
    tnAsgPortInfoAttributeTotal OBJECT-TYPE
        SYNTAX         Integer32
        MAX-ACCESS     read-only
        STATUS         current
        DESCRIPTION    "."
        ::= { tnOpticalPortInfo 493 }

--------------------------------------------------------------------------------
-- ASG Optical Port Info Table
--------------------------------------------------------------------------------
    tnAsgPortInfoTable OBJECT-TYPE
        SYNTAX         SEQUENCE OF TnAsgPortInfoEntry
        MAX-ACCESS     not-accessible
        STATUS         current
        DESCRIPTION    "The ports on a ASG optical card."
        ::= { tnOpticalPortInfo 494 }

    tnAsgPortInfoEntry OBJECT-TYPE
        SYNTAX         TnAsgPortInfoEntry
        MAX-ACCESS     not-accessible
        STATUS         current
        DESCRIPTION    "."
        INDEX { ifIndex }
        ::= { tnAsgPortInfoTable 1 }

    TnAsgPortInfoEntry ::=
        SEQUENCE {
            tnAsgPortInfoFunction  INTEGER
        }

    tnAsgPortInfoFunction OBJECT-TYPE
        SYNTAX         INTEGER {
                         lineIn(1),
                         otdrRx(2),
                         otdrTx(3),
                         lineOut(4),
                         oscSfp(5),
                         osc(6),
                         custLan(7),
                         inv(8)
                       }
        MAX-ACCESS     read-only
        STATUS         current
        DESCRIPTION    "Indicates the functional type of this ASG port."
        ::= { tnAsgPortInfoEntry 1 }

--------------------------------------------------------------------------------
-- 12P120S Optical Port Info Scalar
--------------------------------------------------------------------------------
    tn12p120sPortInfoAttributeTotal OBJECT-TYPE
        SYNTAX         Integer32
        MAX-ACCESS     read-only
        STATUS         current
        DESCRIPTION    "."
        ::= { tnOpticalPortInfo 495 }

--------------------------------------------------------------------------------
-- 12P120S Optical Port Info Table
--------------------------------------------------------------------------------
    tn12p120sPortInfoTable OBJECT-TYPE
        SYNTAX         SEQUENCE OF Tn12p120sPortInfoEntry
        MAX-ACCESS     not-accessible
        STATUS         current
        DESCRIPTION    "The ports on a 12P120S optical card."
        ::= { tnOpticalPortInfo 496 }

    tn12p120sPortInfoEntry OBJECT-TYPE
        SYNTAX         Tn12p120sPortInfoEntry
        MAX-ACCESS     not-accessible
        STATUS         current
        DESCRIPTION    "."
        INDEX { ifIndex }
        ::= { tn12p120sPortInfoTable 1 }

    Tn12p120sPortInfoEntry ::=
        SEQUENCE {
            tn12p120sPortInfoFunction  INTEGER
        }

    tn12p120sPortInfoFunction OBJECT-TYPE
        SYNTAX         INTEGER {
                         network(1),
                         client(2),
                         evoa(3),
                         backplane(4)
                       }
        MAX-ACCESS     read-only
        STATUS         current
        DESCRIPTION    "Indicates the functional type of this 12P120S port."
        ::= { tn12p120sPortInfoEntry 1 }

--------------------------------------------------------------------------------
-- 16P200 Optical Port Info Scalar
--------------------------------------------------------------------------------
    tn16p200PortInfoAttributeTotal OBJECT-TYPE
        SYNTAX         Integer32
        MAX-ACCESS     read-only
        STATUS         current
        DESCRIPTION    "."
        ::= { tnOpticalPortInfo 497 }

--------------------------------------------------------------------------------
-- 16P200 Optical Port Info Table
--------------------------------------------------------------------------------
    tn16p200PortInfoTable OBJECT-TYPE
        SYNTAX         SEQUENCE OF Tn16p200PortInfoEntry
        MAX-ACCESS     not-accessible
        STATUS         current
        DESCRIPTION    "The ports on a 16P200 optical card."
        ::= { tnOpticalPortInfo 498 }

    tn16p200PortInfoEntry OBJECT-TYPE
        SYNTAX         Tn16p200PortInfoEntry
        MAX-ACCESS     not-accessible
        STATUS         current
        DESCRIPTION    "."
        INDEX { ifIndex }
        ::= { tn16p200PortInfoTable 1 }

    Tn16p200PortInfoEntry ::=
        SEQUENCE {
            tn16p200PortInfoFunction  INTEGER
        }

    tn16p200PortInfoFunction OBJECT-TYPE
        SYNTAX         INTEGER {
                         network(1),
                         client(2)
                       }
        MAX-ACCESS     read-only
        STATUS         current
        DESCRIPTION    "Indicates the functional type of this 16P200 port."
        ::= { tn16p200PortInfoEntry 1 }

--------------------------------------------------------------------------------
-- IR9 Optical Port Info Scalar
--------------------------------------------------------------------------------
    tnIr9PortInfoAttributeTotal OBJECT-TYPE
        SYNTAX         Integer32
        MAX-ACCESS     read-only
        STATUS         current
        DESCRIPTION    "."
        ::= { tnOpticalPortInfo 499 }

--------------------------------------------------------------------------------
-- IR9 Optical Port Info Table
--------------------------------------------------------------------------------
    tnIr9PortInfoTable OBJECT-TYPE
        SYNTAX         SEQUENCE OF TnIr9PortInfoEntry
        MAX-ACCESS     not-accessible
        STATUS         current
        DESCRIPTION    "The ports on a IR9 optical card."
        ::= { tnOpticalPortInfo 500 }

    tnIr9PortInfoEntry OBJECT-TYPE
        SYNTAX         TnIr9PortInfoEntry
        MAX-ACCESS     not-accessible
        STATUS         current
        DESCRIPTION    "."
        INDEX { ifIndex }
        ::= { tnIr9PortInfoTable 1 }

    TnIr9PortInfoEntry ::=
        SEQUENCE {
            tnIr9PortInfoFunction INTEGER
        }

    tnIr9PortInfoFunction OBJECT-TYPE
        SYNTAX         INTEGER {
                         lineIn(1),
                         inv(2),
                         osc(3),
                         lineOut(4),
                         oscSfp(5),
                         adt(6),
                         otdrRx(7),
                         otdrTx(8),
                         custLan(9)
                       }
        MAX-ACCESS     read-only
        STATUS         current
        DESCRIPTION    "Indicates the functional type of this IR9 port."
        ::= { tnIr9PortInfoEntry 1 }

--------------------------------------------------------------------------------
-- MXN824 Optical Port Info Scalar
--------------------------------------------------------------------------------
    tnMxn824PortInfoAttributeTotal OBJECT-TYPE
        SYNTAX         Integer32
        MAX-ACCESS     read-only
        STATUS         current
        DESCRIPTION    "."
        ::= { tnOpticalPortInfo 501 }

--------------------------------------------------------------------------------
-- MXN824 Optical Port Info Table
--------------------------------------------------------------------------------
    tnMxn824PortInfoTable OBJECT-TYPE
        SYNTAX         SEQUENCE OF TnMxn824PortInfoEntry
        MAX-ACCESS     not-accessible
        STATUS         current
        DESCRIPTION    "The ports on a MXN824 optical card."
        ::= { tnOpticalPortInfo 502 }

    tnMxn824PortInfoEntry OBJECT-TYPE
        SYNTAX         TnMxn824PortInfoEntry
        MAX-ACCESS     not-accessible
        STATUS         current
        DESCRIPTION    "."
        INDEX { ifIndex }
        ::= { tnMxn824PortInfoTable 1 }

    TnMxn824PortInfoEntry ::=
        SEQUENCE {
            tnMxn824PortInfoFunction                    INTEGER
        }

    tnMxn824PortInfoFunction OBJECT-TYPE
        SYNTAX         INTEGER {
                         sig(1),
                         ad(2),
                         lpbk(3),
                         tl(4),
                         fsm(5)
                       }
        MAX-ACCESS     read-only
        STATUS         current
        DESCRIPTION    "Indicates the functional type of this MXN824 port."
        ::= { tnMxn824PortInfoEntry 1 }

--------------------------------------------------------------------------------
-- ASC4 Optical Port Info Scalar
--------------------------------------------------------------------------------
    tnAsc4PortInfoAttributeTotal OBJECT-TYPE
        SYNTAX         Integer32
        MAX-ACCESS     read-only
        STATUS         current
        DESCRIPTION    "."
        ::= { tnOpticalPortInfo 503 }

--------------------------------------------------------------------------------
-- ASC4 Optical Port Info Table
--------------------------------------------------------------------------------
    tnAsc4PortInfoTable OBJECT-TYPE
        SYNTAX         SEQUENCE OF TnAsc4PortInfoEntry
        MAX-ACCESS     not-accessible
        STATUS         current
        DESCRIPTION    "The ports on a ASC4 optical card."
        ::= { tnOpticalPortInfo 504 }

    tnAsc4PortInfoEntry OBJECT-TYPE
        SYNTAX         TnAsc4PortInfoEntry
        MAX-ACCESS     not-accessible
        STATUS         current
        DESCRIPTION    "."
        INDEX { ifIndex }
        ::= { tnAsc4PortInfoTable 1 }

    TnAsc4PortInfoEntry ::=
        SEQUENCE {
            tnAsc4PortInfoFunction     INTEGER
        }

    tnAsc4PortInfoFunction OBJECT-TYPE
        SYNTAX         INTEGER {
                         sigAIn(1),
                         aOut(2),
                         sigAOut(3),
                         aIn(4),
                         sigBIn(5),
                         bOut(6),
                         sigBOut(7),
                         bIn(8),
                         sigCIn(9),
                         cOut(10),
                         sigCOut(11),
                         cIn(12),
                         sigDIn(13),
                         dOut(14),
                         sigDOut(15),
                         dIn(16)
                       }
        MAX-ACCESS     read-only
        STATUS         current
        DESCRIPTION    "Indicates the functional type of this ASC4 port."
        ::= { tnAsc4PortInfoEntry 1 }

--------------------------------------------------------------------------------
-- 5MX500 Optical Port Info Scalar
--------------------------------------------------------------------------------
    tn5mx500PortInfoAttributeTotal OBJECT-TYPE
        SYNTAX         Integer32
        MAX-ACCESS     read-only
        STATUS         current
        DESCRIPTION    "."
        ::= { tnOpticalPortInfo 505 }

--------------------------------------------------------------------------------
-- 5MX500 Optical Port Info Table
--------------------------------------------------------------------------------
    tn5mx500PortInfoTable OBJECT-TYPE
        SYNTAX         SEQUENCE OF Tn5mx500PortInfoEntry
        MAX-ACCESS     not-accessible
        STATUS         current
        DESCRIPTION    "The ports on a 5MX500 optical card."
        ::= { tnOpticalPortInfo 506 }

    tn5mx500PortInfoEntry OBJECT-TYPE
        SYNTAX         Tn5mx500PortInfoEntry
        MAX-ACCESS     not-accessible
        STATUS         current
        DESCRIPTION    "."
        INDEX { ifIndex }
        ::= { tn5mx500PortInfoTable 1 }

    Tn5mx500PortInfoEntry ::=
        SEQUENCE {
            tn5mx500PortInfoFunction     INTEGER
        }

    tn5mx500PortInfoFunction OBJECT-TYPE
        SYNTAX         INTEGER {
                         client(1)
                       }
        MAX-ACCESS     read-only
        STATUS         current
        DESCRIPTION    "Indicates the functional type of this 5MX500 port."
        ::= { tn5mx500PortInfoEntry 1 }

--------------------------------------------------------------------------------
-- 2UX500 Optical Port Info Scalar
--------------------------------------------------------------------------------
    tn2ux500PortInfoAttributeTotal OBJECT-TYPE
        SYNTAX         Integer32
        MAX-ACCESS     read-only
        STATUS         current
        DESCRIPTION    "."
        ::= { tnOpticalPortInfo 507 }

--------------------------------------------------------------------------------
-- 2UX500 Optical Port Info Table
--------------------------------------------------------------------------------
    tn2ux500PortInfoTable OBJECT-TYPE
        SYNTAX         SEQUENCE OF Tn2ux500PortInfoEntry
        MAX-ACCESS     not-accessible
        STATUS         current
        DESCRIPTION    "The ports on a 2UX500 optical card."
        ::= { tnOpticalPortInfo 508 }

    tn2ux500PortInfoEntry OBJECT-TYPE
        SYNTAX         Tn2ux500PortInfoEntry
        MAX-ACCESS     not-accessible
        STATUS         current
        DESCRIPTION    "."
        INDEX { ifIndex }
        ::= { tn2ux500PortInfoTable 1 }

    Tn2ux500PortInfoEntry ::=
        SEQUENCE {
            tn2ux500PortInfoFunction     INTEGER
        }

    tn2ux500PortInfoFunction OBJECT-TYPE
        SYNTAX         INTEGER {
                         line(1)
                       }
        MAX-ACCESS     read-only
        STATUS         current
        DESCRIPTION    "Indicates the functional type of this 2UX500 port."
        ::= { tn2ux500PortInfoEntry 1 }


--------------------------------------------------------------------------------
-- MXN Channel Info Scalars
--------------------------------------------------------------------------------
    tnMxnPortChannelInfoAttributeTotal OBJECT-TYPE
        SYNTAX         Integer32
        MAX-ACCESS     read-only
        STATUS         current
        DESCRIPTION    "."
        ::= { tnOpticalPortInfo 509 }
--------------------------------------------------------------------------------
-- MXN Port Channel Info Table
--------------------------------------------------------------------------------
    tnMxnPortChannelInfoTable OBJECT-TYPE
        SYNTAX         SEQUENCE OF TnMxnPortChannelInfoEntry
        MAX-ACCESS     not-accessible
        STATUS         current
        DESCRIPTION    "Current disposition AD attributes."
        ::= { tnOpticalPortInfo 510 }

    tnMxnPortChannelInfoEntry OBJECT-TYPE
        SYNTAX         TnMxnPortChannelInfoEntry
        MAX-ACCESS     not-accessible
        STATUS         current
        DESCRIPTION    "."
        INDEX { ifIndex,
                tnChannel }
        ::= { tnMxnPortChannelInfoTable 1 }

    TnMxnPortChannelInfoEntry ::=
        SEQUENCE {
            tnMxnPortChannelInfoCurrentRoutingAdd      INTEGER,
            tnMxnPortChannelInfoCurrentRoutingDrop     INTEGER
        }

    tnMxnPortChannelInfoCurrentRoutingAdd OBJECT-TYPE
        SYNTAX         INTEGER {
                         notProvisioned(1),
                         ad1In(2),
                         ad2In(3),
                         ad3In(4),
                         ad4In(5),
                         ad5In(6),
                         ad6In(7),
                         ad7In(8),
                         ad8In(9),
                         ad9In(10),
                         ad10In(11),
                         ad11In(12),
                         ad12In(13),
                         ad13In(14),
                         ad14In(15),
                         ad15In(16),
                         ad16In(17),
                         ad17In(18),
                         ad18In(19),
                         ad19In(20),
                         ad20In(21),
                         ad21In(22),
                         ad22In(23),
                         ad23In(24),
                         ad24In(25)
                       }
        MAX-ACCESS     read-only
        STATUS         current
        DESCRIPTION    "."
        DEFVAL         { notProvisioned }
        ::= { tnMxnPortChannelInfoEntry 1 }


    tnMxnPortChannelInfoCurrentRoutingDrop OBJECT-TYPE
        SYNTAX         INTEGER {
                         notProvisioned(1),
                         ad1Out(2),
                         ad2Out(3),
                         ad3Out(4),
                         ad4Out(5),
                         ad5Out(6),
                         ad6Out(7),
                         ad7Out(8),
                         ad8Out(9),
                         ad9Out(10),
                         ad10Out(11),
                         ad11Out(12),
                         ad12Out(13),
                         ad13Out(14),
                         ad14Out(15),
                         ad15Out(16),
                         ad16Out(17),
                         ad17Out(18),
                         ad18Out(19),
                         ad19Out(20),
                         ad20Out(21),
                         ad21Out(22),
                         ad22Out(23),
                         ad23Out(24),
                         ad24Out(25)
                       }
        MAX-ACCESS     read-only
        STATUS         current
        DESCRIPTION    "."
        DEFVAL         { notProvisioned }
        ::= { tnMxnPortChannelInfoEntry 2 }

--------------------------------------------------------------------------------
-- MXN Optical Port Info Scalar
--------------------------------------------------------------------------------
    tnMxnPortInfoAttributeTotal OBJECT-TYPE
        SYNTAX         Integer32
        MAX-ACCESS     read-only
        STATUS         current
        DESCRIPTION    "."
        ::= { tnOpticalPortInfo 511 }

--------------------------------------------------------------------------------
-- MXN Optical Port Info Table
--------------------------------------------------------------------------------
    tnMxnPortInfoTable OBJECT-TYPE
        SYNTAX         SEQUENCE OF TnMxnPortInfoEntry
        MAX-ACCESS     not-accessible
        STATUS         current
        DESCRIPTION    "The ports on a MXN optical card."
        ::= { tnOpticalPortInfo 512 }

    tnMxnPortInfoEntry OBJECT-TYPE
        SYNTAX         TnMxnPortInfoEntry
        MAX-ACCESS     not-accessible
        STATUS         current
        DESCRIPTION    "."
        INDEX { ifIndex }
        ::= { tnMxnPortInfoTable 1 }

    TnMxnPortInfoEntry ::=
        SEQUENCE {
            tnMxnPortInfoAddInsertionLossToSig1        Unsigned32,
            tnMxnPortInfoAddInsertionLossToSig2        Unsigned32,
            tnMxnPortInfoAddInsertionLossToSig3        Unsigned32,
            tnMxnPortInfoAddInsertionLossToSig4        Unsigned32,
            tnMxnPortInfoAddInsertionLossToSig5        Unsigned32,
            tnMxnPortInfoAddInsertionLossToSig6        Unsigned32,
            tnMxnPortInfoAddInsertionLossToSig7        Unsigned32,
            tnMxnPortInfoAddInsertionLossToSig8        Unsigned32,
            tnMxnPortInfoInputPower                    Integer32,
            tnMxnPortInfoOutputPower                   Integer32,
            tnMxnPortInfoDropInsertionLossFromSig1     Unsigned32,
            tnMxnPortInfoDropInsertionLossFromSig2     Unsigned32,
            tnMxnPortInfoDropInsertionLossFromSig3     Unsigned32,
            tnMxnPortInfoDropInsertionLossFromSig4     Unsigned32,
            tnMxnPortInfoDropInsertionLossFromSig5     Unsigned32,
            tnMxnPortInfoDropInsertionLossFromSig6     Unsigned32,
            tnMxnPortInfoDropInsertionLossFromSig7     Unsigned32,
            tnMxnPortInfoDropInsertionLossFromSig8     Unsigned32,
            tnMxnPortInfoAddTargetPower                Unsigned32,
            tnMxnPortInfoPlannedFrequencyLowLimitOut   Integer32,
            tnMxnPortInfoPlannedFrequencyHighLimitOut  Integer32,
            tnMxnPortInfoPlannedFrequencyLowLimitIn    Integer32,
            tnMxnPortInfoPlannedFrequencyHighLimitIn   Integer32,
            tnMxnPortInfoAddExpectedPower              Integer32,
            tnMxnPortInfoExpectedPowerDev              Unsigned32
        }

    tnMxnPortInfoAddInsertionLossToSig1 OBJECT-TYPE
        SYNTAX         Unsigned32
        UNITS          "mB"
        MAX-ACCESS     read-only
        STATUS         current
        DESCRIPTION    "Insertion loss to port SIG1 when disposed to this path.
                        Add direction."
        ::= { tnMxnPortInfoEntry 1 }

    tnMxnPortInfoAddInsertionLossToSig2 OBJECT-TYPE
        SYNTAX         Unsigned32
        UNITS          "mB"
        MAX-ACCESS     read-only
        STATUS         current
        DESCRIPTION    "Insertion loss to port SIG2 when disposed to this path.
                        Add direction."
        ::= { tnMxnPortInfoEntry 2 }

    tnMxnPortInfoAddInsertionLossToSig3 OBJECT-TYPE
        SYNTAX         Unsigned32
        UNITS          "mB"
        MAX-ACCESS     read-only
        STATUS         current
        DESCRIPTION    "Insertion loss to port SIG3 when disposed to this path.
                        Add direction."
        ::= { tnMxnPortInfoEntry 3 }

    tnMxnPortInfoAddInsertionLossToSig4 OBJECT-TYPE
        SYNTAX         Unsigned32
        UNITS          "mB"
        MAX-ACCESS     read-only
        STATUS         current
        DESCRIPTION    "Insertion loss to port SIG4 when disposed to this path.
                        Add direction."
        ::= { tnMxnPortInfoEntry 4 }

    tnMxnPortInfoAddInsertionLossToSig5 OBJECT-TYPE
        SYNTAX         Unsigned32
        UNITS          "mB"
        MAX-ACCESS     read-only
        STATUS         current
        DESCRIPTION    "Insertion loss to port SIG5 when disposed to this path.
                        Add direction."
        ::= { tnMxnPortInfoEntry 5 }

    tnMxnPortInfoAddInsertionLossToSig6 OBJECT-TYPE
        SYNTAX         Unsigned32
        UNITS          "mB"
        MAX-ACCESS     read-only
        STATUS         current
        DESCRIPTION    "Insertion loss to port SIG6 when disposed to this path.
                        Add direction."
        ::= { tnMxnPortInfoEntry 6 }

    tnMxnPortInfoAddInsertionLossToSig7 OBJECT-TYPE
        SYNTAX         Unsigned32
        UNITS          "mB"
        MAX-ACCESS     read-only
        STATUS         current
        DESCRIPTION    "Insertion loss to port SIG7 when disposed to this path.
                        Add direction."
        ::= { tnMxnPortInfoEntry 7 }

    tnMxnPortInfoAddInsertionLossToSig8 OBJECT-TYPE
        SYNTAX         Unsigned32
        UNITS          "mB"
        MAX-ACCESS     read-only
        STATUS         current
        DESCRIPTION    "Insertion loss to port SIG8 when disposed to this path.
                        Add direction."
        ::= { tnMxnPortInfoEntry 8 }

    tnMxnPortInfoInputPower OBJECT-TYPE
        SYNTAX         Integer32
        UNITS          "mBm"
        MAX-ACCESS     read-only
        STATUS         current
        DESCRIPTION    "."
        ::= { tnMxnPortInfoEntry 9 }

    tnMxnPortInfoOutputPower OBJECT-TYPE
        SYNTAX         Integer32
        UNITS          "mBm"
        MAX-ACCESS     read-only
        STATUS         current
        DESCRIPTION    "."
        ::= { tnMxnPortInfoEntry 10 }

    tnMxnPortInfoDropInsertionLossFromSig1 OBJECT-TYPE
        SYNTAX         Unsigned32
        UNITS          "mB"
        MAX-ACCESS     read-only
        STATUS         current
        DESCRIPTION    "Insertion loss from port SIG1 when disposed to this path.
                        Drop direction."
        ::= { tnMxnPortInfoEntry 11 }

    tnMxnPortInfoDropInsertionLossFromSig2 OBJECT-TYPE
        SYNTAX         Unsigned32
        UNITS          "mB"
        MAX-ACCESS     read-only
        STATUS         current
        DESCRIPTION    "Insertion loss from port SIG2 when disposed to this path.
                        Drop direction."
        ::= { tnMxnPortInfoEntry 12 }

    tnMxnPortInfoDropInsertionLossFromSig3 OBJECT-TYPE
        SYNTAX         Unsigned32
        UNITS          "mB"
        MAX-ACCESS     read-only
        STATUS         current
        DESCRIPTION    "Insertion loss from port SIG3 when disposed to this path.
                        Drop direction."
        ::= { tnMxnPortInfoEntry 13 }

    tnMxnPortInfoDropInsertionLossFromSig4 OBJECT-TYPE
        SYNTAX         Unsigned32
        UNITS          "mB"
        MAX-ACCESS     read-only
        STATUS         current
        DESCRIPTION    "Insertion loss from port SIG4 when disposed to this path.
                        Drop direction."
        ::= { tnMxnPortInfoEntry 14 }

    tnMxnPortInfoDropInsertionLossFromSig5 OBJECT-TYPE
        SYNTAX         Unsigned32
        UNITS          "mB"
        MAX-ACCESS     read-only
        STATUS         current
        DESCRIPTION    "Insertion loss from port SIG5 when disposed to this path.
                        Drop direction."
        ::= { tnMxnPortInfoEntry 15 }

    tnMxnPortInfoDropInsertionLossFromSig6 OBJECT-TYPE
        SYNTAX         Unsigned32
        UNITS          "mB"
        MAX-ACCESS     read-only
        STATUS         current
        DESCRIPTION    "Insertion loss from port SIG6 when disposed to this path.
                        Drop direction."
        ::= { tnMxnPortInfoEntry 16 }

    tnMxnPortInfoDropInsertionLossFromSig7 OBJECT-TYPE
        SYNTAX         Unsigned32
        UNITS          "mB"
        MAX-ACCESS     read-only
        STATUS         current
        DESCRIPTION    "Insertion loss from port SIG7 when disposed to this path.
                        Drop direction."
        ::= { tnMxnPortInfoEntry 17 }

    tnMxnPortInfoDropInsertionLossFromSig8 OBJECT-TYPE
        SYNTAX         Unsigned32
        UNITS          "mB"
        MAX-ACCESS     read-only
        STATUS         current
        DESCRIPTION    "Insertion loss from port SIG8 when disposed to this path.
                        Drop direction.."
        ::= { tnMxnPortInfoEntry 18 }

    tnMxnPortInfoAddTargetPower OBJECT-TYPE
        SYNTAX         Unsigned32
        UNITS          "mB"
        MAX-ACCESS     read-only
        STATUS         current
        DESCRIPTION    "."
        ::= { tnMxnPortInfoEntry 19 }

    tnMxnPortInfoPlannedFrequencyLowLimitOut OBJECT-TYPE
        SYNTAX         Integer32
        UNITS          "MHz"
        MAX-ACCESS     read-only
        STATUS         current
        DESCRIPTION    "Planned Frequency Low Limit Out.
                        Value in Mhz, which follows additional calculation:
                        (<number>*10 + 100000)*1000
                        (i.e.) (9130.625*10+100000)*1000 = 191306250."
        ::= { tnMxnPortInfoEntry 20 }

    tnMxnPortInfoPlannedFrequencyHighLimitOut OBJECT-TYPE
        SYNTAX         Integer32
        UNITS          "MHz"
        MAX-ACCESS     read-only
        STATUS         current
        DESCRIPTION    "Planned Frequency High Limit Out.
                        Value in Mhz, which follows additional calculation:
                        (<number>*10 + 100000)*1000
                        (i.e.) (9130.625*10+100000)*1000 = 191306250."
        ::= { tnMxnPortInfoEntry 21 }

    tnMxnPortInfoPlannedFrequencyLowLimitIn OBJECT-TYPE
        SYNTAX         Integer32
        UNITS          "MHz"
        MAX-ACCESS     read-only
        STATUS         current
        DESCRIPTION    "Planned Frequency Low Limit In.
                        Value in Mhz, which follows additional calculation:
                        (<number>*10 + 100000)*1000
                        (i.e.) (9130.625*10+100000)*1000 = 191306250."
        ::= { tnMxnPortInfoEntry 22 }

    tnMxnPortInfoPlannedFrequencyHighLimitIn OBJECT-TYPE
        SYNTAX         Integer32
        UNITS          "MHz"
        MAX-ACCESS     read-only
        STATUS         current
        DESCRIPTION    "Planned Frequency High Limit In.
                        Value in Mhz, which follows additional calculation:
                        (<number>*10 + 100000)*1000
                        (i.e.) (9130.625*10+100000)*1000 = 191306250."
        ::= { tnMxnPortInfoEntry 23 }

    tnMxnPortInfoAddExpectedPower OBJECT-TYPE
        SYNTAX         Integer32
        MAX-ACCESS     read-only
        STATUS         current
        DESCRIPTION    "."
        ::= { tnMxnPortInfoEntry 24 }

    tnMxnPortInfoExpectedPowerDev OBJECT-TYPE
        SYNTAX         Unsigned32
        MAX-ACCESS     read-only
        STATUS         current
        DESCRIPTION    "."
        ::= { tnMxnPortInfoEntry 25 }

--------------------------------------------------------------------------------
-- ASC Optical Port Info Scalar
--------------------------------------------------------------------------------
    tnAscPortInfoAttributeTotal OBJECT-TYPE
        SYNTAX         Integer32
        MAX-ACCESS     read-only
        STATUS         current
        DESCRIPTION    "."
        ::= { tnOpticalPortInfo 513 }

--------------------------------------------------------------------------------
-- ASC Optical Port Info Table
--------------------------------------------------------------------------------
    tnAscPortInfoTable OBJECT-TYPE
        SYNTAX         SEQUENCE OF TnAscPortInfoEntry
        MAX-ACCESS     not-accessible
        STATUS         current
        DESCRIPTION    "The ports on a ASC optical card."
        ::= { tnOpticalPortInfo 514 }

    tnAscPortInfoEntry OBJECT-TYPE
        SYNTAX         TnAscPortInfoEntry
        MAX-ACCESS     not-accessible
        STATUS         current
        DESCRIPTION    "."
        INDEX { ifIndex }
        ::= { tnAscPortInfoTable 1 }

    TnAscPortInfoEntry ::=
        SEQUENCE {
            tnAscPortInfoTotalInputPower               Integer32,
            tnAscPortInfoLosMode                       INTEGER,
            tnAscPortInfoChanInputPower                Integer32,
            tnAscPortInfoTotalOutputPower              Integer32,
            tnAscPortInfoPowerGain                     Integer32,
            tnAscPortInfoSignalPowerOut                Integer32,
            tnAscPortInfoOAMPumpTemperature            Integer32,
            tnAscPortInfoOAMPumpBiases                 SnmpAdminString,
            tnAscPortInfoEnable                        Integer32,
            tnAscPortInfoPlannedFrequencyIn            Integer32,
            tnAscPortInfoPlannedFrequencyOut           Integer32,
            tnAscPortInfoPlannedFrequencyLowLimitOut   Integer32,
            tnAscPortInfoPlannedFrequencyHighLimitOut  Integer32,
            tnAscPortInfoPlannedFrequencyLowLimitIn    Integer32,
            tnAscPortInfoPlannedFrequencyHighLimitIn   Integer32,
            tnAscPortInfoChanTargetPower               Integer32,
            tnAscPortInfoExpectedPowerDev              Unsigned32,
            tnAscPortInfoVoaCurrent                    Unsigned32,
            tnAscPortInputToOutputGain                 Integer32
        }

    tnAscPortInfoTotalInputPower OBJECT-TYPE
        SYNTAX         Integer32
        UNITS          "mBm"
        MAX-ACCESS     read-only
        STATUS         current
        DESCRIPTION    "."
        ::= { tnAscPortInfoEntry 1 }

    tnAscPortInfoLosMode OBJECT-TYPE
        SYNTAX         INTEGER {
                         auto(1),
                         losN(2)
                       }
        MAX-ACCESS     read-only
        STATUS         current
        DESCRIPTION    "The LOS mode of the amplifier."
        DEFVAL         { losN }
        ::= { tnAscPortInfoEntry 2 }

    tnAscPortInfoChanInputPower OBJECT-TYPE
        SYNTAX         Integer32
        UNITS          "mBm"
        MAX-ACCESS     read-only
        STATUS         current
        DESCRIPTION    "."
        ::= { tnAscPortInfoEntry 3 }

    tnAscPortInfoTotalOutputPower OBJECT-TYPE
        SYNTAX         Integer32
        UNITS          "mBm"
        MAX-ACCESS     read-only
        STATUS         current
        DESCRIPTION    "Total Output Power band."
        DEFVAL         { -9900 }
        ::= { tnAscPortInfoEntry 4 }

    tnAscPortInfoPowerGain OBJECT-TYPE
        SYNTAX         Integer32
        UNITS          "mB"
        MAX-ACCESS     read-only
        STATUS         current
        DESCRIPTION    "."
        ::= { tnAscPortInfoEntry 5 }

    tnAscPortInfoSignalPowerOut OBJECT-TYPE
        SYNTAX         Integer32
        UNITS          "mBm"
        MAX-ACCESS     read-only
        STATUS         current
        DESCRIPTION    "."
        ::= { tnAscPortInfoEntry 6 }

    tnAscPortInfoOAMPumpTemperature OBJECT-TYPE
        SYNTAX         Integer32
        UNITS          "Celcius"
        MAX-ACCESS     read-only
        STATUS         current
        DESCRIPTION    "The pump temperature."
        ::= { tnAscPortInfoEntry 7 }

    tnAscPortInfoOAMPumpBiases OBJECT-TYPE
        SYNTAX         SnmpAdminString (SIZE(0..512))
        MAX-ACCESS     read-only
        STATUS         current
        DESCRIPTION    "."
        ::= { tnAscPortInfoEntry 8 }

    tnAscPortInfoEnable OBJECT-TYPE
        SYNTAX         Integer32
        MAX-ACCESS     read-only
        STATUS         current
        DESCRIPTION    "."
        ::= { tnAscPortInfoEntry 9 }

    tnAscPortInfoPlannedFrequencyIn OBJECT-TYPE
        SYNTAX         Integer32
        UNITS          "MHz"
        MAX-ACCESS     read-only
        STATUS         current
        DESCRIPTION    "Planned Center Frequency In.
                        Value in Mhz, which follows additional calculation:
                        (<number>*10 + 100000)*1000
                        (i.e.) (9130.625*10+100000)*1000 = 191306250."
        ::= { tnAscPortInfoEntry 10 }

    tnAscPortInfoPlannedFrequencyOut OBJECT-TYPE
        SYNTAX         Integer32
        UNITS          "MHz"
        MAX-ACCESS     read-only
        STATUS         current
        DESCRIPTION    "Planned Center Frequency Out.
                        Value in Mhz, which follows additional calculation:
                        (<number>*10 + 100000)*1000
                        (i.e.) (9130.625*10+100000)*1000 = 191306250."
        ::= { tnAscPortInfoEntry 11 }

    tnAscPortInfoPlannedFrequencyLowLimitOut OBJECT-TYPE
        SYNTAX         Integer32
        UNITS          "MHz"
        MAX-ACCESS     read-only
        STATUS         current
        DESCRIPTION    "Planned Frequency Low Limit Out.
                        Value in Mhz, which follows additional calculation:
                        (<number>*10 + 100000)*1000
                        (i.e.) (9130.625*10+100000)*1000 = 191306250."
        ::= { tnAscPortInfoEntry 12 }

    tnAscPortInfoPlannedFrequencyHighLimitOut OBJECT-TYPE
        SYNTAX         Integer32
        UNITS          "MHz"
        MAX-ACCESS     read-only
        STATUS         current
        DESCRIPTION    "Planned Frequency High Limit Out.
                        Value in Mhz, which follows additional calculation:
                        (<number>*10 + 100000)*1000
                        (i.e.) (9130.625*10+100000)*1000 = 191306250."
        ::= { tnAscPortInfoEntry 13 }

    tnAscPortInfoPlannedFrequencyLowLimitIn OBJECT-TYPE
        SYNTAX         Integer32
        UNITS          "MHz"
        MAX-ACCESS     read-only
        STATUS         current
        DESCRIPTION    "Planned Frequency Low Limit In.
                        Value in Mhz, which follows additional calculation:
                        (<number>*10 + 100000)*1000
                        (i.e.) (9130.625*10+100000)*1000 = 191306250."
        ::= { tnAscPortInfoEntry 14 }

    tnAscPortInfoPlannedFrequencyHighLimitIn OBJECT-TYPE
        SYNTAX         Integer32
        UNITS          "MHz"
        MAX-ACCESS     read-only
        STATUS         current
        DESCRIPTION    "Planned Frequency High Limit In.
                        Value in Mhz, which follows additional calculation:
                        (<number>*10 + 100000)*1000
                        (i.e.) (9130.625*10+100000)*1000 = 191306250."
        ::= { tnAscPortInfoEntry 15 }

    tnAscPortInfoChanTargetPower OBJECT-TYPE
        SYNTAX         Integer32
        UNITS          "mBm"
        MAX-ACCESS     read-only
        STATUS         current
        DESCRIPTION    "."
        ::= { tnAscPortInfoEntry 16 }

    tnAscPortInfoExpectedPowerDev OBJECT-TYPE
        SYNTAX         Unsigned32
        MAX-ACCESS     read-only
        STATUS         current
        DESCRIPTION    "."
        ::= { tnAscPortInfoEntry 17 }

    tnAscPortInfoVoaCurrent OBJECT-TYPE
        SYNTAX         Unsigned32
        MAX-ACCESS     read-only
        STATUS         current
        DESCRIPTION    "."
        ::= { tnAscPortInfoEntry 18 }

    tnAscPortInputToOutputGain OBJECT-TYPE
        SYNTAX         Integer32
        UNITS          "mB"
        MAX-ACCESS     read-only
        STATUS         current
        DESCRIPTION    "."
        ::= { tnAscPortInfoEntry 19 }

--------------------------------------------------------------------------------
-- OPSUM Optical Port Info Scalar
--------------------------------------------------------------------------------
    tnOpsumPortInfoAttributeTotal OBJECT-TYPE
        SYNTAX         Integer32
        MAX-ACCESS     read-only
        STATUS         current
        DESCRIPTION    "."
        ::= { tnOpticalPortInfo 515 }

--------------------------------------------------------------------------------
-- OPSUM Optical Port Info Table
--------------------------------------------------------------------------------
    tnOpsumPortInfoTable OBJECT-TYPE
        SYNTAX         SEQUENCE OF TnOpsumPortInfoEntry
        MAX-ACCESS     not-accessible
        STATUS         current
        DESCRIPTION    "The ports on an Opsum card."
        ::= { tnOpticalPortInfo 516 }

    tnOpsumPortInfoEntry OBJECT-TYPE
        SYNTAX         TnOpsumPortInfoEntry
        MAX-ACCESS     not-accessible
        STATUS         current
        DESCRIPTION    "."
        INDEX { ifIndex }
        ::= { tnOpsumPortInfoTable 1 }

    TnOpsumPortInfoEntry ::=
        SEQUENCE {
            tnOpsumPortInfoFunction     INTEGER
        }

    tnOpsumPortInfoFunction OBJECT-TYPE
        SYNTAX         INTEGER {
                         signal(1),
                         workingProtected(2)
                       }
        MAX-ACCESS     read-only
        STATUS         current
        DESCRIPTION    "Indicates the functional type of this Opsum port."
        ::= { tnOpsumPortInfoEntry 1 }

--------------------------------------------------------------------------------
-- MXN1624 Optical Port Info Scalar
--------------------------------------------------------------------------------
    tnMxn1624PortInfoAttributeTotal OBJECT-TYPE
        SYNTAX         Integer32
        MAX-ACCESS     read-only
        STATUS         current
        DESCRIPTION    "."
        ::= { tnOpticalPortInfo 517 }

--------------------------------------------------------------------------------
-- MXN1624 Optical Port Info Table
--------------------------------------------------------------------------------
    tnMxn1624PortInfoTable OBJECT-TYPE
        SYNTAX         SEQUENCE OF TnMxn1624PortInfoEntry
        MAX-ACCESS     not-accessible
        STATUS         current
        DESCRIPTION    "The ports on a MXN1624 optical card."
        ::= { tnOpticalPortInfo 518 }

    tnMxn1624PortInfoEntry OBJECT-TYPE
        SYNTAX         TnMxn1624PortInfoEntry
        MAX-ACCESS     not-accessible
        STATUS         current
        DESCRIPTION    "."
        INDEX { ifIndex }
        ::= { tnMxn1624PortInfoTable 1 }

    TnMxn1624PortInfoEntry ::=
        SEQUENCE {
            tnMxn1624PortInfoFunction     INTEGER
        }

    tnMxn1624PortInfoFunction OBJECT-TYPE
        SYNTAX         INTEGER {
                         sig(1),
                         ad(2),
                         lpbk(3),
                         tl(4),
                         fsm(5)
                       }
        MAX-ACCESS     read-only
        STATUS         current
        DESCRIPTION    "Indicates the functional type of this MXN1624 port."
        ::= { tnMxn1624PortInfoEntry 1 }

--------------------------------------------------------------------------------
-- IR4 Optical Port Info Scalar
--------------------------------------------------------------------------------
    tnIr4PortInfoAttributeTotal OBJECT-TYPE
        SYNTAX         Integer32
        MAX-ACCESS     read-only
        STATUS         current
        DESCRIPTION    "."
        ::= { tnOpticalPortInfo 519 }

--------------------------------------------------------------------------------
-- IR4 Optical Port Info Table
--------------------------------------------------------------------------------
    tnIr4PortInfoTable OBJECT-TYPE
        SYNTAX         SEQUENCE OF TnIr4PortInfoEntry
        MAX-ACCESS     not-accessible
        STATUS         current
        DESCRIPTION    "The ports on a IR4 optical card."
        ::= { tnOpticalPortInfo 520 }

    tnIr4PortInfoEntry OBJECT-TYPE
        SYNTAX         TnIr4PortInfoEntry
        MAX-ACCESS     not-accessible
        STATUS         current
        DESCRIPTION    "."
        INDEX { ifIndex }
        ::= { tnIr4PortInfoTable 1 }

    TnIr4PortInfoEntry ::=
        SEQUENCE {
            tnIr4PortInfoFunction     INTEGER
        }

    tnIr4PortInfoFunction OBJECT-TYPE
        SYNTAX         INTEGER {
                         lineIn(1),
                         inv(2),
                         osc(3),
                         lineOut(4),
                         oscSfp(5),
                         adt(6),
                         otdrRx(7),
                         otdrTx(8),
                         custLan(9)
                       }
        MAX-ACCESS     read-only
        STATUS         current
        DESCRIPTION    "Indicates the functional type of this IR4 port."
        ::= { tnIr4PortInfoEntry 1 }

--------------------------------------------------------------------------------
-- ASC2 Optical Port Info Scalar
--------------------------------------------------------------------------------
    tnAsc2PortInfoAttributeTotal OBJECT-TYPE
        SYNTAX         Integer32
        MAX-ACCESS     read-only
        STATUS         current
        DESCRIPTION    "."
        ::= { tnOpticalPortInfo 521 }

--------------------------------------------------------------------------------
-- ASC2 Optical Port Info Table
--------------------------------------------------------------------------------
    tnAsc2PortInfoTable OBJECT-TYPE
        SYNTAX         SEQUENCE OF TnAsc2PortInfoEntry
        MAX-ACCESS     not-accessible
        STATUS         current
        DESCRIPTION    "The ports on an ASC2 optical card."
        ::= { tnOpticalPortInfo 522 }

    tnAsc2PortInfoEntry OBJECT-TYPE
        SYNTAX         TnAsc2PortInfoEntry
        MAX-ACCESS     not-accessible
        STATUS         current
        DESCRIPTION    "."
        INDEX { ifIndex }
        ::= { tnAsc2PortInfoTable 1 }

    TnAsc2PortInfoEntry ::=
        SEQUENCE {
            tnAsc2PortInfoFunction     INTEGER
        }

    tnAsc2PortInfoFunction OBJECT-TYPE
        SYNTAX         INTEGER {
                         sigAIn(1),
                         aOut(2),
                         sigAOut(3),
                         aIn(4),
                         sigBIn(5),
                         bOut(6),
                         sigBOut(7),
                         bIn(8),
                         sigCIn(9),
                         cOut(10),
                         sigCOut(11),
                         cIn(12),
                         sigDIn(13),
                         dOut(14),
                         sigDOut(15),
                         dIn(16),
                         sigEIn(17),
                         eOut(18),
                         sigEOut(19),
                         eIn(20),
                         sigFIn(21),
                         fOut(22),
                         sigFOut(23),
                         fIn(24)
                       }
        MAX-ACCESS     read-only
        STATUS         current
        DESCRIPTION    "Indicates the functional type of this ASC2 port."
        ::= { tnAsc2PortInfoEntry 1 }

--------------------------------------------------------------------------------
-- SFD48 Optical Port Info Scalar
--------------------------------------------------------------------------------
    tnSfd48PortInfoAttributeTotal OBJECT-TYPE
        SYNTAX         Integer32
        MAX-ACCESS     read-only
        STATUS         current
        DESCRIPTION    "."
        ::= { tnOpticalPortInfo 523 }

--------------------------------------------------------------------------------
-- SFD48 Optical Port Info Table
--------------------------------------------------------------------------------
    tnSfd48PortInfoTable OBJECT-TYPE
        SYNTAX         SEQUENCE OF TnSfd48PortInfoEntry
        MAX-ACCESS     not-accessible
        STATUS         current
        DESCRIPTION    "The ports on a SFD48 optical card."
        ::= { tnOpticalPortInfo 524 }

    tnSfd48PortInfoEntry OBJECT-TYPE
        SYNTAX         TnSfd48PortInfoEntry
        MAX-ACCESS     not-accessible
        STATUS         current
        DESCRIPTION    "."
        INDEX { ifIndex }
        ::= { tnSfd48PortInfoTable 1 }

    TnSfd48PortInfoEntry ::=
        SEQUENCE {
            tnSfd48PortInfoFunction     INTEGER
        }

    tnSfd48PortInfoFunction OBJECT-TYPE
        SYNTAX         INTEGER {
                         channel(1),
                         mux(2)
                       }
        MAX-ACCESS     read-only
        STATUS         current
        DESCRIPTION    "Indicates the functional type of this SFD48 port."
        ::= { tnSfd48PortInfoEntry 1 }

--------------------------------------------------------------------------------
-- SFD64 Optical Port Info Scalar
--------------------------------------------------------------------------------
    tnSfd64PortInfoAttributeTotal OBJECT-TYPE
        SYNTAX         Integer32
        MAX-ACCESS     read-only
        STATUS         current
        DESCRIPTION    "."
        ::= { tnOpticalPortInfo 525 }

--------------------------------------------------------------------------------
-- SFD64 Optical Port Info Table
--------------------------------------------------------------------------------
    tnSfd64PortInfoTable OBJECT-TYPE
        SYNTAX         SEQUENCE OF TnSfd64PortInfoEntry
        MAX-ACCESS     not-accessible
        STATUS         current
        DESCRIPTION    "The ports on a SFD64 optical card."
        ::= { tnOpticalPortInfo 526 }

    tnSfd64PortInfoEntry OBJECT-TYPE
        SYNTAX         TnSfd64PortInfoEntry
        MAX-ACCESS     not-accessible
        STATUS         current
        DESCRIPTION    "."
        INDEX { ifIndex }
        ::= { tnSfd64PortInfoTable 1 }

    TnSfd64PortInfoEntry ::=
        SEQUENCE {
            tnSfd64PortInfoFunction     INTEGER
        }

    tnSfd64PortInfoFunction OBJECT-TYPE
        SYNTAX         INTEGER {
                         channel(1),
                         mux(2)
                       }
        MAX-ACCESS     read-only
        STATUS         current
        DESCRIPTION    "Indicates the functional type of this SFD64 port."
        ::= { tnSfd64PortInfoEntry 1 }

--------------------------------------------------------------------------------
-- IR32AW Optical Port Info Scalar
--------------------------------------------------------------------------------
    tnIr32AWPortInfoAttributeTotal OBJECT-TYPE
        SYNTAX         Integer32
        MAX-ACCESS     read-only
        STATUS         current
        DESCRIPTION    "."
        ::= { tnOpticalPortInfo 527 }

--------------------------------------------------------------------------------
-- IR32AW Optical Port Info Table
--------------------------------------------------------------------------------
    tnIr32AWPortInfoTable OBJECT-TYPE
        SYNTAX         SEQUENCE OF TnIr32AWPortInfoEntry
        MAX-ACCESS     not-accessible
        STATUS         current
        DESCRIPTION    "The ports on a IR32AW optical card."
        ::= { tnOpticalPortInfo 528 }

    tnIr32AWPortInfoEntry OBJECT-TYPE
        SYNTAX         TnIr32AWPortInfoEntry
        MAX-ACCESS     not-accessible
        STATUS         current
        DESCRIPTION    "."
        INDEX { ifIndex }
        ::= { tnIr32AWPortInfoTable 1 }

    TnIr32AWPortInfoEntry ::=
        SEQUENCE {
            tnIr32AWPortInfoFunction INTEGER
        }

    tnIr32AWPortInfoFunction OBJECT-TYPE
        SYNTAX         INTEGER {
                         lineIn(1),
                         inv(2),
                         osc(3),
                         lineOut(4),
                         oscSfp(5),
                         adt(6),
                         lineLoading(7),
                         otdr(8),
                         custLan(9),
                         testLaser(10),
                         mpoFs(11),
                         oscLan(12)
                       }
        MAX-ACCESS     read-only
        STATUS         current
        DESCRIPTION    "Indicates the functional type of this IR32AW port."
        ::= { tnIr32AWPortInfoEntry 1 }

-------------------------------------------------------------------------------
-- EILAAW Optical Port Info Scalar
-------------------------------------------------------------------------------
    tnEilaAWPortInfoAttributeTotal OBJECT-TYPE
        SYNTAX         Integer32
        MAX-ACCESS     read-only
        STATUS         current
        DESCRIPTION    "."
        ::= { tnOpticalPortInfo 529 }

-------------------------------------------------------------------------------
-- EILAAW Optical Port Info Table
-------------------------------------------------------------------------------
    tnEilaAWPortInfoTable OBJECT-TYPE
        SYNTAX         SEQUENCE OF TnEilaAWPortInfoEntry
        MAX-ACCESS     not-accessible
        STATUS         current
        DESCRIPTION    "The ports on a EILAAW optical card."
        ::= { tnOpticalPortInfo 530 }

    tnEilaAWPortInfoEntry OBJECT-TYPE
        SYNTAX         TnEilaAWPortInfoEntry
        MAX-ACCESS     not-accessible
        STATUS         current
        DESCRIPTION    "."
        INDEX { ifIndex }
        ::= { tnEilaAWPortInfoTable 1 }

    TnEilaAWPortInfoEntry ::=
        SEQUENCE {
            tnEilaAWPortInfoFunction INTEGER
        }

    tnEilaAWPortInfoFunction OBJECT-TYPE
        SYNTAX         INTEGER {
                         lineIn(1),
                         otdr(2),
                         lineOut(3),
                         oscSfp(4),
                         osc(5),
                         custLan(6),
                         inv(7),
                         oscLan(8)
                       }
        MAX-ACCESS     read-only
        STATUS         current
        DESCRIPTION    "Indicates the functional type of this EILAAW port."
        ::= { tnEilaAWPortInfoEntry 1 }

--------------------------------------------------------------------------------
-- 18CE300 Optical Port Info Scalar
--------------------------------------------------------------------------------
    tn18ce300PortInfoAttributeTotal OBJECT-TYPE
        SYNTAX         Integer32
        MAX-ACCESS     read-only
        STATUS         current
        DESCRIPTION    "."
        ::= { tnOpticalPortInfo 531 }

--------------------------------------------------------------------------------
 -- 18CE300 Optical Port Info Table
--------------------------------------------------------------------------------
    tn18ce300PortInfoTable OBJECT-TYPE
        SYNTAX         SEQUENCE OF Tn18ce300PortInfoEntry
        MAX-ACCESS     not-accessible
        STATUS         current
        DESCRIPTION    "The ports on a 18CE300 optical card."
        ::= { tnOpticalPortInfo 532 }

    tn18ce300PortInfoEntry OBJECT-TYPE
        SYNTAX         Tn18ce300PortInfoEntry
        MAX-ACCESS     not-accessible
        STATUS         current
        DESCRIPTION    "."
        INDEX { ifIndex }
        ::= { tn18ce300PortInfoTable 1 }

    Tn18ce300PortInfoEntry ::=
        SEQUENCE {
            tn18ce300PortInfoFunction INTEGER
        }

    tn18ce300PortInfoFunction OBJECT-TYPE
        SYNTAX         INTEGER {
                         network(1),
                         client(2),
                         backplane(3),
                         ethman(4)
                       }
        MAX-ACCESS     read-only
        STATUS         current
        DESCRIPTION    "Indicates the functional type of this 18CE300 port."
        ::= { tn18ce300PortInfoEntry 1 }

--------------------------------------------------------------------------------
-- OPSUML Optical Port Info Scalar
--------------------------------------------------------------------------------
    tnOpsumlPortInfoAttributeTotal OBJECT-TYPE
        SYNTAX         Integer32
        MAX-ACCESS     read-only
        STATUS         current
        DESCRIPTION    "."
        ::= { tnOpticalPortInfo 533 }

--------------------------------------------------------------------------------
-- OPSUML Optical Port Info Table
--------------------------------------------------------------------------------
    tnOpsumlPortInfoTable OBJECT-TYPE
        SYNTAX         SEQUENCE OF TnOpsumPortInfoEntry
        MAX-ACCESS     not-accessible
        STATUS         current
        DESCRIPTION    "The ports on an Opsuml card."
        ::= { tnOpticalPortInfo 534 }

    tnOpsumlPortInfoEntry OBJECT-TYPE
        SYNTAX         TnOpsumlPortInfoEntry
        MAX-ACCESS     not-accessible
        STATUS         current
        DESCRIPTION    "."
        INDEX { ifIndex }
        ::= { tnOpsumlPortInfoTable 1 }

    TnOpsumlPortInfoEntry ::=
        SEQUENCE {
            tnOpsumlPortInfoFunction     INTEGER
        }

    tnOpsumlPortInfoFunction OBJECT-TYPE
        SYNTAX         INTEGER {
                         signal(1),
                         workingProtected(2)
                       }
        MAX-ACCESS     read-only
        STATUS         current
        DESCRIPTION    "Indicates the functional type of this Opsuml port."
        ::= { tnOpsumlPortInfoEntry 1 }

--    obsolete
--    tnBbaHgPortLcConfigAttributeTotal OBJECT-TYPE ::= { tnOpticalPortLcConfig 1 }
--    tnBbaHgPortLcConfigTable          OBJECT-TYPE ::= { tnOpticalPortLcConfig 2 }
--    tnBbaLgPortLcConfigAttributeTotal OBJECT-TYPE ::= { tnOpticalPortLcConfig 3 }
--    tnBbaLgPortLcConfigTable          OBJECT-TYPE ::= { tnOpticalPortLcConfig 4 }

--------------------------------------------------------------------------------
-- Conformance Group Definitions
--------------------------------------------------------------------------------

--------------------------------------------------------------------------------
-- Obsoleted OIDs
--------------------------------------------------------------------------------
--    obsolete
--    tnOpticalPortScalarsGroup        OBJECT-GROUP ::= { tnOpticalPortGroups 1 }
--    tnOC48SwsPortScalarsGroup        OBJECT-GROUP ::= { tnOpticalPortGroups 2 }
--    tnSimpleOpticsPortScalarsGroup   OBJECT-GROUP ::= { tnOpticalPortGroups 3 }
--    tnOC48SwsUserNwPortScalarsGroup  OBJECT-GROUP ::= { tnOpticalPortGroups 4 }
--    tnOC48SwsUserNwPortGroup         OBJECT-GROUP ::= { tnOpticalPortGroups 5 }
--    tnBandFilterPortScalarsGroup     OBJECT-GROUP ::= { tnOpticalPortGroups 6 }
--    tnBandFilterPortGroup            OBJECT-GROUP ::= { tnOpticalPortGroups 7 }
--    tnOscPortScalarsGroup            OBJECT-GROUP ::= { tnOpticalPortGroups 8 }
--    tnOscPortGroup                   OBJECT-GROUP ::= { tnOpticalPortGroups 9 }
--    tnChannelFilterPortScalarsGroup  OBJECT-GROUP ::= { tnOpticalPortGroups 10 }
--    tnChannelFilterPortGroup         OBJECT-GROUP ::= { tnOpticalPortGroups 11 }
--    tnBbaLinePortScalarsGroup        OBJECT-GROUP ::= { tnOpticalPortGroups 12 }
--    tnBbaLinePortGroup               OBJECT-GROUP ::= { tnOpticalPortGroups 13 }
--    tnPpsPortScalarsGroup            OBJECT-GROUP ::= { tnOpticalPortGroups 14 }
--    tnPpsPortGroup                   OBJECT-GROUP ::= { tnOpticalPortGroups 15 }
--    tnOC192SwsUserNwPortScalarsGroup OBJECT-GROUP ::= { tnOpticalPortGroups 16 }
--    tnOC192SwsUserNwPortGroup        OBJECT-GROUP ::= { tnOpticalPortGroups 17 }
--    tn2x1GEoSWSPortScalarsGroup      OBJECT-GROUP ::= { tnOpticalPortGroups 18 }
--    tn2x1GEoSWSPortGroup             OBJECT-GROUP ::= { tnOpticalPortGroups 19 }
--    tnSonetPortScalarsGroup          OBJECT-GROUP ::= { tnOpticalPortGroups 20 }
--    tnSonetPortGroup                 OBJECT-GROUP ::= { tnOpticalPortGroups 21 }

    tnOpticalPortGroup OBJECT-GROUP
        OBJECTS {
            tnOpticalPortInsertionLoss
        }
        STATUS         current
        DESCRIPTION    "."
        ::= { tnOpticalPortGroups 22 }

--------------------------------------------------------------------------------
-- Obsoleted OIDs
--------------------------------------------------------------------------------
--    obsolete
--    tnRoadmPortScalarsGroup   OBJECT-GROUP ::= { tnOpticalPortGroups 23 }
--    tnRoadmPortGroup          OBJECT-GROUP ::= { tnOpticalPortGroups 24 }
--    tnWaveKeyPortScalarsGroup OBJECT-GROUP ::= { tnOpticalPortGroups 25 }

    tnWaveKeyPortGroup OBJECT-GROUP
        OBJECTS {
            tnWaveKeyPortUnexpectedWKThreshIngress,
            tnWaveKeyPortUnexpectedWKThreshEgress,
            tnWaveKeyPortUnexpectedWKThreshAutoModeIngress,
            tnWaveKeyPortUnexpectedWKThreshAutoModeEgress,
            tnWaveKeyPortUnexpectedWKThreshDeltaIngress,
            tnWaveKeyPortUnexpectedWKThreshDeltaEgress,
            tnWaveKeyPortPresentUnexpectedWKThreshIngress,
            tnWaveKeyPortPresentUnexpectedWKThreshEgress,
            tnWaveKeyPortSupportedDirections,
            tnWaveKeyPortUnexpectedWKThreshAutoMaxOffsetIn,
            tnWaveKeyPortUnexpectedWKThreshAutoMaxOffsetOut,
            tnWaveKeyPortCommonEgressPower,
            tnWaveKeyPortCommonIngressPower,
            tnWaveKeyPortDefaultPowerDeviationIn,
            tnWaveKeyPortDefaultPowerDeviationOut,
            tnWaveKeyPortDefaultPowerDeviationInL,
            tnWaveKeyPortDefaultPowerDeviationOutL,
            tnWaveKeyPortCommonEgressPowerL
        }
        STATUS         current
        DESCRIPTION    "."
        ::= { tnOpticalPortGroups 26 }

--------------------------------------------------------------------------------
-- Obsoleted OIDs
--------------------------------------------------------------------------------
--    obsolete
--    tn10GELANPortScalarsGroup OBJECT-GROUP ::= { tnOpticalPortGroups 27 }
--    tn10GELANPortGroup        OBJECT-GROUP ::= { tnOpticalPortGroups 28 }

    tnOpticalFiberGroup OBJECT-GROUP
        OBJECTS {
            tnOpticalFiberFixedLoss,
            tnOpticalFiberLength,
            tnOpticalFiberLossRating,
            tnOpticalFiberDispersionRating
        }
        STATUS         current
        DESCRIPTION    "."
        ::= { tnOpticalPortGroups 29 }

--------------------------------------------------------------------------------
-- Obsoleted OIDs
--------------------------------------------------------------------------------
--    obsolete
--    tnChannelAddDropPortScalarsGroup OBJECT-GROUP ::= { tnOpticalPortGroups 30 }
--    tnChannelAddDropPortGroup        OBJECT-GROUP ::= { tnOpticalPortGroups 31 }
--    tnQuadOC48MuxPortScalarsGroup    OBJECT-GROUP ::= { tnOpticalPortGroups 32 }
--    tnQuadOC48MuxPortGroup           OBJECT-GROUP ::= { tnOpticalPortGroups 33 }
--    tnBbaLowGainPortScalarsGroup     OBJECT-GROUP ::= { tnOpticalPortGroups 34 }
--    tnBbaLowGainPortGroup            OBJECT-GROUP ::= { tnOpticalPortGroups 35 }

    tnLoopbackPortGroup OBJECT-GROUP
        OBJECTS {
            tnLoopbackPortDLEB,
            tnLoopbackPortLLEB,
            tnLoopbackPortTSEB,
            tnLoopbackPortFacTwo
        }
        STATUS         current
        DESCRIPTION    "."
        ::= { tnOpticalPortGroups 36 }

--------------------------------------------------------------------------------
-- Obsoleted OIDs
--------------------------------------------------------------------------------
--    obsolete
--    tnDcmPortScalarsGroup OBJECT-GROUP ::= { tnOpticalPortGroups 37 }
--    tnDcmPortGroup        OBJECT-GROUP ::= { tnOpticalPortGroups 38 }

    tnInsertionLossPortGroup OBJECT-GROUP
        OBJECTS {
            tnInsertionLossPortEgress,
            tnInsertionLossPortIngress,
            tnInsertionLossPortEgressL,
            tnInsertionLossPortIngressL
        }
        STATUS         current
        DESCRIPTION    "."
        ::= { tnOpticalPortGroups 39 }

--------------------------------------------------------------------------------
-- Obsoleted OIDs
--------------------------------------------------------------------------------
--    obsolete
--    tnQuadOC3or12MuxPortScalarsGroup OBJECT-GROUP ::= { tnOpticalPortGroups 40 }
--    tnQuadOC3or12MuxPortGroup        OBJECT-GROUP ::= { tnOpticalPortGroups 41 }
--    tnDecaGigEMuxPortScalarsGroup    OBJECT-GROUP ::= { tnOpticalPortGroups 42 }
--    tnDecaGigEMuxPortGroup           OBJECT-GROUP ::= { tnOpticalPortGroups 43 }

    tnProtectionGroupPortGroup OBJECT-GROUP
        OBJECTS {
            tnProtectionGroupId
        }
        STATUS         current
        DESCRIPTION    "."
        ::= { tnOpticalPortGroups 44 }

    tnDTVPortGroup OBJECT-GROUP
        OBJECTS {
            tnDTVPortControl,
            tnDTVPortValueAmplitude,
            tnDTVPortValuePhase
        }
        STATUS         current
        DESCRIPTION    "."
        ::= { tnOpticalPortGroups 45 }

    tnPortInventoryGroup OBJECT-GROUP
        OBJECTS {
            tnPortInventoryCLEI,
            tnPortInventoryCompanyID,
            tnPortInventoryDate,
            tnPortInventoryExtraData,
            tnPortInventoryFactoryID,
            tnPortInventoryManufacturingPartNumber,
            tnPortInventoryMnemonic,
            tnPortInventorySerialNumber,
            tnPortInventorySWPartNumber
        }
        STATUS         current
        DESCRIPTION    "."
        ::= { tnOpticalPortGroups 46 }

    tnPortOtdrScanGroup OBJECT-GROUP
        OBJECTS {
            tnPortOtdrScanConnAddress,
            tnPortOtdrScanDescription,
            tnPortOtdrScanFileName,
            tnPortOtdrScanProfileId,
            tnPortOtdrScanAvgTime,
            tnPortOtdrScanPulseLength,
            tnPortOtdrScanRange,
            tnPortOtdrScanResolution,
            tnPortOtdrScanWaveLength,
            tnPortOtdrScanControl,
            tnPortOtdrScanStatus,
            tnPortOtdrScanResult,
            tnPortOtdrScanTimeRemaining,
            tnPortOtdrScanLastSuccessfulTimeStamp,
            tnPortOtdrScanEventThreshold,
            tnPortOtdrScanIOR,
            tnPortOtdrScanState,
            tnPortOtdrScanErrorType,
            tnPortOtdrScanErrorDetail,
            tnPortOtdrScanRequestTimeStamp
        }
        STATUS         current
        DESCRIPTION    "."
        ::= { tnOpticalPortGroups 47 }

    tnFlexgridOtsInfoGroup OBJECT-GROUP
        OBJECTS {
            tnFlexgridOtsInfoLineGranularityMHz,
            tnFlexgridOtsInfoCBandLowestFrequencyGHzOut,
            tnFlexgridOtsInfoCBandHighestFrequencyGHzOut,
            tnFlexgridOtsInfoCBandLowestFrequencyGHzIn,
            tnFlexgridOtsInfoCBandHighestFrequencyGHzIn,
            tnFlexgridOtsInfoLBandLowestFrequencyGHzOut,
            tnFlexgridOtsInfoLBandHighestFrequencyGHzOut,
            tnFlexgridOtsInfoLBandLowestFrequencyGHzIn,
            tnFlexgridOtsInfoLBandHighestFrequencyGHzIn,
            tnFlexgridOtsInfoChannelMonitoringAllowsOffGridOut,
            tnFlexgridOtsInfoChannelMonitoringAllowsOffGridIn,
            tnFlexgridOtsInfoLineWssIsFlexgrid,
            tnFlexgridOtsInfoLineMinMSlicesPerXc,
            tnFlexgridOtsInfoLineMaxMSlicesPerXc,
            tnFlexgridOtsInfoOadmDgeSupportedBands,
            tnFlexgridOtsInfoChannelMonitoringAllowsOffGridOutL,
            tnFlexgridOtsInfoChannelMonitoringAllowsOffGridInL,
            tnFlexgridOtsInfoLineWssIsFlexgridL,
            tnFlexgridOtsInfoLineGranularityMHzL,
            tnFlexgridOtsInfoLineMinMSlicesPerXcL,
            tnFlexgridOtsInfoLineMaxMSlicesPerXcL,
            tnFlexgridOtsInfoDcmExistsOut,
            tnFlexgridOtsInfoDcmExistsIn,
            tnFlexgridOtsInfoLineGranularityMHzIn,
            tnFlexgridOtsInfoLineGranularityMHzInL,
            tnFlexgridOtsInfoLineMinMSlicesPerXcIn,
            tnFlexgridOtsInfoLineMinMSlicesPerXcInL
        }
        STATUS         current
        DESCRIPTION    "."
        ::= { tnOpticalPortGroups 48 }

    tnOpticalPortConnectorGroup OBJECT-GROUP
        OBJECTS {
            tnOpticalPortConnectorExtraInsertionLossIn
        }
        STATUS         current
        DESCRIPTION    "."
        ::= { tnOpticalPortGroups 49}

--    obsolete
--    tnPortOtdrScanMGroup OBJECT-GROUP ::= { tnOpticalPortGroups 50 }

    tnOtsConfigGroup OBJECT-GROUP
        OBJECTS {
            tnOtsConfigsupportingsinglefiberbidi,
            tnOtsConfigsinglefiberchannelplan,
            tnOtsConfigGridStepSizeType,
            tnOtsConfigExternalAmp,
            tnOtsConfigOscInExternal
        }
        STATUS         current
        DESCRIPTION    "."
        ::= { tnOpticalPortGroups 51 }

    tnPotentialQMarginGroup OBJECT-GROUP
        OBJECTS {
            tnPotentialQMarginBaudrate,
            tnPotentialQMarginPayloadRate,
            tnPotentialQMarginMin,
            tnPotentialQMarginMax,
            tnPotentialQMarginAverage
        }
        STATUS         current
        DESCRIPTION    "."
        ::= { tnOpticalPortGroups 52 }

    tnAutoTurnUpGroup OBJECT-GROUP
        OBJECTS {
            tnAutoTurnUpEnabled,
            tnAutoTurnUpLineType,
            tnAutoTurnUpStatus,
            tnAutoTurnUpDegreeNumber,
            tnAutoTurnUpTxFiberType,
            tnAutoTurnUpTxConnectorLoss,
            tnAutoTurnUpRxConnectorLoss,
            tnAutoTurnUpTxFiberLength,
            tnAutoTurnUpOperationType,
            tnAutoTurnUpSummary,
            tnAutoTurnUpIfIndexOtsRx,
            tnAutoTurnUpIfIndexOtsTx,
            tnAutoTurnUpLinkSequenceNumber,
            tnAutoTurnUpLinkState,
            tnAutoTurnUpLinkStatus,
            tnAutoTurnUpOtsTxIpv6Address,
            tnAutoTurnUpOtsTxIfIndex,
            tnAutoTurnUpOtsTxLineType,
            tnAutoTurnUpOtsTxTargetPower,
            tnAutoTurnUpOtsRxIpAddress,
            tnAutoTurnUpOtsRxIfIndex,
            tnAutoTurnUpOtsRxLineType,
            tnAutoTurnUpOtsRxTargetPower,
            tnAutoTurnUpActiveTemplate,
            tnAutoTurnUpResetOtsLinks,
            tnAutoTurnUpHoldOff,
            tnAutoTurnUpOtsIngressCardType,
            tnAutoTurnUpOtsIngressSubType,
            tnAutoTurnUpOtsRamanCardType,
            tnAutoTurnUpTxSpanLoss
        }
        STATUS         current
        DESCRIPTION    "."
        ::= { tnOpticalPortGroups 53 }

    tnMaxPortGroup OBJECT-GROUP
        OBJECTS {
            tnMaxPortRate
        }
        STATUS         current
        DESCRIPTION    "."
        ::= { tnOpticalPortGroups 54 }

    tnAutoTurnUpOmsGroup OBJECT-GROUP
        OBJECTS {
            tnAutoTurnUpOmsData
        }
        STATUS         current
        DESCRIPTION    "."
        ::= { tnOpticalPortGroups 55 }

--------------------------------------------------------------------------------
-- Conformance Port Config Group Definitions
--------------------------------------------------------------------------------
    tnSdhPortConfigScalarsGroup OBJECT-GROUP
        OBJECTS {
            tnSdhPortConfigAttributeTotal
        }
        STATUS         current
        DESCRIPTION    "."
        ::= { tnOpticalPortConfigGroups 1 }

    tnSdhPortConfigGroup OBJECT-GROUP
        OBJECTS {
            tnSdhPortRxSignalDegradeThreshold,
            tnSdhPortRxSignalFailThreshold,
            tnSdhPortExpectedRxSectionTrace,
            tnSdhPortTxSectionTrace,
            tnSdhPortRxTIMSEnabled,
            tnSdhPortRxSectionTraceMode,
            tnSdhPortTxSectionTraceMode,
            tnSdhPortTxSynchStatusMessageDUS
        }
        STATUS         current
        DESCRIPTION    "."
        ::= { tnOpticalPortConfigGroups 2 }

--    obsolete
--    tnOC48STM16PortConfigScalarsGroup             OBJECT-GROUP ::= { tnOpticalPortConfigGroups 3 }
--    tnOC48STM16PortConfigGroup                    OBJECT-GROUP ::= { tnOpticalPortConfigGroups 4 }
--    tnOC192STM64PortConfigScalarsGroup            OBJECT-GROUP ::= { tnOpticalPortConfigGroups 5 }
--    tnOC192STM64PortConfigGroup                   OBJECT-GROUP ::= { tnOpticalPortConfigGroups 6 }
--    tnQuadOC48STM16MuxPortConfigScalarsGroup      OBJECT-GROUP ::= { tnOpticalPortConfigGroups 7 }
--    tnQuadOC48STM16MuxPortConfigGroup             OBJECT-GROUP ::= { tnOpticalPortConfigGroups 8 }
--    tnQuadOC3or12STM1or4MuxPortConfigScalarsGroup OBJECT-GROUP ::= { tnOpticalPortConfigGroups 9 }
--    tnQuadOC3or12STM1or4MuxPortConfigGroup        OBJECT-GROUP ::= { tnOpticalPortConfigGroups 10 }
--    tnBandFilterPortConfigScalarsGroup            OBJECT-GROUP ::= { tnOpticalPortConfigGroups 11 }
--    tnBandFilterPortConfigGroup                   OBJECT-GROUP ::= { tnOpticalPortConfigGroups 12 }

    tnOscPortConfigScalarsGroup OBJECT-GROUP
        OBJECTS {
            tnOscPortConfigAttributeTotal
        }
        STATUS         current
        DESCRIPTION    "."
        ::= { tnOpticalPortConfigGroups 13 }

    tnOscPortConfigGroup OBJECT-GROUP
        OBJECTS {
            tnOscPortConfigFunction
--            obsolete
--            tnOscPortPhyDeviceReset
        }
        STATUS         current
        DESCRIPTION    "."
        ::= { tnOpticalPortConfigGroups 14 }

--    obsolete
--    tnChFilterPortConfigScalarsGroup    OBJECT-GROUP ::= { tnOpticalPortConfigGroups 15 }
--    tnChFilterPortConfigGroup           OBJECT-GROUP ::= { tnOpticalPortConfigGroups 16 }
--    tnChAddDropPortConfigScalarsGroup   OBJECT-GROUP ::= { tnOpticalPortConfigGroups 17 }
--    tnChAddDropPortConfigGroup          OBJECT-GROUP ::= { tnOpticalPortConfigGroups 18 }
--    tnBbaHgPortConfigScalarsGroup       OBJECT-GROUP ::= { tnOpticalPortConfigGroups 19 }
--    tnBbaHgPortConfigGroup              OBJECT-GROUP ::= { tnOpticalPortConfigGroups 20 }
--    tnBbaLgPortConfigScalarsGroup       OBJECT-GROUP ::= { tnOpticalPortConfigGroups 21 }
--    tnBbaLgPortConfigGroup              OBJECT-GROUP ::= { tnOpticalPortConfigGroups 22 }
--    tnPpsPortConfigScalarsGroup         OBJECT-GROUP ::= { tnOpticalPortConfigGroups 23 }
--    tnPpsPortConfigGroup                OBJECT-GROUP ::= { tnOpticalPortConfigGroups 24 }
--    tnDualGigEMuxPortConfigScalarsGroup OBJECT-GROUP ::= { tnOpticalPortConfigGroups 25 }
--    tnDualGigEMuxPortConfigGroup        OBJECT-GROUP ::= { tnOpticalPortConfigGroups 26 }
--    tnRoadmPortConfigScalarsGroup       OBJECT-GROUP ::= { tnOpticalPortConfigGroups 27 }
--    tnRoadmPortConfigGroup              OBJECT-GROUP ::= { tnOpticalPortConfigGroups 28 }
--    tn10GigELANPortConfigScalarsGroup   OBJECT-GROUP ::= { tnOpticalPortConfigGroups 29 }
--    tn10GigELANPortConfigGroup          OBJECT-GROUP ::= { tnOpticalPortConfigGroups 30 }

    tnDcmPortConfigScalarsGroup OBJECT-GROUP
        OBJECTS {
            tnDcmPortConfigAttributeTotal
        }
        STATUS         current
        DESCRIPTION    "."
        ::= { tnOpticalPortConfigGroups 31 }

    tnDcmPortConfigGroup OBJECT-GROUP
        OBJECTS {
            tnDcmPortConfigFunction
        }
        STATUS         current
        DESCRIPTION    "."
        ::= { tnOpticalPortConfigGroups 32 }

--    obsolete
--    tnDecaGigEMuxPortConfigScalarsGroup OBJECT-GROUP ::= { tnOpticalPortConfigGroups 33 }
--    tnDecaGigEMuxPortConfigGroup        OBJECT-GROUP ::= { tnOpticalPortConfigGroups 34 }

    tnSonetPortConfigScalarsGroup OBJECT-GROUP
        OBJECTS {
            tnSonetPortConfigAttributeTotal
        }
        STATUS         current
        DESCRIPTION    "."
        ::= { tnOpticalPortConfigGroups 35 }

    tnSonetPortConfigGroup OBJECT-GROUP
        OBJECTS {
            tnSonetPortRxSignalDegradeThreshold,
            tnSonetPortRxSignalFailThreshold,
            tnSonetPortExpectedRxSectionTrace,
            tnSonetPortTxSectionTrace,
            tnSonetPortRxTIMSEnabled,
            tnSonetPortRxSectionTraceMode,
            tnSonetPortTxSectionTraceMode,
            tnSonetPortTxSynchStatusMessageDUS
        }
        STATUS         current
        DESCRIPTION    "."
        ::= { tnOpticalPortConfigGroups 36 }

--    obsolete
--    tnExternalDcuPortConfigScalarsGroup OBJECT-GROUP ::= { tnOpticalPortConfigGroups 37 }
--    tnExternalDcuPortConfigGroup        OBJECT-GROUP ::= { tnOpticalPortConfigGroups 38 }

    tnDigitalWrapperPortConfigScalarsGroup OBJECT-GROUP
        OBJECTS {
            tnDigitalWrapperPortConfigAttributeTotal
        }
        STATUS         current
        DESCRIPTION    "."
        ::= { tnOpticalPortConfigGroups 39 }

    tnDigitalWrapperPortConfigGroup OBJECT-GROUP
        OBJECTS {
            tnDwPortRxRSBERSDThresh,
            tnDwPortRxRSBERSFThresh,
            tnDwPortDwMode,
            tnDwPortPMTTIEnabled,
            tnDwPortPTIEnabled
        }
        STATUS         current
        DESCRIPTION    "."
        ::= { tnOpticalPortConfigGroups 40 }

    tnNetworkPortConfigScalarsGroup OBJECT-GROUP
        OBJECTS {
            tnNetworkPortConfigAttributeTotal
        }
        STATUS         current
        DESCRIPTION    "."
        ::= { tnOpticalPortConfigGroups 41 }

    tnNetworkPortConfigGroup OBJECT-GROUP
        OBJECTS {
--            obsolete
--            tnNwPortOchStatusRx,
--            tnNwPortOchStatusTx,
            tnNwPortProgrammedChannel,
            tnNwPortChannelRx,
            tnNwPortChannelSpacing,
            tnNwPortLaserOffRequest,
            tnNwPortForcedLaserState,
            tnNwPortProgrammedITUNumOffsetTx,
            tnNwPortProgrammedITUNumOffsetRx,
            tnNwPortProgrammedITUNumOffsetGridStepSize,
            tnNwPortCalculatedRxFreq,
            tnNwPortCalculatedTxFreq,
            tnNwPortLinkSpan,
            tnNwPortChannelTxLane,
            tnNwPortChannelRxLane,
            tnNwPortRxFineOffSet,
            tnNwPortTxFineOffSet
        }
        STATUS         current
        DESCRIPTION    "."
        ::= { tnOpticalPortConfigGroups 42 }

--    obsolete
--    tnMsaHgPortConfigScalarsGroup OBJECT-GROUP ::= { tnOpticalPortConfigGroups 43 }
--    tnMsaHgPortConfigGroup        OBJECT-GROUP ::= { tnOpticalPortConfigGroups 44 }
--    tnCmd42PortConfigScalarsGroup OBJECT-GROUP ::= { tnOpticalPortConfigGroups 45 }
--    tnCmd42PortConfigGroup        OBJECT-GROUP ::= { tnOpticalPortConfigGroups 46 }
--    tnWssX9PortConfigScalarsGroup OBJECT-GROUP ::= { tnOpticalPortConfigGroups 47 }
--    tnWssX9PortConfigGroup        OBJECT-GROUP ::= { tnOpticalPortConfigGroups 48 }

    tnSfpPortConfigScalarsGroup OBJECT-GROUP
        OBJECTS {
            tnSfpPortConfigAttributeTotal
        }
        STATUS         current
        DESCRIPTION    "."
        ::= { tnOpticalPortConfigGroups 49 }

    tnSfpPortConfigGroup OBJECT-GROUP
        OBJECTS {
            tnSfpPortType,
            tnSfpPortModuleName,
            tnSfpPortLifeCycleState,
            tnSfpPortProductCode,
            tnSfpPortDueDate,
            tnSfpPortProductCodeSup,
            tnSfpPortModuleCustomerLifeCycleState,
            tnSfpPortCircuitId,
            tnSfpPortIdModuleXponder,
            tnSfpPortModuleDescription
        }
        STATUS         current
        DESCRIPTION    "."
        ::= { tnOpticalPortConfigGroups 50 }

--    obsolete
--    tn1xMR2dot5GPortConfigScalarsGroup OBJECT-GROUP ::= { tnOpticalPortConfigGroups 51 }
--    tn1xMR2dot5GPortConfigGroup        OBJECT-GROUP ::= { tnOpticalPortConfigGroups 52 }

    tnOpsaPortConfigScalarsGroup OBJECT-GROUP
        OBJECTS {
            tnOpsaPortConfigAttributeTotal
        }
        STATUS         current
        DESCRIPTION    "."
        ::= { tnOpticalPortConfigGroups 53 }

    tnOpsaPortConfigGroup OBJECT-GROUP
        OBJECTS {
            tnOpsaPortConfigFunction
--            obsolete
--            tnOpsaPortSwitchingThreshold,
--            tnOpsaPortSwitchingThresholdTolerance,
--            tnOpsaPortTransmitAttenuation,
--            tnOpsaPortSwitchingThreshCalcControl
        }
        STATUS         current
        DESCRIPTION    "."
        ::= { tnOpticalPortConfigGroups 54 }

    tn11stmm10PortConfigScalarsGroup OBJECT-GROUP
        OBJECTS {
            tn11stmm10PortConfigAttributeTotal
        }
        STATUS         current
        DESCRIPTION    "."
        ::= { tnOpticalPortConfigGroups 55 }

    tn11stmm10PortConfigGroup OBJECT-GROUP
        OBJECTS {
            tn11stmm10PortConfigFunction
        }
        STATUS         current
        DESCRIPTION    "."
        ::= { tnOpticalPortConfigGroups 56 }

    tn11star1PortConfigScalarsGroup OBJECT-GROUP
        OBJECTS {
            tn11star1PortConfigAttributeTotal
        }
        STATUS         current
        DESCRIPTION    "."
        ::= { tnOpticalPortConfigGroups 57 }

    tn11star1PortConfigGroup OBJECT-GROUP
        OBJECTS {
            tn11star1PortConfigFunction
        }
        STATUS         current
        DESCRIPTION    "."
        ::= { tnOpticalPortConfigGroups 58 }

    tnAhphgPortConfigScalarsGroup OBJECT-GROUP
        OBJECTS {
            tnAhphgPortConfigAttributeTotal
        }
        STATUS         current
        DESCRIPTION    "."
        ::= { tnOpticalPortConfigGroups 59 }

    tnAhphgPortConfigGroup OBJECT-GROUP
        OBJECTS {
            tnAhphgPortConfigFunction
        }
        STATUS         current
        DESCRIPTION    "."
        ::= { tnOpticalPortConfigGroups 60 }

    tnAlphgPortConfigScalarsGroup OBJECT-GROUP
        OBJECTS {
            tnAlphgPortConfigAttributeTotal
        }
        STATUS         current
        DESCRIPTION    "."
        ::= { tnOpticalPortConfigGroups 61 }

    tnAlphgPortConfigGroup OBJECT-GROUP
        OBJECTS {
            tnAlphgPortConfigFunction
        }
        STATUS         current
        DESCRIPTION    "."
        ::= { tnOpticalPortConfigGroups 62 }

    tnCwr8PortConfigScalarsGroup OBJECT-GROUP
        OBJECTS {
            tnCwr8PortConfigAttributeTotal
        }
        STATUS         current
        DESCRIPTION    "."
        ::= { tnOpticalPortConfigGroups 63 }

    tnCwr8PortConfigGroup OBJECT-GROUP
        OBJECTS {
            tnCwr8PortConfigFunction,
--            obsolete
--            tnCwr8PortBlockerAging,
            tnCwr8PortDropTargetPower
        }
        STATUS         current
        DESCRIPTION    "."
        ::= { tnOpticalPortConfigGroups 64 }

    tn11stge12PortConfigScalarsGroup OBJECT-GROUP
        OBJECTS {
            tn11stge12PortConfigAttributeTotal
        }
        STATUS         current
        DESCRIPTION    "."
        ::= { tnOpticalPortConfigGroups 65 }

    tn11stge12PortConfigGroup OBJECT-GROUP
        OBJECTS {
            tn11stge12PortConfigFunction
        }
        STATUS         current
        DESCRIPTION    "."
        ::= { tnOpticalPortConfigGroups 66 }

    tn11dpge12PortConfigScalarsGroup OBJECT-GROUP
        OBJECTS {
            tn11dpge12PortConfigAttributeTotal
        }
        STATUS         current
        DESCRIPTION    "."
        ::= { tnOpticalPortConfigGroups 67 }

    tn11dpge12PortConfigGroup OBJECT-GROUP
        OBJECTS {
            tn11dpge12PortConfigFunction
        }
        STATUS         current
        DESCRIPTION    "."
        ::= { tnOpticalPortConfigGroups 68 }

    tnSfd44PortConfigScalarsGroup OBJECT-GROUP
        OBJECTS {
            tnSfd44PortConfigAttributeTotal
        }
        STATUS         current
        DESCRIPTION    "."
        ::= { tnOpticalPortConfigGroups 69 }

    tnSfd44PortConfigGroup OBJECT-GROUP
        OBJECTS {
            tnSfd44PortConfigFunction
        }
        STATUS         current
        DESCRIPTION    "."
        ::= { tnOpticalPortConfigGroups 70 }

    tnDwdmCmnPortConfigGroup OBJECT-GROUP
        OBJECTS {
            tnDwdmCmnPortXfpType,
            tnDwdmCmnPortAlmProfName,
            tnDwdmCmnPortMgracd,
            tnDwdmCmnPortPowerClassMod,
            tnDwdmCmnPortCustomerLifeCycleState
        }
        STATUS         current
        DESCRIPTION    "."
        ::= { tnOpticalPortConfigGroups 71 }

    tnDwdmCmnLinePortConfigGroup OBJECT-GROUP
        OBJECTS {
--          obsolete
--            tnDwdmCmnLinePortLoopType,
            tnDwdmCmnLinePortTransmissionMode,
            tnDwdmCmnLinePortOchOtu2FecMode,
            tnDwdmCmnLinePortOchOtu2Rate,
            tnDwdmCmnLinePortOtu2TransmittedTti,
            tnDwdmCmnLinePortOtu2ExpectedTti,
            tnDwdmCmnLinePortOtu2TimConsequenceAction,
            tnDwdmCmnLinePortOtu2TimDetectionMode,
            tnDwdmCmnLinePortOdu2PayloadType,
            tnDwdmCmnLinePortOdu2OchSignalDefConsequenceAction,
            tnDwdmCmnLinePortOdu2PlmConsequenceAction,
            tnDwdmCmnLinePortOdu2MappingMode,
            tnDwdmCmnLinePortOdu2TpMode,
            tnDwdmCmnLinePortOdu2TransmittedTti,
            tnDwdmCmnLinePortOdu2ExpectedTti,
            tnDwdmCmnLinePortOdu2TimConsequenceAction,
            tnDwdmCmnLinePortOdu2TimDetectionMode,
            tnDwdmCmnLinePortCrossRegPartner,
            tnDwdmCmnLinePortBroadcastFrom,
            tnDwdmCmnLinePortRegenResponse,
            tnDwdmCmnLinePortOtu2holdofftimer,  -- deprecated
            tnDwdmCmnLinePortDemandName,
            tnDwdmCmnLinePortApsEnable,
            tnDwdmCmnLinePortHoldOffTimer,
            tnDwdmCmnLinePortDMConfigCMEPMode,
            tnDwdmCmnLinePortDMConfigEnable,
            tnDwdmCmnLinePortCluster,
            tnDwdmCmnLinePortDegInterval,
            tnDwdmCmnLinePortDegThreshold,
            tnDwdmCmnLinePorttxShape,
            tnDwdmCmnLinePortCdPreComp,
            tnDwdmCmnLinePortPhasenCode,
            tnDwdmCmnLinePortPolarizationTrack,
            tnDwdmCmnLinePortClusterConnFrom,
            tnDwdmCmnLinePortWtpsProtection,
            tnDwdmCmnLinePortDegUcbIntvl,
            tnDwdmCmnLinePortDegUcbThr,
            tnDwdmCmnLinePortDegUcbMon,
            tnDwdmCmnLinePortDegUcbCa,
            tnDwdmCmnLinePortDesignatedPortMode,
            tnDwdmCmnLinePortDesignatedRegenPair,
            tnDwdmCmnLinePortManagementMode,
            tnDwdmCmnLinePortOtuOtsigId,
            tnDwdmCmnLinePortOtsigOTSiList,
            tnDwdmCmnLinePortOtsigOtuStruct,
            tnDwdmCmnLinePortOtsigProfileId,
            tnDwdmCmnLinePortOtsigCapacity,
            tnDwdmCmnLinePortOtsiPayloadRate,
            tnDwdmCmnLinePortOtsigMgracd,
            tnDwdmCmnLinePortDegPrefecThr
        }
        STATUS         current
        DESCRIPTION    "."
        ::= { tnOpticalPortConfigGroups 72 }

    tnDwdmCmnClientPortConfigGroup OBJECT-GROUP
        OBJECTS {
--            obsolete
--            tnDwdmCmnClientPortLoopType,
            tnDwdmCmnClientPortLosProp,
            tnDwdmCmnClientPortTs1,
            tnDwdmCmnClientPortTs2,
            tnDwdmCmnClientPortOchOtu2FecMode,
            tnDwdmCmnClientPortOchOtu2Rate,
            tnDwdmCmnClientPortOtu2TransmittedTti,
            tnDwdmCmnClientPortOtu2ExpectedTti,
            tnDwdmCmnClientPortOtu2TimConsequenceAction,
            tnDwdmCmnClientPortOtu2TimDetectionMode,
            tnDwdmCmnClientPortOdu2TransmittedTti,
            tnDwdmCmnClientPortOdu2ExpectedTti,
            tnDwdmCmnClientPortOdu2TimDetectionMode,
            tnDwdmCmnClientPortProtectionTs1,
            tnDwdmCmnClientPortProtectionTs2,
            tnDwdmCmnClientPortTsMap,
            tnDwdmCmnClientPortContainer,
            tnDwdmCmnClientPortCSF,
            tnDwdmCmnClientPortSSF,
            tnDwdmCmnClientPortScramMode,
            tnDwdmCmnClientPortDegInterval,
            tnDwdmCmnClientPortDegThreshold,
            tnDwdmCmnClientPortHoldOffTimer,
            tnDwdmCmnClientPortYcableMode,
            tnDwdmCmnClientPortEthFecMode,
            tnDwdmCmnClientPortHoldOffTimerValue,
            tnDwdmCmnClientPortFlsState,
            tnDwdmCmnClientPortServerPort,
            tnDwdmCmnClientPortInOpsbAction,
            tnDwdmCmnClientPortSSFDelayTimer,
            tnDwdmCmnClientPortFecBypassInd,
            tnDwdmCmnClientPortSSFDelayCa,
            tnDwdmCmnClientPortSsdca,
            tnDwdmCmnClientPortFlexGfpSize,
            tnDwdmCmnClientPortSdiRate,
            tnDwdmCmnClientPortGfpFcs,
            tnDwdmCmnClientPortCSFHoldOff,
            tnDwdmCmnClientPortSSFHoldOff,
            tnDwdmCmnClientPortSignalMode,
            tnDwdmCmnClientPortCSFDelayTimer,
            tnDwdmCmnClientPortSSFOnOCIAction
        }
        STATUS         current
        DESCRIPTION    "."
        ::= { tnOpticalPortConfigGroups 73 }

    tnRsmonIngrPortConfigGroup OBJECT-GROUP
        OBJECTS {
            tnRsmonIngrPortTransmittedTti,
            tnRsmonIngrPortExpectedTti,
            tnRsmonIngrPortTimod,
            tnRsmonIngrPortTimDetection,
            tnRsmonIngrPortTimConsequenceAction,
--            obsolete
--            tnRsmonIngrPortTimDetectionMode,
            tnRsmonIngrPortSigMode
        }
        STATUS         current
        DESCRIPTION    "."
        ::= { tnOpticalPortConfigGroups 74 }

    tnMsmonPortConfigGroup OBJECT-GROUP
        OBJECTS {
            tnMsmonPortMappingMode,
            tnMsmonPortExcThLevel,
            tnMsmonPortDegThLevel
        }
        STATUS         current
        DESCRIPTION    "."
        ::= { tnOpticalPortConfigGroups 75 }

    tnOscSfpPortConfigGroup OBJECT-GROUP
        OBJECTS {
--            obsolete
--            tnOscSfpPortType,
            tnOscSfpTemperature,
            tnOscMtu,
            tnOscMtuNeg,
            tnOscEnable,
            tnOscConnId,
            tnOscPortInfoETR,
            tnOscIPv6LinkLocalInetAddress,
            tnOscLcpEchoInterval,
            tnOscLcpEchoFailure
        }
        STATUS         current
        DESCRIPTION    "."
        ::= { tnOpticalPortConfigGroups 76 }

    tnDwdmGpPhyPortConfigGroup OBJECT-GROUP
        OBJECTS {
            tnDwdmGpPhyPortPacketIfType,
            tnDwdmGpPhyPortErroredFrameDrop,
            tnDwdmGpPhyPortAutoNegotiation,
            tnDwdmGpPhyPortPacketFcMode,
            tnDwdmGpPhyPortGfpcrc
        }
        STATUS         current
        DESCRIPTION    "."
        ::= { tnOpticalPortConfigGroups 77 }

--    obsolete
--    tnGccPortConfigGroup OBJECT-GROUP ::= { tnOpticalPortConfigGroups 78 }

    tnSvacPortConfigGroup OBJECT-GROUP
        OBJECTS {
            tnSvacPortConfigFunction
        }
        STATUS         current
        DESCRIPTION    "."
        ::= { tnOpticalPortConfigGroups 79 }

    tnSfdPortConfigGroup OBJECT-GROUP
        OBJECTS {
            tnSfd5aPortConfigFunction,
            tnSfd5bPortConfigFunction,
            tnSfd5cPortConfigFunction,
            tnSfd5dPortConfigFunction,
            tnSfd5ePortConfigFunction,
            tnSfd5fPortConfigFunction,
            tnSfd5gPortConfigFunction,
            tnSfd5hPortConfigFunction,
            tnSfd10aPortConfigFunction,
            tnSfd10bPortConfigFunction,
            tnSfd10cPortConfigFunction,
            tnSfd10dPortConfigFunction,
            tnSfd8aPortConfigFunction,
            tnSfd8bPortConfigFunction,
            tnSfd8cPortConfigFunction,
            tnSfd8dPortConfigFunction,
            tnSfd4aPortConfigFunction,
            tnSfd4bPortConfigFunction,
            tnSfd4cPortConfigFunction,
            tnSfd4dPortConfigFunction,
            tnSfd4ePortConfigFunction,
            tnSfd4fPortConfigFunction,
            tnSfd4gPortConfigFunction,
            tnSfd4hPortConfigFunction,
            tnSfd2aPortConfigFunction,
            tnSfd2bPortConfigFunction,
            tnSfd2cPortConfigFunction,
            tnSfd2dPortConfigFunction,
            tnSfd2ePortConfigFunction,
            tnSfd2fPortConfigFunction,
            tnSfd2gPortConfigFunction,
            tnSfd2hPortConfigFunction,
            tnSfd2iPortConfigFunction,
            tnSfd2lPortConfigFunction,
            tnSfd2mPortConfigFunction,
            tnSfd2nPortConfigFunction,
            tnSfd2oPortConfigFunction,
            tnSfd2pPortConfigFunction,
            tnSfd2qPortConfigFunction,
            tnSfd2rPortConfigFunction,
            tnVwmSfd8aPortConfigFunction,
            tnVwmSfd8bPortConfigFunction,
            tnVwmSfd8cPortConfigFunction,
            tnVwmSfd8dPortConfigFunction,
            tnSfdc8aPortConfigFunction,
            tnSfdc8bPortConfigFunction,
            tnSfdc8cPortConfigFunction,
            tnSfdc8dPortConfigFunction,
            tnSfdc8ePortConfigFunction
        }
        STATUS         current
        DESCRIPTION    "."
        ::= { tnOpticalPortConfigGroups 80 }

    tnSfcPortConfigGroup OBJECT-GROUP
        OBJECTS {
            tnSfc2aPortConfigFunction,
            tnSfc2bPortConfigFunction,
            tnSfc2cPortConfigFunction,
            tnSfc2dPortConfigFunction,
            tnSfc4aPortConfigFunction,
            tnSfc4bPortConfigFunction,
            tnSfc8PortConfigFunction,
            tnSfc1aPortConfigFunction,
            tnSfc1bPortConfigFunction,
            tnSfc1cPortConfigFunction,
            tnSfc1dPortConfigFunction,
            tnSfc1ePortConfigFunction,
            tnSfc1fPortConfigFunction,
            tnSfc1gPortConfigFunction,
            tnSfc1hPortConfigFunction,
            tnVwmSfc8PortConfigFunction
        }
        STATUS         current
        DESCRIPTION    "."
        ::= { tnOpticalPortConfigGroups 81 }

    tnVtsPortConfigGroup OBJECT-GROUP
        OBJECTS {
            tnVtsPortVts1Source,
            tnVtsPortVts2Source,
            tnVtsPortVts3Source,
            tnVtsPortVts4Source,
            tnVtsPortVts5Source,
            tnVtsPortVts6Source,
            tnVtsPortVts7Source,
            tnVtsPortVts8Source,
            tnVtsPortVts9Source,
            tnVtsPortVts10Source
        }
        STATUS         current
        DESCRIPTION    "."
        ::= { tnOpticalPortConfigGroups 82 }

    tnOmdPortConfigGroup OBJECT-GROUP
        OBJECTS {
            tnOmdPortLosThreshold,
            tnOmdPortLosThresholdTolerance,
            tnOmdPortLosOutThreshold,
            tnOmdPortLosOutThresholdTolerance
        }
        STATUS         current
        DESCRIPTION    "."
        ::= { tnOpticalPortConfigGroups 83 }

    tn4dpa4PortConfigScalarsGroup OBJECT-GROUP
        OBJECTS {
            tn4dpa4PortConfigAttributeTotal
        }
        STATUS         current
        DESCRIPTION    "."
        ::= { tnOpticalPortConfigGroups 84 }

    tn4dpa4PortConfigGroup OBJECT-GROUP
        OBJECTS {
            tn4dpa4PortConfigFunction
        }
        STATUS         current
        DESCRIPTION    "."
        ::= { tnOpticalPortConfigGroups 85 }

    tnCwr8c88PortConfigScalarsGroup OBJECT-GROUP
        OBJECTS {
            tnCwr8c88PortConfigAttributeTotal
        }
        STATUS         current
        DESCRIPTION    "."
        ::= { tnOpticalPortConfigGroups 86 }

    tnCwr8c88PortConfigGroup OBJECT-GROUP
        OBJECTS {
            tnCwr8c88PortConfigFunction,
--            obsolete
--            tnCwr8c88PortBlockerAging,
            tnCwr8c88PortDropTargetPower
        }
        STATUS         current
        DESCRIPTION    "."
        ::= { tnOpticalPortConfigGroups 87 }

    tnSfd44bPortConfigScalarsGroup OBJECT-GROUP
        OBJECTS {
            tnSfd44bPortConfigAttributeTotal
        }
        STATUS         current
        DESCRIPTION    "."
        ::= { tnOpticalPortConfigGroups 88 }

    tnSfd44bPortConfigGroup OBJECT-GROUP
        OBJECTS {
            tnSfd44bPortConfigFunction
        }
        STATUS         current
        DESCRIPTION    "."
        ::= { tnOpticalPortConfigGroups 89 }

    tnItlbPortConfigScalarsGroup OBJECT-GROUP
        OBJECTS {
            tnItlbPortConfigAttributeTotal
        }
        STATUS         current
        DESCRIPTION    "."
        ::= { tnOpticalPortConfigGroups 90 }

    tnItlbPortConfigGroup OBJECT-GROUP
        OBJECTS {
            tnItlbPortConfigFunction
        }
        STATUS         current
        DESCRIPTION    "."
        ::= { tnOpticalPortConfigGroups 91 }

    tnAhplgPortConfigScalarsGroup OBJECT-GROUP
        OBJECTS {
            tnAhplgPortConfigAttributeTotal
        }
        STATUS         current
        DESCRIPTION    "."
        ::= { tnOpticalPortConfigGroups 92 }

    tnAhplgPortConfigGroup OBJECT-GROUP
        OBJECTS {
            tnAhplgPortConfigFunction
        }
        STATUS         current
        DESCRIPTION    "."
        ::= { tnOpticalPortConfigGroups 93 }

    tnDwdmCmnOtu1Odu1LinePortConfigGroup OBJECT-GROUP
        OBJECTS {
            tnDwdmCmnLinePortOchOtu1FecMode,
            tnDwdmCmnLinePortOchOtu1Rate,
            tnDwdmCmnLinePortOtu1TransmittedTti,
            tnDwdmCmnLinePortOtu1ExpectedTti,
            tnDwdmCmnLinePortOtu1TimConsequenceAction,
            tnDwdmCmnLinePortOtu1TimDetectionMode,
            tnDwdmCmnLinePortOdu1PayloadType,
            tnDwdmCmnLinePortOdu1OchSignalDefConsequenceAction,
            tnDwdmCmnLinePortOdu1PlmConsequenceAction,
            tnDwdmCmnLinePortOdu1MappingMode,
            tnDwdmCmnLinePortOdu1TpMode,
            tnDwdmCmnLinePortOdu1TransmittedTti,
            tnDwdmCmnLinePortOdu1ExpectedTti,
            tnDwdmCmnLinePortOdu1TimConsequenceAction,
            tnDwdmCmnLinePortOdu1TimDetectionMode,
            tnDwdmCmnLinePortOdu1Interworking
        }
        STATUS         current
        DESCRIPTION    "."
        ::= { tnOpticalPortConfigGroups 94 }

    tnDwdmCmnOtu1Odu1ClientPortConfigGroup OBJECT-GROUP
        OBJECTS {
            tnDwdmCmnClientPortOchOtu1FecMode,
            tnDwdmCmnClientPortOchOtu1Rate,
            tnDwdmCmnClientPortOtu1TransmittedTti,
            tnDwdmCmnClientPortOtu1ExpectedTti,
            tnDwdmCmnClientPortOtu1TimConsequenceAction,
            tnDwdmCmnClientPortOtu1TimDetectionMode,
            tnDwdmCmnClientPortOdu1TransmittedTti,
            tnDwdmCmnClientPortOdu1ExpectedTti,
            tnDwdmCmnClientPortOdu1TimDetectionMode
        }
        STATUS         current
        DESCRIPTION    "."
        ::= { tnOpticalPortConfigGroups 95 }

    tn43stx4PortConfigScalarsGroup OBJECT-GROUP
        OBJECTS {
            tn43stx4PortConfigAttributeTotal
        }
        STATUS         current
        DESCRIPTION    "."
        ::= { tnOpticalPortConfigGroups 96 }

    tn43stx4PortConfigGroup OBJECT-GROUP
        OBJECTS {
            tn43stx4PortConfigFunction
        }
        STATUS         current
        DESCRIPTION    "."
        ::= { tnOpticalPortConfigGroups 97 }

    tnDwdmCmnOtu3Odu3LinePortConfigGroup OBJECT-GROUP
        OBJECTS {
            tnDwdmCmnLinePortOchOtu3FecMode,
            tnDwdmCmnLinePortOtu3TransmittedTti,
            tnDwdmCmnLinePortOtu3ExpectedTti,
            tnDwdmCmnLinePortOtu3TimConsequenceAction,
            tnDwdmCmnLinePortOtu3TimDetectionMode,
            tnDwdmCmnLinePortOdu3PayloadType,
            tnDwdmCmnLinePortOdu3PlmConsequenceAction,
            tnDwdmCmnLinePortOdu3TransmittedTti,
            tnDwdmCmnLinePortOdu3ExpectedTti,
            tnDwdmCmnLinePortOdu3TimConsequenceAction,
            tnDwdmCmnLinePortOdu3TimDetectionMode,
            tnDwdmCmnLinePortOdu3MappingMode,
            tnDwdmCmnLinePortOchOtu3Rate,
            tnDwdmCmnLinePortOdu3Interworking
        }
        STATUS         current
        DESCRIPTION    "."
        ::= { tnOpticalPortConfigGroups 98 }

    tnAlpfgkPortConfigScalarsGroup OBJECT-GROUP
        OBJECTS {
            tnAlpfgkPortConfigAttributeTotal
        }
        STATUS         current
        DESCRIPTION    "."
        ::= { tnOpticalPortConfigGroups 99 }

    tnAlpfgkPortConfigGroup OBJECT-GROUP
        OBJECTS {
            tnAlpfgkPortConfigFunction
        }
        STATUS         current
        DESCRIPTION    "."
        ::= { tnOpticalPortConfigGroups 100 }

    tn4dpa2PortConfigScalarsGroup OBJECT-GROUP
        OBJECTS {
            tn4dpa2PortConfigAttributeTotal
        }
        STATUS         current
        DESCRIPTION    "."
        ::= { tnOpticalPortConfigGroups 101 }

    tn4dpa2PortConfigGroup OBJECT-GROUP
        OBJECTS {
            tn4dpa2PortConfigFunction
        }
        STATUS         current
        DESCRIPTION    "."
        ::= { tnOpticalPortConfigGroups 102 }

    tn43sta1pPortConfigScalarsGroup OBJECT-GROUP
        OBJECTS {
            tn43sta1pPortConfigAttributeTotal
        }
        STATUS         current
        DESCRIPTION    "."
        ::= { tnOpticalPortConfigGroups 103 }

    tn43sta1pPortConfigGroup OBJECT-GROUP
        OBJECTS {
            tn43sta1pPortConfigFunction
        }
        STATUS         current
        DESCRIPTION    "."
        ::= { tnOpticalPortConfigGroups 104 }

    tn43stx4pPortConfigScalarsGroup OBJECT-GROUP
        OBJECTS {
            tn43stx4pPortConfigAttributeTotal
        }
        STATUS         current
        DESCRIPTION    "."
        ::= { tnOpticalPortConfigGroups 105 }

    tn43stx4pPortConfigGroup OBJECT-GROUP
        OBJECTS {
            tn43stx4pPortConfigFunction
        }
        STATUS         current
        DESCRIPTION    "."
        ::= { tnOpticalPortConfigGroups 106 }

    tnA2325aPortConfigScalarsGroup OBJECT-GROUP
        OBJECTS {
            tnA2325aPortConfigAttributeTotal
        }
        STATUS         current
        DESCRIPTION    "."
        ::= { tnOpticalPortConfigGroups 109 }

    tnA2325aPortConfigGroup OBJECT-GROUP
        OBJECTS {
            tnA2325aPortConfigFunction
        }
        STATUS         current
        DESCRIPTION    "."
        ::= { tnOpticalPortConfigGroups 110 }

    tnSfd40PortConfigScalarsGroup OBJECT-GROUP
        OBJECTS {
            tnSfd40PortConfigAttributeTotal
        }
        STATUS         current
        DESCRIPTION    "."
        ::= { tnOpticalPortConfigGroups 111 }

    tnSfd40PortConfigGroup OBJECT-GROUP
        OBJECTS {
            tnSfd40PortConfigFunction
        }
        STATUS         current
        DESCRIPTION    "."
        ::= { tnOpticalPortConfigGroups 112 }

    tnSfd40bPortConfigScalarsGroup OBJECT-GROUP
        OBJECTS {
            tnSfd40bPortConfigAttributeTotal
        }
        STATUS         current
        DESCRIPTION    "."
        ::= { tnOpticalPortConfigGroups 113 }

    tnSfd40bPortConfigGroup OBJECT-GROUP
        OBJECTS {
            tnSfd40bPortConfigFunction
        }
        STATUS         current
        DESCRIPTION    "."
        ::= { tnOpticalPortConfigGroups 114 }

    tn11qpa4PortConfigScalarsGroup OBJECT-GROUP
        OBJECTS {
            tn11qpa4PortConfigAttributeTotal
        }
        STATUS         current
        DESCRIPTION    "."
        ::= { tnOpticalPortConfigGroups 115 }

    tn11qpa4PortConfigGroup OBJECT-GROUP
        OBJECTS {
            tn11qpa4PortConfigFunction
        }
        STATUS         current
        DESCRIPTION    "."
        ::= { tnOpticalPortConfigGroups 116 }

    tn112scx10PortConfigScalarsGroup OBJECT-GROUP
        OBJECTS {
            tn112scx10PortConfigAttributeTotal
        }
        STATUS         current
        DESCRIPTION    "."
        ::= { tnOpticalPortConfigGroups 117 }

    tn112scx10PortConfigGroup OBJECT-GROUP
        OBJECTS {
            tn112scx10PortConfigFunction
        }
        STATUS         current
        DESCRIPTION    "."
        ::= { tnOpticalPortConfigGroups 118 }

    tn112sca1PortConfigScalarsGroup OBJECT-GROUP
        OBJECTS {
            tn112sca1PortConfigAttributeTotal
        }
        STATUS         current
        DESCRIPTION    "."
        ::= { tnOpticalPortConfigGroups 119 }

    tn112sca1PortConfigGroup OBJECT-GROUP
        OBJECTS {
            tn112sca1PortConfigFunction
        }
        STATUS         current
        DESCRIPTION    "."
        ::= { tnOpticalPortConfigGroups 120 }

    tnDwdmCmnOtu4Odu4LinePortConfigGroup OBJECT-GROUP
        OBJECTS {
            tnDwdmCmnLinePortOchOtu4FecMode,
            tnDwdmCmnLinePortOchOtu4Rate,
            tnDwdmCmnLinePortOtu4TransmittedTti,
            tnDwdmCmnLinePortOtu4ExpectedTti,
            tnDwdmCmnLinePortOtu4TimConsequenceAction,
            tnDwdmCmnLinePortOtu4TimDetectionMode,
            tnDwdmCmnLinePortOdu4PayloadType,
            tnDwdmCmnLinePortOdu4PlmConsequenceAction,
            tnDwdmCmnLinePortOdu4TransmittedTti,
            tnDwdmCmnLinePortOdu4ExpectedTti,
            tnDwdmCmnLinePortOdu4TimConsequenceAction,
            tnDwdmCmnLinePortOdu4TimDetectionMode,
            tnDwdmCmnLinePortOtu4RegenResponse,
            tnDwdmCmnLinePortOdu4Interworking,
            tnDwdmCmnLinePortOtu4holdofftimer,  -- deprecated
            tnDwdmCmnLinePortOdu4112GInterworking,
            tnDwdmCmnLinePortOdu4DMConfigCMEPMode,
            tnDwdmCmnLinePortOdu4DMConfigEnable,
            tnDwdmCmnLinePortOdu4CndRes,
            tnDwdmCmnLinePortOdu4Encoding
        }
        STATUS         current
        DESCRIPTION    "."
        ::= { tnOpticalPortConfigGroups 121 }

    tnDwdmCmnOtu4Odu4ClientPortConfigGroup OBJECT-GROUP
        OBJECTS {
            tnDwdmCmnClientPortOchOtu4FecMode,
            tnDwdmCmnClientPortOchOtu4Rate,
            tnDwdmCmnClientPortOtu4TransmittedTti,
            tnDwdmCmnClientPortOtu4ExpectedTti,
            tnDwdmCmnClientPortOtu4TimConsequenceAction,
            tnDwdmCmnClientPortOtu4TimDetectionMode,
            tnDwdmCmnClientPortOdu4TransmittedTti,
            tnDwdmCmnClientPortOdu4ExpectedTti,
            tnDwdmCmnClientPortOdu4TimDetectionMode,
--            obsolete
--            tnDwdmCmnClientPortOdu4IncomingTti,
--            tnDwdmCmnClientPortOdu4TtiStatus,
            tnDwdmCmnClientPortOtu4PreFec,
            tnDwdmCmnClientPortOtu4PostFec
        }
        STATUS         current
        DESCRIPTION    "."
        ::= { tnOpticalPortConfigGroups 122 }

    tnRsmonEgrPortConfigGroup OBJECT-GROUP
        OBJECTS {
            tnRsmonEgrPortTimod,
            tnRsmonEgrPortSigMode,
            tnRsmonEgrPortTransmittedTti,
            tnRsmonEgrPortExpectedTti,
            tnRsmonEgrPortTimDetection,
            tnRsmonEgrPortTimConsequenceAction
        }
        STATUS         current
        DESCRIPTION    "."
        ::= { tnOpticalPortConfigGroups 123 }

    tnDwdmCbrArPortConfigGroup OBJECT-GROUP
        OBJECTS {
            tnDwdmCbrArPortHdsdiRate
        }
        STATUS         current
        DESCRIPTION    "."
        ::= { tnOpticalPortConfigGroups 124 }

    tnAlpfgtPortConfigScalarsGroup OBJECT-GROUP
        OBJECTS {
            tnAlpfgtPortConfigAttributeTotal
        }
        STATUS         current
        DESCRIPTION    "."
        ::= { tnOpticalPortConfigGroups 125 }

    tnAlpfgtPortConfigGroup OBJECT-GROUP
        OBJECTS {
            tnAlpfgtPortConfigFunction
        }
        STATUS         current
        DESCRIPTION    "."
        ::= { tnOpticalPortConfigGroups 126 }

    tnOsctPortConfigScalarsGroup OBJECT-GROUP
        OBJECTS {
            tnOsctPortConfigAttributeTotal
        }
        STATUS         current
        DESCRIPTION    "."
        ::= { tnOpticalPortConfigGroups 127 }

    tnOsctPortConfigGroup OBJECT-GROUP
        OBJECTS {
            tnOsctPortConfigFunction
        }
        STATUS         current
        DESCRIPTION    "."
        ::= { tnOpticalPortConfigGroups 128 }

    tnWtocmPortConfigScalarsGroup OBJECT-GROUP
        OBJECTS {
            tnWtocmPortConfigAttributeTotal
        }
        STATUS         current
        DESCRIPTION    "."
        ::= { tnOpticalPortConfigGroups 129 }

    tnWtocmPortConfigGroup OBJECT-GROUP
        OBJECTS {
            tnWtocmPortConfigFunction
        }
        STATUS         current
        DESCRIPTION    "."
        ::= { tnOpticalPortConfigGroups 130 }

    tnWr2c88PortConfigScalarsGroup OBJECT-GROUP
        OBJECTS {
            tnWr2c88PortConfigAttributeTotal
        }
        STATUS         current
        DESCRIPTION    "."
        ::= { tnOpticalPortConfigGroups 131 }

    tnWr2c88PortConfigGroup OBJECT-GROUP
        OBJECTS {
            tnWr2c88PortConfigFunction
--            obsolete
--            tnWr2c88PortBlockerAging
        }
        STATUS         current
        DESCRIPTION    "."
        ::= { tnOpticalPortConfigGroups 132 }

    tnAm2017bPortConfigScalarsGroup OBJECT-GROUP
        OBJECTS {
            tnAm2017bPortConfigAttributeTotal
        }
        STATUS         current
        DESCRIPTION    "."
        ::= { tnOpticalPortConfigGroups 133 }

    tnAm2017bPortConfigGroup OBJECT-GROUP
        OBJECTS {
            tnAm2017bPortConfigFunction
        }
        STATUS         current
        DESCRIPTION    "."
        ::= { tnOpticalPortConfigGroups 134 }

    tnAm2325bPortConfigScalarsGroup OBJECT-GROUP
        OBJECTS {
            tnAm2325bPortConfigAttributeTotal
        }
        STATUS         current
        DESCRIPTION    "."
        ::= { tnOpticalPortConfigGroups 135 }

    tnAm2325bPortConfigGroup OBJECT-GROUP
        OBJECTS {
            tnAm2325bPortConfigFunction
        }
        STATUS         current
        DESCRIPTION    "."
        ::= { tnOpticalPortConfigGroups 136 }

    tn1dpp21PortConfigScalarsGroup OBJECT-GROUP
        OBJECTS {
            tn1dpp21PortConfigAttributeTotal
        }
        STATUS         current
        DESCRIPTION    "."
        ::= { tnOpticalPortConfigGroups 137 }

    tn1dpp21PortConfigGroup OBJECT-GROUP
        OBJECTS {
            tn1dpp21PortConfigFunction
        }
        STATUS         current
        DESCRIPTION    "."
        ::= { tnOpticalPortConfigGroups 138 }

    tnE1T1PortConfigGroup OBJECT-GROUP
        OBJECTS {
            tnE1T1MappingMode,
            tnE1T1Format,
            tnE1T1ClientEgressTimingMode,
            tnE1T1PortConfigImpedance
        }
        STATUS         current
        DESCRIPTION    "."
        ::= { tnOpticalPortConfigGroups 139 }

    tnMvacPortConfigScalarsGroup OBJECT-GROUP
        OBJECTS {
            tnMvacPortConfigAttributeTotal
        }
        STATUS         current
        DESCRIPTION    "."
        ::= { tnOpticalPortConfigGroups 140 }

    tnMvacPortConfigGroup OBJECT-GROUP
        OBJECTS {
            tnMvacPortConfigFunction,
            tnMvacPortConfigVoaMode,
            tnMvacPortConfigAttenuationModeAtten,
            tnMvacPortConfigConnToPort
        }
        STATUS         current
        DESCRIPTION    "."
        ::= { tnOpticalPortConfigGroups 141 }

    tn43scx4PortConfigScalarsGroup OBJECT-GROUP
        OBJECTS {
            tn43scx4PortConfigAttributeTotal
        }
        STATUS         current
        DESCRIPTION    "."
        ::= { tnOpticalPortConfigGroups 144 }

    tn43scx4PortConfigGroup OBJECT-GROUP
        OBJECTS {
            tn43scx4PortConfigFunction
        }
        STATUS         current
        DESCRIPTION    "."
        ::= { tnOpticalPortConfigGroups 145 }

    tnRa2pPortConfigScalarsGroup OBJECT-GROUP
        OBJECTS {
            tnRa2pPortConfigAttributeTotal
        }
        STATUS         current
        DESCRIPTION    "."
        ::= { tnOpticalPortConfigGroups 146 }

    tnRa2pPortConfigGroup OBJECT-GROUP
        OBJECTS {
            tnRa2pPortConfigFunction
        }
        STATUS         current
        DESCRIPTION    "."
        ::= { tnOpticalPortConfigGroups 147 }

    tnAm2318aPortConfigScalarsGroup OBJECT-GROUP
        OBJECTS {
            tnAm2318aPortConfigAttributeTotal
        }
        STATUS         current
        DESCRIPTION    "."
        ::= { tnOpticalPortConfigGroups 148 }

    tnAm2318aPortConfigGroup OBJECT-GROUP
        OBJECTS {
            tnAm2318aPortConfigFunction
        }
        STATUS         current
        DESCRIPTION    "."
        ::= { tnOpticalPortConfigGroups 149 }

    tnAm2125aPortConfigScalarsGroup OBJECT-GROUP
        OBJECTS {
            tnAm2125aPortConfigAttributeTotal
        }
        STATUS         current
        DESCRIPTION    "."
        ::= { tnOpticalPortConfigGroups 150 }

    tnAm2125aPortConfigGroup OBJECT-GROUP
        OBJECTS {
            tnAm2125aPortConfigFunction
        }
        STATUS         current
        DESCRIPTION    "."
        ::= { tnOpticalPortConfigGroups 151 }

    tnItluPortConfigScalarsGroup OBJECT-GROUP
        OBJECTS {
            tnItluPortConfigAttributeTotal
        }
        STATUS         current
        DESCRIPTION    "."
        ::= { tnOpticalPortConfigGroups 152 }

    tnItluPortConfigGroup OBJECT-GROUP
        OBJECTS {
            tnItluPortConfigFunction
        }
        STATUS         current
        DESCRIPTION    "."
        ::= { tnOpticalPortConfigGroups 153 }

    tnWr8c88aPortConfigScalarsGroup OBJECT-GROUP
        OBJECTS {
            tnWr8c88aPortConfigAttributeTotal
        }
        STATUS         current
        DESCRIPTION    "."
        ::= { tnOpticalPortConfigGroups 154 }

    tnWr8c88aPortConfigGroup OBJECT-GROUP
        OBJECTS {
            tnWr8c88aPortConfigFunction
        }
        STATUS         current
        DESCRIPTION    "."
        ::= { tnOpticalPortConfigGroups 155 }

    tn11dpe12ePortConfigScalarsGroup OBJECT-GROUP
        OBJECTS {
            tn11dpe12ePortConfigAttributeTotal
        }
        STATUS         current
        DESCRIPTION    "."
        ::= { tnOpticalPortConfigGroups 156 }

    tn11dpe12ePortConfigGroup OBJECT-GROUP
        OBJECTS {
            tn11dpe12ePortConfigFunction,
            tn11dpe12ePortQinQModeTPID,
            tn11dpe12ePortQinQModePVID
        }
        STATUS         current
        DESCRIPTION    "."
        ::= { tnOpticalPortConfigGroups 157 }

    tn112sx10lPortConfigScalarsGroup OBJECT-GROUP
        OBJECTS {
            tn112sx10lPortConfigAttributeTotal
        }
        STATUS         current
        DESCRIPTION    "."
        ::= { tnOpticalPortConfigGroups 158 }

    tn112sx10lPortConfigGroup OBJECT-GROUP
        OBJECTS {
            tn112sx10lPortConfigFunction
        }
        STATUS         current
        DESCRIPTION    "."
        ::= { tnOpticalPortConfigGroups 159 }

    tn112sa1lPortConfigScalarsGroup OBJECT-GROUP
        OBJECTS {
            tn112sa1lPortConfigAttributeTotal
        }
        STATUS         current
        DESCRIPTION    "."
        ::= { tnOpticalPortConfigGroups 160 }

    tn112sa1lPortConfigGroup OBJECT-GROUP
        OBJECTS {
            tn112sa1lPortConfigFunction
        }
        STATUS         current
        DESCRIPTION    "."
        ::= { tnOpticalPortConfigGroups 161 }

    tn11dpm12PortConfigScalarsGroup OBJECT-GROUP
        OBJECTS {
            tn11dpm12PortConfigAttributeTotal
        }
        STATUS         current
        DESCRIPTION    "."
        ::= { tnOpticalPortConfigGroups 162 }

    tn11dpm12PortConfigGroup OBJECT-GROUP
        OBJECTS {
            tn11dpm12PortConfigFunction
        }
        STATUS         current
        DESCRIPTION    "."
        ::= { tnOpticalPortConfigGroups 163 }

--    obsolete
--    tnWr8c88aAttenPortConfigGroup OBJECT-GROUP ::= { tnOpticalPortConfigGroups 164 }

    tnRamanPortConfigGroup OBJECT-GROUP
        OBJECTS {
            tnRamanPortFiberType,
            tnRamanPortGMinExpected,
            tnRamanPortGMaxExpected,
            tnRamanPortTiltTarget,
            tnRamanPortOperatingMode,
            tnRamanPortAgcTargetGain,
            tnRamanPortAprMode,
            tnRamanPortInitialAgcTargetGain,
            tnRamanPortAPRPulseAttempt,
            tnRamanPortConfigConnToPort,
            tnRamanPortORLThreshold,
            tnRamanPortSpanLossTh
        }
        STATUS         current
        DESCRIPTION    "."
        ::= { tnOpticalPortConfigGroups 165 }

    tnMesh4PortConfigScalarsGroup OBJECT-GROUP
        OBJECTS {
            tnMesh4PortConfigAttributeTotal
        }
        STATUS         current
        DESCRIPTION    "."
        ::= { tnOpticalPortConfigGroups 166 }

    tnMesh4PortConfigGroup OBJECT-GROUP
        OBJECTS {
            tnMesh4PortConfigFunction
        }
        STATUS         current
        DESCRIPTION    "."
        ::= { tnOpticalPortConfigGroups 167 }

--    obsolete
--    tnTcmPortConfigScalarsGroup OBJECT-GROUP OBJECT-TYPE ::= { tnOpticalPortConfigGroups 168 }
--    tnTcmPortConfigGroup        OBJECT-GROUP OBJECT-TYPE ::= { tnOpticalPortConfigGroups 169 }

    tn43sca1PortConfigScalarsGroup OBJECT-GROUP
        OBJECTS {
            tn43sca1PortConfigAttributeTotal
        }
        STATUS         current
        DESCRIPTION    "."
        ::= { tnOpticalPortConfigGroups 170 }

    tn43sca1PortConfigGroup OBJECT-GROUP
        OBJECTS {
            tn43sca1PortConfigFunction
        }
        STATUS         current
        DESCRIPTION    "."
        ::= { tnOpticalPortConfigGroups 171 }

    tn43scx4lPortConfigScalarsGroup OBJECT-GROUP
        OBJECTS {
            tn43scx4lPortConfigAttributeTotal
        }
        STATUS         current
        DESCRIPTION    "."
        ::= { tnOpticalPortConfigGroups 172 }

    tn43scx4lPortConfigGroup OBJECT-GROUP
        OBJECTS {
            tn43scx4lPortConfigFunction
        }
        STATUS         current
        DESCRIPTION    "."
        ::= { tnOpticalPortConfigGroups 173 }

    tnAm2125bPortConfigScalarsGroup OBJECT-GROUP
        OBJECTS {
            tnAm2125bPortConfigAttributeTotal
        }
        STATUS         current
        DESCRIPTION    "."
        ::= { tnOpticalPortConfigGroups 174 }

    tnAm2125bPortConfigGroup OBJECT-GROUP
        OBJECTS {
            tnAm2125bPortConfigFunction
        }
        STATUS         current
        DESCRIPTION    "."
        ::= { tnOpticalPortConfigGroups 175 }

    tn112snx10PortConfigScalarsGroup OBJECT-GROUP
        OBJECTS {
            tn112snx10PortConfigAttributeTotal
        }
        STATUS         current
        DESCRIPTION    "."
        ::= { tnOpticalPortConfigGroups 176 }

    tn112snx10PortConfigGroup OBJECT-GROUP
        OBJECTS {
            tn112snx10PortConfigFunction
        }
        STATUS         current
        DESCRIPTION    "."
        ::= { tnOpticalPortConfigGroups 177 }

    tn112sna1PortConfigScalarsGroup OBJECT-GROUP
        OBJECTS {
            tn112sna1PortConfigAttributeTotal
        }
        STATUS         current
        DESCRIPTION    "."
        ::= { tnOpticalPortConfigGroups 178 }

    tn112sna1PortConfigGroup OBJECT-GROUP
        OBJECTS {
            tn112sna1PortConfigFunction
        }
        STATUS         current
        DESCRIPTION    "."
        ::= { tnOpticalPortConfigGroups 179 }

--    obsolete
--    tn11qta4PortConfigScalarsGroup OBJECT-GROUP ::= { tnOpticalPortConfigGroups 180 }
--    tn11qta4PortConfigGroup        OBJECT-GROUP ::= { tnOpticalPortConfigGroups 181 }

    tn1dpp24mPortConfigScalarsGroup OBJECT-GROUP
        OBJECTS {
            tn1dpp24mPortConfigAttributeTotal
        }
        STATUS         current
        DESCRIPTION    "."
        ::= { tnOpticalPortConfigGroups 182 }

    tn1dpp24mPortConfigGroup OBJECT-GROUP
        OBJECTS {
            tn1dpp24mPortConfigFunction
        }
        STATUS         current
        DESCRIPTION    "."
        ::= { tnOpticalPortConfigGroups 183 }

    tnDwdmCmnOtu3Odu3ClientPortConfigGroup OBJECT-GROUP
        OBJECTS {
            tnDwdmCmnClientPortOchOtu3FecMode,
            tnDwdmCmnClientPortOchOtu3Rate,
            tnDwdmCmnClientPortOtu3TransmittedTti,
            tnDwdmCmnClientPortOtu3ExpectedTti,
            tnDwdmCmnClientPortOtu3TimConsequenceAction,
            tnDwdmCmnClientPortOtu3TimDetectionMode,
            tnDwdmCmnClientPortOdu3TransmittedTti,
            tnDwdmCmnClientPortOdu3ExpectedTti,
            tnDwdmCmnClientPortOdu3TimDetectionMode
        }
        STATUS         current
        DESCRIPTION    "."
        ::= { tnOpticalPortConfigGroups 184 }

    tnul43scupPortConfigScalarsGroup OBJECT-GROUP
        OBJECTS {
            tnul43scupPortConfigAttributeTotal
        }
        STATUS         current
        DESCRIPTION    "."
        ::= { tnOpticalPortConfigGroups 185 }

    tnul43scupPortConfigGroup OBJECT-GROUP
        OBJECTS {
            tnul43scupPortConfigFunction
        }
        STATUS         current
        DESCRIPTION    "."
        ::= { tnOpticalPortConfigGroups 186 }

    tnul11qcupPortConfigScalarsGroup OBJECT-GROUP
        OBJECTS {
            tnul11qcupPortConfigAttributeTotal
        }
        STATUS         current
        DESCRIPTION    "."
        ::= { tnOpticalPortConfigGroups 187 }

    tnul11qcupPortConfigGroup OBJECT-GROUP
        OBJECTS {
            tnul11qcupPortConfigFunction
        }
        STATUS         current
        DESCRIPTION    "."
        ::= { tnOpticalPortConfigGroups 188 }

    tn11qpen4PortConfigScalarsGroup OBJECT-GROUP
        OBJECTS {
            tn11qpen4PortConfigAttributeTotal
        }
        STATUS         current
        DESCRIPTION    "."
        ::= { tnOpticalPortConfigGroups 189 }

    tn11qpen4PortConfigGroup OBJECT-GROUP
        OBJECTS {
            tn11qpen4PortConfigFunction,
            tn11qpen4PortConfigEncryptionOperateKeySwitch,
            tn11qpen4PortConfigEncryptionState,
            tn11qpen4PortConfigEncryptionNextKey,
            tn11qpen4PortConfigEncryptionWKAT
        }
        STATUS         current
        DESCRIPTION    "."
        ::= { tnOpticalPortConfigGroups 190 }

    tn43scx4ePortConfigScalarsGroup OBJECT-GROUP
        OBJECTS {
            tn43scx4ePortConfigAttributeTotal
        }
        STATUS         current
        DESCRIPTION    "."
        ::= { tnOpticalPortConfigGroups 191 }

    tn43scx4ePortConfigGroup OBJECT-GROUP
        OBJECTS {
            tn43scx4ePortConfigFunction
        }
        STATUS         current
        DESCRIPTION    "."
        ::= { tnOpticalPortConfigGroups 192 }

    tn43scge1PortConfigScalarsGroup OBJECT-GROUP
        OBJECTS {
            tn43scge1PortConfigAttributeTotal
        }
        STATUS         current
        DESCRIPTION    "."
        ::= { tnOpticalPortConfigGroups 193 }

    tn43scge1PortConfigGroup OBJECT-GROUP
        OBJECTS {
            tn43scge1PortConfigFunction
        }
        STATUS         current
        DESCRIPTION    "."
        ::= { tnOpticalPortConfigGroups 194 }

    tn11qpe24PortConfigScalarsGroup OBJECT-GROUP
        OBJECTS {
            tn11qpe24PortConfigAttributeTotal
        }
        STATUS         current
        DESCRIPTION    "."
        ::= { tnOpticalPortConfigGroups 195 }

    tn11qpe24PortConfigGroup OBJECT-GROUP
        OBJECTS {
            tn11qpe24PortConfigFunction
        }
        STATUS         current
        DESCRIPTION    "."
        ::= { tnOpticalPortConfigGroups 196 }

    tn11star1aPortConfigScalarsGroup OBJECT-GROUP
        OBJECTS {
            tn11star1aPortConfigAttributeTotal
        }
        STATUS         current
        DESCRIPTION    "."
        ::= { tnOpticalPortConfigGroups 197 }

    tn11star1aPortConfigGroup OBJECT-GROUP
        OBJECTS {
            tn11star1aPortConfigFunction
        }
        STATUS         current
        DESCRIPTION    "."
        ::= { tnOpticalPortConfigGroups 198 }

    tnMvac8bPortConfigScalarsGroup OBJECT-GROUP
        OBJECTS {
            tnMvac8bPortConfigAttributeTotal
        }
        STATUS         current
        DESCRIPTION    "."
        ::= { tnOpticalPortConfigGroups 199 }

    tnMvac8bPortConfigGroup OBJECT-GROUP
        OBJECTS {
            tnMvac8bPortConfigFunction
        }
        STATUS         current
        DESCRIPTION    "."
        ::= { tnOpticalPortConfigGroups 200 }

    tnWssAttenPortConfigScalarsGroup OBJECT-GROUP
        OBJECTS {
            tnWssAttenPortConfigAttributeTotal
        }
        STATUS         current
        DESCRIPTION    "."
        ::= { tnOpticalPortConfigGroups 201 }

    tnWssAttenPortConfigGroup OBJECT-GROUP
        OBJECTS {
            tnWssAttenPortConfigWssAtten
        }
        STATUS         current
        DESCRIPTION    "."
        ::= { tnOpticalPortConfigGroups 202 }

    tnWr8c88afPortConfigScalarsGroup OBJECT-GROUP
        OBJECTS {
            tnWr8c88afPortConfigAttributeTotal
        }
        STATUS         current
        DESCRIPTION    "."
        ::= { tnOpticalPortConfigGroups 203 }

    tnWr8c88afPortConfigGroup OBJECT-GROUP
        OBJECTS {
            tnWr8c88afPortConfigFunction
        }
        STATUS         current
        DESCRIPTION    "."
        ::= { tnOpticalPortConfigGroups 204 }

    tncl10an10gPortConfigScalarsGroup OBJECT-GROUP
        OBJECTS {
            tncl10an10gPortConfigAttributeTotal
        }
        STATUS         current
        DESCRIPTION    "."
        ::= { tnOpticalPortConfigGroups 205 }

    tncl10an10gPortConfigGroup OBJECT-GROUP
        OBJECTS {
            tncl10an10gPortConfigFunction
        }
        STATUS         current
        DESCRIPTION    "."
        ::= { tnOpticalPortConfigGroups 206 }

    tncl24anmPortConfigScalarsGroup OBJECT-GROUP
        OBJECTS {
            tncl24anmPortConfigAttributeTotal
        }
        STATUS         current
        DESCRIPTION    "."
        ::= { tnOpticalPortConfigGroups 207 }

    tncl24anmPortConfigGroup OBJECT-GROUP
        OBJECTS {
            tncl24anmPortConfigFunction
        }
        STATUS         current
        DESCRIPTION    "."
        ::= { tnOpticalPortConfigGroups 208 }

    tnOpsbPortConfigScalarsGroup OBJECT-GROUP
        OBJECTS {
            tnOpsbPortConfigAttributeTotal
        }
        STATUS         current
        DESCRIPTION    "."
        ::= { tnOpticalPortConfigGroups 209 }

    tnOpsbPortConfigGroup OBJECT-GROUP
        OBJECTS {
            tnOpsbPortConfigFunction
        }
        STATUS         current
        DESCRIPTION    "."
        ::= { tnOpticalPortConfigGroups 210 }

    tnOpsPortConfigScalarsGroup OBJECT-GROUP
        OBJECTS {
            tnOpsPortConfigAttributeTotal
        }
        STATUS         current
        DESCRIPTION    "."
        ::= { tnOpticalPortConfigGroups 211 }

    tnOpsPortConfigGroup OBJECT-GROUP
        OBJECTS {
            tnOpsPortConfigSwitchingThreshold,
            tnOpsPortConfigSwitchingThresholdTolerance,
            tnOpsPortConfigTransmitAttenuation,
            tnOpsPortConfigSwitchingThreshCalcControl,
            tnOpsPortTargetReceivedPower,
            tnOpsPortPaired,
            tnOpsPortConfigChannelFreq,
            tnOpsPortConfigSwitchingThresholdPsd,
            tnOpsPortConfigExpectedInputPower
        }
        STATUS         current
        DESCRIPTION    "."
        ::= { tnOpticalPortConfigGroups 212 }

    tn11dpe12aPortConfigScalarsGroup OBJECT-GROUP
        OBJECTS {
            tn11dpe12aPortConfigAttributeTotal
        }
        STATUS         current
        DESCRIPTION    "."
        ::= { tnOpticalPortConfigGroups 213 }

    tn11dpe12aPortConfigGroup OBJECT-GROUP
        OBJECTS {
            tn11dpe12aPortConfigFunction,
            tn11dpe12aPortConfigQinQModeTPID,
            tn11dpe12aPortConfigQinQModePVID,
            tn11dpe12aPortConfigLPTConsequenceAction,
            tn11dpe12aPortConfigMtu,
            tn11dpe12aPortConfigPortRole,
            tn11dpe12aPortConfigPtpTrans,
            tn11dpe12aPortConfigCompatibilityMode,
            tn11dpe12aPortConfigFlowControl
        }
        STATUS         current
        DESCRIPTION    "."
        ::= { tnOpticalPortConfigGroups 214 }

    tnul130scupPortConfigScalarsGroup OBJECT-GROUP
        OBJECTS {
            tnul130scupPortConfigAttributeTotal
        }
        STATUS         current
        DESCRIPTION    "."
        ::= { tnOpticalPortConfigGroups 215 }

    tnul130scupPortConfigGroup OBJECT-GROUP
        OBJECTS {
            tnul130scupPortConfigFunction
        }
        STATUS         current
        DESCRIPTION    "."
        ::= { tnOpticalPortConfigGroups 216 }

    tn130scx10PortConfigScalarsGroup OBJECT-GROUP
        OBJECTS {
            tn130scx10PortConfigAttributeTotal
        }
        STATUS         current
        DESCRIPTION    "."
        ::= { tnOpticalPortConfigGroups 217 }

    tn130scx10PortConfigGroup OBJECT-GROUP
        OBJECTS {
            tn130scx10PortConfigFunction
        }
        STATUS         current
        DESCRIPTION    "."
        ::= { tnOpticalPortConfigGroups 218 }

    tnA2p2125PortConfigScalarsGroup OBJECT-GROUP
        OBJECTS {
            tnA2p2125PortConfigAttributeTotal
        }
        STATUS         current
        DESCRIPTION    "."
        ::= { tnOpticalPortConfigGroups 219 }

    tnA2p2125PortConfigGroup OBJECT-GROUP
        OBJECTS {
            tnA2p2125PortConfigFunction
        }
        STATUS         current
        DESCRIPTION    "."
        ::= { tnOpticalPortConfigGroups 220 }

    tn4qpa8PortConfigScalarsGroup OBJECT-GROUP
        OBJECTS {
            tn4qpa8PortConfigAttributeTotal
        }
        STATUS         current
        DESCRIPTION    "."
        ::= { tnOpticalPortConfigGroups 221 }

    tn4qpa8PortConfigGroup OBJECT-GROUP
        OBJECTS {
            tn4qpa8PortConfigFunction,
            tn4qpa8PortConfigTtpPresent
        }
        STATUS         current
        DESCRIPTION    "."
        ::= { tnOpticalPortConfigGroups 222 }

    tnOt112pdm11PortConfigScalarsGroup OBJECT-GROUP
        OBJECTS {
            tnOt112pdm11PortConfigAttributeTotal
        }
        STATUS         current
        DESCRIPTION    "."
        ::= { tnOpticalPortConfigGroups 223 }

    tnOt112pdm11PortConfigGroup OBJECT-GROUP
        OBJECTS {
            tnOt112pdm11PortConfigFunction
        }
        STATUS         current
        DESCRIPTION    "."
        ::= { tnOpticalPortConfigGroups 224 }

    tnWtocmaPortConfigScalarsGroup OBJECT-GROUP
        OBJECTS {
            tnWtocmaPortConfigAttributeTotal
        }
        STATUS         current
        DESCRIPTION    "."
        ::= { tnOpticalPortConfigGroups 225 }

    tnWtocmaPortConfigGroup OBJECT-GROUP
        OBJECTS {
            tnWtocmaPortConfigFunction,
            tnWtocmaPortConfigOsnrMeasure,
            tnWtocmaPortConfigOsnrClear
        }
        STATUS         current
        DESCRIPTION    "."
        ::= { tnOpticalPortConfigGroups 226 }

    tnPtpctlPortConfigScalarsGroup OBJECT-GROUP
        OBJECTS {
            tnPtpctlPortConfigAttributeTotal
        }
        STATUS         current
        DESCRIPTION    "."
        ::= { tnOpticalPortConfigGroups 227 }

    tnPtpctlPortConfigGroup OBJECT-GROUP
        OBJECTS {
            tnPtpctlPortConfigFunction,
            tnPtpctlPortConfigFiberConnectPort
        }
        STATUS         current
        DESCRIPTION    "."
        ::= { tnOpticalPortConfigGroups 228 }

    tnPtpioPortConfigScalarsGroup OBJECT-GROUP
        OBJECTS {
            tnPtpioPortConfigAttributeTotal
        }
        STATUS         current
        DESCRIPTION    "."
        ::= { tnOpticalPortConfigGroups 229 }

    tnPtpioPortConfigGroup OBJECT-GROUP
        OBJECTS {
            tnPtpioPortConfigFunction,
            tnPtpioPortConfigSigPortConnFromPort,
            tnPtpioPortConfigSigPortConnToPort
        }
        STATUS         current
        DESCRIPTION    "."
        ::= { tnOpticalPortConfigGroups 230 }

    tnIo24et1gbPortConfigScalarsGroup OBJECT-GROUP
        OBJECTS {
            tnIo24et1gbPortConfigAttributeTotal
        }
        STATUS         current
        DESCRIPTION    "."
        ::= { tnOpticalPortConfigGroups 231 }

    tnIo24et1gbPortConfigGroup OBJECT-GROUP
        OBJECTS {
            tnIo24et1gbPortConfigFunction
        }
        STATUS         current
        DESCRIPTION    "."
        ::= { tnOpticalPortConfigGroups 232 }

    tnDwdmIoPortConfigScalarsGroup OBJECT-GROUP
        OBJECTS {
            tnDwdmIoPortConfigAttributeTotal
        }
        STATUS         current
        DESCRIPTION    "."
        ::= { tnOpticalPortConfigGroups 233 }

    tnDwdmIoPortConfigGroup OBJECT-GROUP
        OBJECTS {
            tnDwdmIoPortRole
        }
        STATUS         current
        DESCRIPTION    "."
        ::= { tnOpticalPortConfigGroups 234 }

    tnIo4an10gPortConfigScalarsGroup OBJECT-GROUP
        OBJECTS {
            tnIo4an10gPortConfigAttributeTotal
        }
        STATUS         current
        DESCRIPTION    "."
        ::= { tnOpticalPortConfigGroups 235 }

    tnIo4an10gPortConfigGroup OBJECT-GROUP
        OBJECTS {
            tnIo4an10gPortConfigFunction
        }
        STATUS         current
        DESCRIPTION    "."
        ::= { tnOpticalPortConfigGroups 236 }

    tnIo8et1gbPortConfigScalarsGroup OBJECT-GROUP
        OBJECTS {
            tnIo8et1gbPortConfigAttributeTotal
        }
        STATUS         current
        DESCRIPTION    "."
        ::= { tnOpticalPortConfigGroups 237 }

    tnIo8et1gbPortConfigGroup OBJECT-GROUP
        OBJECTS {
            tnIo8et1gbPortConfigFunction
        }
        STATUS         current
        DESCRIPTION    "."
        ::= { tnOpticalPortConfigGroups 238 }

    tnIo10et10gPortConfigScalarsGroup OBJECT-GROUP
        OBJECTS {
            tnIo10et10gPortConfigAttributeTotal
        }
        STATUS         current
        DESCRIPTION    "."
        ::= { tnOpticalPortConfigGroups 239 }

    tnIo10et10gPortConfigGroup OBJECT-GROUP
        OBJECTS {
            tnIo10et10gPortConfigFunction
        }
        STATUS         current
        DESCRIPTION    "."
        ::= { tnOpticalPortConfigGroups 240 }

    tnUl11qcupcPortConfigScalarsGroup OBJECT-GROUP
        OBJECTS {
            tnUl11qcupcPortConfigAttributeTotal
        }
        STATUS         current
        DESCRIPTION    "."
        ::= { tnOpticalPortConfigGroups 241 }

    tnUl11qcupcPortConfigGroup OBJECT-GROUP
        OBJECTS {
            tnUl11qcupcPortConfigFunction
        }
        STATUS         current
        DESCRIPTION    "."
        ::= { tnOpticalPortConfigGroups 242 }

    tnOt520scx4PortConfigScalarsGroup OBJECT-GROUP
        OBJECTS {
            tnOt520scx4PortConfigAttributeTotal
        }
        STATUS         current
        DESCRIPTION    "."
        ::= { tnOpticalPortConfigGroups 243 }

    tnOt520scx4PortConfigGroup OBJECT-GROUP
        OBJECTS {
            tnOt520scx4PortConfigFunction
        }
        STATUS         current
        DESCRIPTION    "."
        ::= { tnOpticalPortConfigGroups 244 }

    tnWssAprPortConfigScalarsGroup OBJECT-GROUP
        OBJECTS {
            tnWssAprPortConfigAttributeTotal
        }
        STATUS         current
        DESCRIPTION    "."
        ::= { tnOpticalPortConfigGroups 245 }

    tnWssAprPortConfigGroup OBJECT-GROUP
        OBJECTS {
            tnWssAprPortConfigAprHoldOffTime
        }
        STATUS         current
        DESCRIPTION    "."
        ::= { tnOpticalPortConfigGroups 246 }

    tnPowerFilterPortConfigScalarsGroup OBJECT-GROUP
        OBJECTS {
            tnPowerFilterPortConfigAttributeTotal
        }
        STATUS         current
        DESCRIPTION    "."
        ::= { tnOpticalPortConfigGroups 247 }

    tnPowerFilterPortConfigGroup OBJECT-GROUP
        OBJECTS {
            tnPowerFilterPortConfigFunction
        }
        STATUS         current
        DESCRIPTION    "."
        ::= { tnOpticalPortConfigGroups 248 }

    tn11ope8PortConfigScalarsGroup OBJECT-GROUP
        OBJECTS {
            tn11ope8PortConfigAttributeTotal
        }
        STATUS         current
        DESCRIPTION    "."
        ::= { tnOpticalPortConfigGroups 249 }

    tn11ope8PortConfigGroup OBJECT-GROUP
        OBJECTS {
            tn11ope8PortConfigFunction
        }
        STATUS         current
        DESCRIPTION    "."
        ::= { tnOpticalPortConfigGroups 250 }

    tn11qce12xPortConfigScalarsGroup OBJECT-GROUP
        OBJECTS {
            tn11qce12xPortConfigAttributeTotal
        }
        STATUS         current
        DESCRIPTION    "."
        ::= { tnOpticalPortConfigGroups 251 }

    tn11qce12xPortConfigGroup OBJECT-GROUP
        OBJECTS {
            tn11qce12xPortConfigFunction
        }
        STATUS         current
        DESCRIPTION    "."
        ::= { tnOpticalPortConfigGroups 252 }

    tnAm2625aPortConfigScalarsGroup OBJECT-GROUP
        OBJECTS {
            tnAm2625aPortConfigAttributeTotal
        }
        STATUS         current
        DESCRIPTION    "."
        ::= { tnOpticalPortConfigGroups 253 }

    tnAm2625aPortConfigGroup OBJECT-GROUP
        OBJECTS {
            tnAm2625aPortConfigFunction
        }
        STATUS         current
        DESCRIPTION    "."
        ::= { tnOpticalPortConfigGroups 254 }

    tnAm2032aPortConfigScalarsGroup OBJECT-GROUP
        OBJECTS {
            tnAm2032aPortConfigAttributeTotal
        }
        STATUS         current
        DESCRIPTION    "."
        ::= { tnOpticalPortConfigGroups 255 }

    tnAm2032aPortConfigGroup OBJECT-GROUP
        OBJECTS {
            tnAm2032aPortConfigFunction
        }
        STATUS         current
        DESCRIPTION    "."
        ::= { tnOpticalPortConfigGroups 256 }

    tnOt260scx2PortConfigScalarsGroup OBJECT-GROUP
        OBJECTS {
            tnOt260scx2PortConfigAttributeTotal
        }
        STATUS         current
        DESCRIPTION    "."
        ::= { tnOpticalPortConfigGroups 257 }

    tnOt260scx2PortConfigGroup OBJECT-GROUP
        OBJECTS {
            tnOt260scx2PortConfigFunction
        }
        STATUS         current
        DESCRIPTION    "."
        ::= { tnOpticalPortConfigGroups 258 }

    tnOt130snx10PortConfigScalarsGroup OBJECT-GROUP
        OBJECTS {
            tnOt130snx10PortConfigAttributeTotal
        }
        STATUS         current
        DESCRIPTION    "."
        ::= { tnOpticalPortConfigGroups 259 }

    tnOt130snx10PortConfigGroup OBJECT-GROUP
        OBJECTS {
            tnOt130snx10PortConfigFunction
        }
        STATUS         current
        DESCRIPTION    "."
        ::= { tnOpticalPortConfigGroups 260 }

    tnIo24anmbPortConfigScalarsGroup OBJECT-GROUP
        OBJECTS {
            tnIo24anmbPortConfigAttributeTotal
        }
        STATUS         current
        DESCRIPTION    "."
        ::= { tnOpticalPortConfigGroups 261 }

    tnIo24anmbPortConfigGroup OBJECT-GROUP
        OBJECTS {
            tnIo24anmbPortConfigFunction
        }
        STATUS         current
        DESCRIPTION    "."
        ::= { tnOpticalPortConfigGroups 262 }

    tnOt11dpm8PortConfigScalarsGroup OBJECT-GROUP
        OBJECTS {
            tnOt11dpm8PortConfigAttributeTotal
        }
        STATUS         current
        DESCRIPTION    "."
        ::= { tnOpticalPortConfigGroups 263 }

    tnOt11dpm8PortConfigGroup OBJECT-GROUP
        OBJECTS {
            tnOt11dpm8PortConfigFunction,
            tnOt11dpm8PortConfigTtpPresent
        }
        STATUS         current
        DESCRIPTION    "."
        ::= { tnOpticalPortConfigGroups 264 }

    tnOt11dpm4mPortConfigScalarsGroup OBJECT-GROUP
        OBJECTS {
            tnOt11dpm4mPortConfigAttributeTotal
        }
        STATUS         current
        DESCRIPTION    "."
        ::= { tnOpticalPortConfigGroups 265 }

    tnOt11dpm4mPortConfigGroup OBJECT-GROUP
        OBJECTS {
            tnOt11dpm4mPortConfigFunction
        }
        STATUS         current
        DESCRIPTION    "."
        ::= { tnOpticalPortConfigGroups 266 }

    tnUl130scupbPortConfigScalarsGroup OBJECT-GROUP
        OBJECTS {
            tnUl130scupbPortConfigAttributeTotal
        }
        STATUS         current
        DESCRIPTION    "."
        ::= { tnOpticalPortConfigGroups 267 }

    tnUl130scupbPortConfigGroup OBJECT-GROUP
        OBJECTS {
            tnUl130scupbPortConfigFunction
        }
        STATUS         current
        DESCRIPTION    "."
        ::= { tnOpticalPortConfigGroups 268 }

    tnOt112sdx11PortConfigScalarsGroup OBJECT-GROUP
        OBJECTS {
            tnOt112sdx11PortConfigAttributeTotal
        }
        STATUS         current
        DESCRIPTION    "."
        ::= { tnOpticalPortConfigGroups 269 }

    tnOt112sdx11PortConfigGroup OBJECT-GROUP
        OBJECTS {
            tnOt112sdx11PortConfigFunction,
            tnOt112sdx11PortConfigLinkGroupId,
            tnOt112sdx11ProgrammedNwOutputPower
        }
        STATUS         current
        DESCRIPTION    "."
        ::= { tnOpticalPortConfigGroups 270 }

    tnAa2donwPortConfigScalarsGroup OBJECT-GROUP
        OBJECTS {
            tnAa2donwPortConfigAttributeTotal
        }
        STATUS         current
        DESCRIPTION    "."
        ::= { tnOpticalPortConfigGroups 271 }

    tnAa2donwPortConfigGroup OBJECT-GROUP
        OBJECTS {
            tnAa2donwPortConfigFunction
        }
        STATUS         current
        DESCRIPTION    "."
        ::= { tnOpticalPortConfigGroups 272 }

    tnOt130sca1PortConfigScalarsGroup OBJECT-GROUP
        OBJECTS {
            tnOt130sca1PortConfigAttributeTotal
        }
        STATUS         current
        DESCRIPTION    "."
        ::= { tnOpticalPortConfigGroups 273 }

    tnOt130sca1PortConfigGroup OBJECT-GROUP
        OBJECTS {
            tnOt130sca1PortConfigFunction
        }
        STATUS         current
        DESCRIPTION    "."
        ::= { tnOpticalPortConfigGroups 274 }

    tnIo10an10gbPortConfigScalarsGroup OBJECT-GROUP
        OBJECTS {
            tnIo10an10gbPortConfigAttributeTotal
        }
        STATUS         current
        DESCRIPTION    "."
        ::= { tnOpticalPortConfigGroups 275 }

    tnIo10an10gbPortConfigGroup OBJECT-GROUP
        OBJECTS {
            tnIo10an10gbPortConfigFunction
        }
        STATUS         current
        DESCRIPTION    "."
        ::= { tnOpticalPortConfigGroups 276 }

    tnIo10et10gbPortConfigScalarsGroup OBJECT-GROUP
        OBJECTS {
            tnIo10et10gbPortConfigAttributeTotal
        }
        STATUS         current
        DESCRIPTION    "."
        ::= { tnOpticalPortConfigGroups 277 }

    tnIo10et10gbPortConfigGroup OBJECT-GROUP
        OBJECTS {
            tnIo10et10gbPortConfigFunction
        }
        STATUS         current
        DESCRIPTION    "."
        ::= { tnOpticalPortConfigGroups 278 }

    tnPsc1x6PortConfigScalarsGroup OBJECT-GROUP
        OBJECTS {
            tnPsc1x6PortConfigAttributeTotal
        }
        STATUS         current
        DESCRIPTION    "."
        ::= { tnOpticalPortConfigGroups 279 }

    tnPsc1x6PortConfigGroup OBJECT-GROUP
        OBJECTS {
            tnPsc1x6PortConfigFunction
        }
        STATUS         current
        DESCRIPTION    "."
        ::= { tnOpticalPortConfigGroups 280 }

    tnWr20tfPortConfigScalarsGroup OBJECT-GROUP
        OBJECTS {
            tnWr20tfPortConfigAttributeTotal
        }
        STATUS         current
        DESCRIPTION    "."
        ::= { tnOpticalPortConfigGroups 281 }

    tnWr20tfPortConfigGroup OBJECT-GROUP
        OBJECTS {
            tnWr20tfPortConfigFunction,
            tnWr20tfPortConfigDropInitTargetPower,
            tnWr20tfPortConfigExpressTargetPower,
            tnWr20tfPortConfigDropMaxTargetPower,
            tnWr20tfPortConfigDropMinTargetPower
        }
        STATUS         current
        DESCRIPTION    "."
        ::= { tnOpticalPortConfigGroups 282 }

    tnWtocmfPortConfigScalarsGroup OBJECT-GROUP
        OBJECTS {
            tnWtocmfPortConfigAttributeTotal
        }
        STATUS         current
        DESCRIPTION    "."
        ::= { tnOpticalPortConfigGroups 283 }

    tnWtocmfPortConfigGroup OBJECT-GROUP
        OBJECTS {
            tnWtocmfPortConfigFunction
        }
        STATUS         current
        DESCRIPTION    "."
        ::= { tnOpticalPortConfigGroups 284 }

    tnAswgPortConfigScalarsGroup OBJECT-GROUP
        OBJECTS {
            tnAswgPortConfigAttributeTotal
        }
        STATUS         current
        DESCRIPTION    "."
        ::= { tnOpticalPortConfigGroups 285 }

    tnAswgPortConfigGroup OBJECT-GROUP
        OBJECTS {
            tnAswgPortConfigFunction
        }
        STATUS         current
        DESCRIPTION    "."
        ::= { tnOpticalPortConfigGroups 286 }

    tnA4pswgPortConfigScalarsGroup OBJECT-GROUP
        OBJECTS {
            tnA4pswgPortConfigAttributeTotal
        }
        STATUS         current
        DESCRIPTION    "."
        ::= { tnOpticalPortConfigGroups 287 }

    tnA4pswgPortConfigGroup OBJECT-GROUP
        OBJECTS {
            tnA4pswgPortConfigFunction
        }
        STATUS         current
        DESCRIPTION    "."
        ::= { tnOpticalPortConfigGroups 288 }

    tnOtdrPortConfigScalarsGroup OBJECT-GROUP
        OBJECTS {
            tnOtdrPortConfigAttributeTotal
        }
        STATUS         current
        DESCRIPTION    "."
        ::= { tnOpticalPortConfigGroups 289 }

    tnOtdrPortConfigGroup OBJECT-GROUP
        OBJECTS {
            tnOtdrPortConfigFunction,
            tnOtdrPortConfigConnAddress
        }
        STATUS         current
        DESCRIPTION    "."
        ::= { tnOpticalPortConfigGroups 290 }

    tnWr20tfmPortConfigScalarsGroup OBJECT-GROUP
        OBJECTS {
            tnWr20tfmPortConfigAttributeTotal
        }
        STATUS         current
        DESCRIPTION    "."
        ::= { tnOpticalPortConfigGroups 291 }

    tnWr20tfmPortConfigGroup OBJECT-GROUP
        OBJECTS {
            tnWr20tfmPortConfigFunction,
            tnWr20tfmPortConfigDropInitTargetPower,
            tnWr20tfmPortConfigExpressTargetPower,
            tnWr20tfmPortConfigDropMaxTargetPower,
            tnWr20tfmPortConfigDropMinTargetPower,
--            obsolete
--            tnWr20tfmPortConfigExecuteForcedDropDisposition,
            tnWr20tfmPortConfigEndForcedDropDisposition,
--            obsolete
--            tnWr20tfmPortConfigExecuteForcedAddDisposition,
            tnWr20tfmPortConfigEndForcedAddDisposition,
            tnWr20tfmPortConfigForceAllchannelsDropDisposition,
            tnWr20tfmPortConfigForceAllchannelsAddDisposition
        }
        STATUS         current
        DESCRIPTION    "."
        ::= { tnOpticalPortConfigGroups 292 }

    tnAar8aPortConfigScalarsGroup OBJECT-GROUP
        OBJECTS {
            tnAar8aPortConfigAttributeTotal
        }
        STATUS         current
        DESCRIPTION    "."
        ::= { tnOpticalPortConfigGroups 293 }

    tnAar8aPortConfigGroup OBJECT-GROUP
        OBJECTS {
            tnAar8aPortConfigFunction
        }
        STATUS         current
        DESCRIPTION    "."
        ::= { tnOpticalPortConfigGroups 294 }

    tnMcs8x16PortConfigScalarsGroup OBJECT-GROUP
        OBJECTS {
            tnMcs8x16PortConfigAttributeTotal
        }
        STATUS         current
        DESCRIPTION    "."
        ::= { tnOpticalPortConfigGroups 295 }

    tnMcs8x16PortConfigGroup OBJECT-GROUP
        OBJECTS {
            tnMcs8x16PortConfigFunction
        }
        STATUS         current
        DESCRIPTION    "."
        ::= { tnOpticalPortConfigGroups 296 }

    tnMsh8fsmPortConfigScalarsGroup OBJECT-GROUP
        OBJECTS {
            tnMsh8fsmPortConfigAttributeTotal
        }
        STATUS         current
        DESCRIPTION    "."
        ::= { tnOpticalPortConfigGroups 297 }

    tnMsh8fsmPortConfigGroup OBJECT-GROUP
        OBJECTS {
            tnMsh8fsmPortConfigFunction
        }
        STATUS         current
        DESCRIPTION    "."
        ::= { tnOpticalPortConfigGroups 298 }

    tnMcsPortConfigScalarsGroup OBJECT-GROUP
        OBJECTS {
            tnMcsPortConfigAttributeTotal
        }
        STATUS         current
        DESCRIPTION    "."
        ::= { tnOpticalPortConfigGroups 299 }

    tnMcsPortConfigGroup OBJECT-GROUP
        OBJECTS {
            tnMcsPortConfigTargetForDispositionForce,
            tnMcsPortConfigExecuteForceDispositionToTarget
        }
        STATUS         current
        DESCRIPTION    "."
        ::= { tnOpticalPortConfigGroups 300 }

    tnAarPortConfigScalarsGroup OBJECT-GROUP
        OBJECTS {
            tnAarPortConfigAttributeTotal
        }
        STATUS         current
        DESCRIPTION    "."
        ::= { tnOpticalPortConfigGroups 301 }

    tnAarPortConfigGroup OBJECT-GROUP
        OBJECTS {
            tnAarPortConfigOperatingMode,
            tnAarPortConfigPowerGainTarget,
            tnAarPortConfigSignalPowerTarget,
            tnAarPortConfigOaInputChannelPowerTargetSpecified,
            tnAarPortConfigOaInputChannelPowerTargetActive
        }
        STATUS         current
        DESCRIPTION    "."
        ::= { tnOpticalPortConfigGroups 302 }

    tnWr20tfmPortChannelConfigScalarsGroup OBJECT-GROUP
        OBJECTS {
            tnWr20tfmPortChannelConfigAttributeTotal
        }
        STATUS         current
        DESCRIPTION    "."
        ::= { tnOpticalPortConfigGroups 303 }

    tnWr20tfmPortChannelConfigGroup OBJECT-GROUP
        OBJECTS {
            tnWr20tfmPortChannelConfigTargetForcedDropDisposition,
            tnWr20tfmPortChannelConfigTargetForcedAddDisposition
        }
        STATUS         current
        DESCRIPTION    "."
        ::= { tnOpticalPortConfigGroups 304 }

    tnMpoPortConfigScalarsGroup OBJECT-GROUP
        OBJECTS {
            tnMpoPortConfigAttributeTotal
        }
        STATUS         current
        DESCRIPTION    "."
        ::= { tnOpticalPortConfigGroups 305 }

    tnMpoPortChannelConfigGroup OBJECT-GROUP
        OBJECTS {
            tnMpoPortConfigFarEndIfIndex,
            tnMpoPortConfigFarEndType,
            tnMpoPortConfigDescription
        }
        STATUS         current
        DESCRIPTION    "."
        ::= { tnOpticalPortConfigGroups 306 }

    tnIo4an100gPortConfigScalarsGroup OBJECT-GROUP
        OBJECTS {
            tnIo4an100gPortConfigAttributeTotal
        }
        STATUS         current
        DESCRIPTION    "."
        ::= { tnOpticalPortConfigGroups 307 }

    tnIo4an100gPortConfigGroup OBJECT-GROUP
        OBJECTS {
            tnIo4an100gPortConfigFunction
        }
        STATUS         current
        DESCRIPTION    "."
        ::= { tnOpticalPortConfigGroups 308 }

    tnIo30an10gPortConfigScalarsGroup OBJECT-GROUP
        OBJECTS {
            tnIo30an10gPortConfigAttributeTotal
        }
        STATUS         current
        DESCRIPTION    "."
        ::= { tnOpticalPortConfigGroups 309 }

    tnIo30an10gPortConfigGroup OBJECT-GROUP
        OBJECTS {
            tnIo30an10gPortConfigFunction
        }
        STATUS         current
        DESCRIPTION    "."
        ::= { tnOpticalPortConfigGroups 310 }

    tnIo30an300PortConfigScalarsGroup OBJECT-GROUP
        OBJECTS {
            tnIo30an300PortConfigAttributeTotal
        }
        STATUS         current
        DESCRIPTION    "."
        ::= { tnOpticalPortConfigGroups 311 }

    tnIo30an300PortConfigGroup OBJECT-GROUP
        OBJECTS {
            tnIo30an300PortConfigFunction
        }
        STATUS         current
        DESCRIPTION    "."
        ::= { tnOpticalPortConfigGroups 312 }

    tnIo4an400PortConfigScalarsGroup OBJECT-GROUP
        OBJECTS {
            tnIo4an400PortConfigAttributeTotal
        }
        STATUS         current
        DESCRIPTION    "."
        ::= { tnOpticalPortConfigGroups 313 }

    tnIo4an400PortConfigGroup OBJECT-GROUP
        OBJECTS {
            tnIo4an400PortConfigFunction
        }
        STATUS         current
        DESCRIPTION    "."
        ::= { tnOpticalPortConfigGroups 314 }

    tn12p120PortConfigScalarsGroup OBJECT-GROUP
        OBJECTS {
            tn12p120PortConfigAttributeTotal
        }
        STATUS         current
        DESCRIPTION    "."
        ::= { tnOpticalPortConfigGroups 315 }

    tn12p120PortConfigGroup OBJECT-GROUP
        OBJECTS {
            tn12p120PortConfigFunction
        }
        STATUS         current
        DESCRIPTION    "."
        ::= { tnOpticalPortConfigGroups 316 }

    tn20p200PortConfigScalarsGroup OBJECT-GROUP
        OBJECTS {
            tn20p200PortConfigAttributeTotal
        }
        STATUS         current
        DESCRIPTION    "."
        ::= { tnOpticalPortConfigGroups 317 }

    tn20p200PortConfigGroup OBJECT-GROUP
        OBJECTS {
            tn20p200PortConfigFunction
        }
        STATUS         current
        DESCRIPTION    "."
        ::= { tnOpticalPortConfigGroups 318 }

    tn1ud200PortConfigScalarsGroup OBJECT-GROUP
        OBJECTS {
            tn1ud200PortConfigAttributeTotal
        }
        STATUS         current
        DESCRIPTION    "."
        ::= { tnOpticalPortConfigGroups 319 }

    tn1ud200PortConfigGroup OBJECT-GROUP
        OBJECTS {
            tn1ud200PortConfigFunction
        }
        STATUS         current
        DESCRIPTION    "."
        ::= { tnOpticalPortConfigGroups 320 }

    tnOt130snq10PortConfigScalarsGroup OBJECT-GROUP
        OBJECTS {
            tnOt130snq10PortConfigAttributeTotal
        }
        STATUS         current
        DESCRIPTION    "."
        ::= { tnOpticalPortConfigGroups 321 }

    tnOt130snq10PortConfigGroup OBJECT-GROUP
        OBJECTS {
            tnOt130snq10PortConfigFunction
        }
        STATUS         current
        DESCRIPTION    "."
        ::= { tnOpticalPortConfigGroups 322 }

    tnIroadmvPortConfigScalarsGroup OBJECT-GROUP
        OBJECTS {
            tnIroadmvPortConfigAttributeTotal
        }
        STATUS         current
        DESCRIPTION    "."
        ::= { tnOpticalPortConfigGroups 323 }

    tnIroadmvPortConfigGroup OBJECT-GROUP
        OBJECTS {
            tnIroadmvPortConfigFunction
        }
        STATUS         current
        DESCRIPTION    "."
        ::= { tnOpticalPortConfigGroups 324 }

    tnIroadmfPortConfigScalarsGroup OBJECT-GROUP
        OBJECTS {
            tnIroadmfPortConfigAttributeTotal
        }
        STATUS         current
        DESCRIPTION    "."
        ::= { tnOpticalPortConfigGroups 325 }

    tnIroadmfPortConfigGroup OBJECT-GROUP
        OBJECTS {
            tnIroadmfPortConfigFunction
        }
        STATUS         current
        DESCRIPTION    "."
        ::= { tnOpticalPortConfigGroups 326 }

    tnIroadmPortConfigScalarsGroup OBJECT-GROUP
        OBJECTS {
            tnIroadmPortConfigAttributeTotal
        }
        STATUS         current
        DESCRIPTION    "."
        ::= { tnOpticalPortConfigGroups 327 }

    tnIroadmPortConfigGroup OBJECT-GROUP
        OBJECTS {
            tnIroadmPortConfigPowerGain,
            tnIroadmPortConfigPowerGainBackoff,
            tnIroadmPortConfigTargetTilt,
            tnIroadmPortConfigVoaSet,
            tnIroadmPortConfigNominalSpanLossOut,
            tnIroadmPortConfigFiberTypeOut,
            tnIroadmPortConfigFiberLengthKm,
            tnIroadmPortConfigAddMinChannelPower,
            tnIroadmPortConfigEgressOaRippleToRemove,
            tnIroadmPortConfigExpressMinChannelPower,
            tnIroadmPortConfigIngressOaGainMin,
            tnIroadmPortConfigIngressOaGainMax,
            tnIroadmPortConfigTargetPpcOut,
            tnIroadmPortConfigIngressOaTargetPpcOut,
            tnIroadmPortConfigIngressOaTargetPpcAdj,
            tnIroadmPortConfigSignalFailThreshold,
            tnIroadmPortConfigSignalDegradeThreshold,
            tnIroadmPortConfigAprDisable,
            tnIroadmPortConfigForcedTargetPpcOut,
            tnIroadmPortConfigLineDcmConnAddress,
            tnIroadmPortConfigAprMode,
            tnIroadmPortConfigGainRange,
            tnIroadmPortConfigOSCVoaAtten,
            tnIroadmPortConfigDropMaxTargetPower,
            tnIroadmPortConfigDropMinTargetPower,
            tnIroadmPortConfigDropInitTargetPower,
            tnIroadmPortConfigDropExpressTargetPower,
            tnIroadmPortConfigGainRangeL,
            tnIroadmPortConfigIngressOaTargetPpcOutL,
            tnIroadmPortConfigPowerGainL,
            tnIroadmPortConfigIngressOaGainMaxL,
            tnIroadmPortConfigIngressOaGainMinL,
            tnIroadmPortConfigTargetTiltL,
            tnIroadmPortConfigVoaSetL,
            tnIroadmPortConfigTargetPpcOutL,
            tnIroadmPortConfigAlienWaveBank,
            tnIroadmPortConfigSpanLossTh,
            tnIroadmPortConfigAsellEnabled,
            tnIroadmPortConfigTargetPowerWidth,
            tnIroadmPortConfigTargetPowerWidthL,
            tnIroadmPortConfigIngressTargetPowerWidth
        }
        STATUS         current
        DESCRIPTION    "."
        ::= { tnOpticalPortConfigGroups 328 }

    tnMonOcmPortConfigScalarsGroup OBJECT-GROUP
        OBJECTS {
            tnMonOcmPortConfigAttributeTotal
        }
        STATUS         current
        DESCRIPTION    "."
        ::= { tnOpticalPortConfigGroups 329 }

    tnMonOcmPortConfigGroup OBJECT-GROUP
        OBJECTS {
            tnMonOcmPortConfigFunction,
            tnMonOcmPortConfigUserLabel,
            tnMonOcmPortAssociatedFirstRoadmTx,
            tnMonOcmPortAssociatedSecondRoadmTx,
            tnMonOcmPortAssociatedFirstRoadmRx,
            tnMonOcmPortAssociatedSecondRoadmRx,
            tnMonOcmPortAssociatedOlpOpsRx,
            tnMonOcmPortAssociatedOlpOpsTx
        }
        STATUS         current
        DESCRIPTION    "."
        ::= { tnOpticalPortConfigGroups 330 }

    tnUl2uc400PortConfigScalarsGroup OBJECT-GROUP
        OBJECTS {
            tnUl2uc400PortConfigAttributeTotal
        }
        STATUS         current
        DESCRIPTION    "."
        ::= { tnOpticalPortConfigGroups 331 }

    tnUl2uc400PortConfigGroup OBJECT-GROUP
        OBJECTS {
            tnUl2uc400PortConfigFunction
        }
        STATUS         current
        DESCRIPTION    "."
        ::= { tnOpticalPortConfigGroups 332 }

    tnUl4uc400PortConfigScalarsGroup OBJECT-GROUP
        OBJECTS {
            tnUl4uc400PortConfigAttributeTotal
        }
        STATUS         current
        DESCRIPTION    "."
        ::= { tnOpticalPortConfigGroups 333 }

    tnUl4uc400PortConfigGroup OBJECT-GROUP
        OBJECTS {
            tnUl4uc400PortConfigFunction
        }
        STATUS         current
        DESCRIPTION    "."
        ::= { tnOpticalPortConfigGroups 334 }

    tnUl20uc200PortConfigScalarsGroup OBJECT-GROUP
        OBJECTS {
            tnUl20uc200PortConfigAttributeTotal
        }
        STATUS         current
        DESCRIPTION    "."
        ::= { tnOpticalPortConfigGroups 335 }

    tnUl20uc200PortConfigGroup OBJECT-GROUP
        OBJECTS {
            tnUl20uc200PortConfigFunction
        }
        STATUS         current
        DESCRIPTION    "."
        ::= { tnOpticalPortConfigGroups 336 }

    tnD5x500PortConfigScalarsGroup OBJECT-GROUP
        OBJECTS {
            tnD5x500PortConfigAttributeTotal
        }
        STATUS         current
        DESCRIPTION    "."
        ::= { tnOpticalPortConfigGroups 337 }

    tnD5x500PortConfigGroup OBJECT-GROUP
        OBJECTS {
            tnD5x500PortConfigFunction
        }
        STATUS         current
        DESCRIPTION    "."
        ::= { tnOpticalPortConfigGroups 338 }

    tnOtS11M100PortConfigScalarsGroup OBJECT-GROUP
        OBJECTS {
            tnOtS11M100PortConfigAttributeTotal
        }
        STATUS         current
        DESCRIPTION    "."
        ::= { tnOpticalPortConfigGroups 339 }

    tnOtS11M100PortConfigGroup OBJECT-GROUP
        OBJECTS {
            tnOtS11M100PortConfigFunction
        }
        STATUS         current
        DESCRIPTION    "."
        ::= { tnOpticalPortConfigGroups 340 }

    tnMonOtdrPortConfigScalarsGroup OBJECT-GROUP
        OBJECTS {
            tnMonOtdrPortConfigAttributeTotal
        }
        STATUS         current
        DESCRIPTION    "."
        ::= { tnOpticalPortConfigGroups 341 }

    tnMonOtdrPortConfigGroup OBJECT-GROUP
        OBJECTS {
            tnMonOtdrPortConfigFunction,
            tnMonOtdrPortConfigConnAddress
        }
        STATUS         current
        DESCRIPTION    "."
        ::= { tnOpticalPortConfigGroups 342 }

    tnPSS96PowerFilterPortConfigScalarsGroup OBJECT-GROUP
        OBJECTS {
            tnPSS96PowerFilterPortConfigAttributeTotal
        }
        STATUS         current
        DESCRIPTION    "."
        ::= { tnOpticalPortConfigGroups 343 }

    tnPSS96PowerFilterPortConfigGroup OBJECT-GROUP
        OBJECTS {
            tnPSS96PowerFilterPortConfigFunction,
            tnPSS96ExpectedAmps
        }
        STATUS         current
        DESCRIPTION    "."
        ::= { tnOpticalPortConfigGroups 344 }

    tn12ce120PortConfigScalarsGroup OBJECT-GROUP
        OBJECTS {
            tn12ce120PortConfigAttributeTotal
        }
        STATUS         current
        DESCRIPTION    "."
        ::= { tnOpticalPortConfigGroups 345 }

    tn12ce120PortConfigGroup OBJECT-GROUP
        OBJECTS {
            tn12ce120PortConfigFunction
        }
        STATUS         current
        DESCRIPTION    "."
        ::= { tnOpticalPortConfigGroups 346 }

    tn1ce100PortConfigScalarsGroup OBJECT-GROUP
        OBJECTS {
            tn1ce100PortConfigAttributeTotal
        }
        STATUS         current
        DESCRIPTION    "."
        ::= { tnOpticalPortConfigGroups 347 }

    tn1ce100PortConfigGroup OBJECT-GROUP
        OBJECTS {
            tn1ce100PortConfigFunction
        }
        STATUS         current
        DESCRIPTION    "."
        ::= { tnOpticalPortConfigGroups 348 }

    tnLcI1000PortConfigScalarsGroup OBJECT-GROUP
        OBJECTS {
            tnLcI1000PortConfigAttributeTotal
        }
        STATUS         current
        DESCRIPTION    "."
        ::= { tnOpticalPortConfigGroups 349 }

    tnLcI1000PortConfigGroup OBJECT-GROUP
        OBJECTS {
            tnLcI1000PortConfigFunction
        }
        STATUS         current
        DESCRIPTION    "."
        ::= { tnOpticalPortConfigGroups 350 }

    tnAwbegrPortConfigScalarsGroup OBJECT-GROUP
        OBJECTS {
            tnAwbegrPortConfigAttributeTotal
        }
        STATUS         current
        DESCRIPTION    "."
        ::= { tnOpticalPortConfigGroups 351 }

    tnAwbegrPortConfigGroup OBJECT-GROUP
        OBJECTS {
            tnAwbegrPortConfigFunction
        }
        STATUS         current
        DESCRIPTION    "."
        ::= { tnOpticalPortConfigGroups 352 }

    tnAwbingPortConfigScalarsGroup OBJECT-GROUP
        OBJECTS {
            tnAwbingPortConfigAttributeTotal
        }
        STATUS         current
        DESCRIPTION    "."
        ::= { tnOpticalPortConfigGroups 353 }

    tnAwbingPortConfigGroup OBJECT-GROUP
        OBJECTS {
            tnAwbingPortConfigFunction
        }
        STATUS         current
        DESCRIPTION    "."
        ::= { tnOpticalPortConfigGroups 354 }

    tnAwbilaPortConfigScalarsGroup OBJECT-GROUP
        OBJECTS {
            tnAwbilaPortConfigAttributeTotal
        }
        STATUS         current
        DESCRIPTION    "."
        ::= { tnOpticalPortConfigGroups 355 }

    tnAwbilaPortConfigGroup OBJECT-GROUP
        OBJECTS {
            tnAwbilaPortConfigFunction
        }
        STATUS         current
        DESCRIPTION    "."
        ::= { tnOpticalPortConfigGroups 356 }

    tnRa5pPortConfigScalarsGroup OBJECT-GROUP
        OBJECTS {
            tnRa5pPortConfigAttributeTotal
        }
        STATUS         current
        DESCRIPTION    "."
        ::= { tnOpticalPortConfigGroups 357 }

    tnRa5pPortConfigGroup OBJECT-GROUP
        OBJECTS {
            tnRa5pPortConfigFunction
        }
        STATUS         current
        DESCRIPTION    "."
        ::= { tnOpticalPortConfigGroups 358 }

    tnIroadm9mPortConfigScalarsGroup OBJECT-GROUP
        OBJECTS {
            tnIroadm9mPortConfigAttributeTotal
        }
        STATUS         current
        DESCRIPTION    "."
        ::= { tnOpticalPortConfigGroups 359 }

    tnIroadm9mPortConfigGroup OBJECT-GROUP
        OBJECTS {
            tnIroadm9mPortConfigFunction
        }
        STATUS         current
        DESCRIPTION    "."
        ::= { tnOpticalPortConfigGroups 360 }

    tnS13x100PortConfigScalarsGroup OBJECT-GROUP
        OBJECTS {
            tnS13x100PortConfigAttributeTotal
        }
        STATUS         current
        DESCRIPTION    "."
        ::= { tnOpticalPortConfigGroups 361 }

    tnS13x100PortConfigGroup OBJECT-GROUP
        OBJECTS {
            tnS13x100PortConfigFunction
        }
        STATUS         current
        DESCRIPTION    "."
        ::= { tnOpticalPortConfigGroups 362 }

    tn12ce121PortConfigScalarsGroup OBJECT-GROUP
        OBJECTS {
            tn12ce121PortConfigAttributeTotal
        }
        STATUS         current
        DESCRIPTION    "."
        ::= { tnOpticalPortConfigGroups 363 }

    tn12ce121PortConfigGroup OBJECT-GROUP
        OBJECTS {
            tn12ce121PortConfigFunction
        }
        STATUS         current
        DESCRIPTION    "."
        ::= { tnOpticalPortConfigGroups 364 }

    tnPtpioctlPortConfigScalarsGroup OBJECT-GROUP
        OBJECTS {
            tnPtpioctlPortConfigAttributeTotal
        }
        STATUS         current
        DESCRIPTION    "."
        ::= { tnOpticalPortConfigGroups 365 }

    tnPtpioctlPortConfigGroup OBJECT-GROUP
        OBJECTS {
            tnPtpioctlPortConfigFunction,
            tnPtpioctlPortConfigFiberConnectPort
        }
        STATUS         current
        DESCRIPTION    "."
        ::= { tnOpticalPortConfigGroups 366 }

    tnAa2donwbPortConfigScalarsGroup OBJECT-GROUP
        OBJECTS {
            tnAa2donwbPortConfigAttributeTotal
        }
        STATUS         current
        DESCRIPTION    "."
        ::= { tnOpticalPortConfigGroups 367 }

    tnAa2donwbPortConfigGroup OBJECT-GROUP
        OBJECTS {
            tnAa2donwbPortConfigFunction,
            tnAa2donwbPortConfigVoaMode,
            tnAa2donwbPortConfigAttenuationModeAtten,
            tnAa2donwbPortConfigConnToPort
        }
        STATUS         current
        DESCRIPTION    "."
        ::= { tnOpticalPortConfigGroups 368 }

    tnOsctaprPortConfigScalarsGroup OBJECT-GROUP
        OBJECTS {
            tnOsctaprPortConfigAttributeTotal
        }
        STATUS         current
        DESCRIPTION    "."
        ::= { tnOpticalPortConfigGroups 369 }

    tnOsctaprPortConfigGroup OBJECT-GROUP
        OBJECTS {
            tnOsctaprPortConfigFunction,
            tnOsctaprPortConfigVoaMode,
            tnOsctaprPortConfigAttenuationModeAtten,
            tnOsctaprPortConfigConnToPort
        }
        STATUS         current
        DESCRIPTION    "."
        ::= { tnOpticalPortConfigGroups 370 }

    tn11qpa4bPortConfigScalarsGroup OBJECT-GROUP
        OBJECTS {
            tn11qpa4bPortConfigAttributeTotal
        }
        STATUS         current
        DESCRIPTION    "."
        ::= { tnOpticalPortConfigGroups 371 }

    tn11qpa4bPortConfigGroup OBJECT-GROUP
        OBJECTS {
            tn11qpa4bPortConfigFunction
        }
        STATUS         current
        DESCRIPTION    "."
        ::= { tnOpticalPortConfigGroups 372 }

    tn1ux100PortConfigScalarsGroup OBJECT-GROUP
        OBJECTS {
            tn1ux100PortConfigAttributeTotal
        }
        STATUS         current
        DESCRIPTION    "."
        ::= { tnOpticalPortConfigGroups 373 }

    tn1ux100PortConfigGroup OBJECT-GROUP
        OBJECTS {
            tn1ux100PortConfigFunction
        }
        STATUS         current
        DESCRIPTION    "."
        ::= { tnOpticalPortConfigGroups 374 }

    tn20ax200PortConfigScalarsGroup OBJECT-GROUP
        OBJECTS {
            tn20ax200PortConfigAttributeTotal
        }
        STATUS         current
        DESCRIPTION    "."
        ::= { tnOpticalPortConfigGroups 375 }

    tn20ax200PortConfigGroup OBJECT-GROUP
        OBJECTS {
            tn20ax200PortConfigFunction
        }
        STATUS         current
        DESCRIPTION    "."
        ::= { tnOpticalPortConfigGroups 376 }

    tn20mx80PortConfigScalarsGroup OBJECT-GROUP
        OBJECTS {
            tn20mx80PortConfigAttributeTotal
        }
        STATUS         current
        DESCRIPTION    "."
        ::= { tnOpticalPortConfigGroups 377 }

    tn20mx80PortConfigGroup OBJECT-GROUP
        OBJECTS {
            tn20mx80PortConfigFunction
        }
        STATUS         current
        DESCRIPTION    "."
        ::= { tnOpticalPortConfigGroups 378 }

    tnAar2x8aPortConfigScalarsGroup OBJECT-GROUP
        OBJECTS {
            tnAar2x8aPortConfigAttributeTotal
        }
        STATUS         current
        DESCRIPTION    "."
        ::= { tnOpticalPortConfigGroups 379 }

    tnAar2x8aPortConfigGroup OBJECT-GROUP
        OBJECTS {
            tnAar2x8aPortConfigFunction
        }
        STATUS         current
        DESCRIPTION    "."
        ::= { tnOpticalPortConfigGroups 380 }

    tnS13x100ePortConfigScalarsGroup OBJECT-GROUP
        OBJECTS {
            tnS13x100ePortConfigAttributeTotal
        }
        STATUS         current
        DESCRIPTION    "."
        ::= { tnOpticalPortConfigGroups 381 }

    tnS13x100ePortConfigGroup OBJECT-GROUP
        OBJECTS {
            tnS13x100ePortConfigFunction
        }
        STATUS         current
        DESCRIPTION    "."
        ::= { tnOpticalPortConfigGroups 382 }

    tnWtocmflPortConfigScalarsGroup OBJECT-GROUP
        OBJECTS {
            tnWtocmflPortConfigAttributeTotal
        }
        STATUS         current
        DESCRIPTION    "."
        ::= { tnOpticalPortConfigGroups 383 }

    tnWtocmflPortConfigGroup OBJECT-GROUP
        OBJECTS {
            tnWtocmflPortConfigFunction
        }
        STATUS         current
        DESCRIPTION    "."
        ::= { tnOpticalPortConfigGroups 384 }

    tnAar2x8alPortConfigScalarsGroup OBJECT-GROUP
        OBJECTS {
            tnAar2x8alPortConfigAttributeTotal
        }
        STATUS         current
        DESCRIPTION    "."
        ::= { tnOpticalPortConfigGroups 385 }

    tnAar2x8alPortConfigGroup OBJECT-GROUP
        OBJECTS {
            tnAar2x8alPortConfigFunction
        }
        STATUS         current
        DESCRIPTION    "."
        ::= { tnOpticalPortConfigGroups 386 }

    tnWr20tfmlPortConfigScalarsGroup OBJECT-GROUP
        OBJECTS {
            tnWr20tfmlPortConfigAttributeTotal
        }
        STATUS         current
        DESCRIPTION    "."
        ::= { tnOpticalPortConfigGroups 387 }

    tnWr20tfmlPortConfigGroup OBJECT-GROUP
        OBJECTS {
            tnWr20tfmlPortConfigFunction
        }
        STATUS         current
        DESCRIPTION    "."
        ::= { tnOpticalPortConfigGroups 388 }

    tnMcs8x16lPortConfigScalarsGroup OBJECT-GROUP
        OBJECTS {
            tnMcs8x16lPortConfigAttributeTotal
        }
        STATUS         current
        DESCRIPTION    "."
        ::= { tnOpticalPortConfigGroups 389 }

    tnMcs8x16lPortConfigGroup OBJECT-GROUP
        OBJECTS {
            tnMcs8x16lPortConfigFunction
        }
        STATUS         current
        DESCRIPTION    "."
        ::= { tnOpticalPortConfigGroups 390 }

    tnPSS8xPowerFilterPortConfigScalarsGroup OBJECT-GROUP
        OBJECTS {
            tnPSS8xPowerFilterPortConfigAttributeTotal
        }
        STATUS         current
        DESCRIPTION    "."
        ::= { tnOpticalPortConfigGroups 391 }

    tnPSS8xPowerFilterPortConfigGroup OBJECT-GROUP
        OBJECTS {
            tnPSS8xPowerFilterPortConfigFunction,
            tnPSS8xExpectedAmps
        }
        STATUS         current
        DESCRIPTION    "."
        ::= { tnOpticalPortConfigGroups 392 }

    tnLcI2000PortConfigScalarsGroup OBJECT-GROUP
        OBJECTS {
            tnLcI2000PortConfigAttributeTotal
        }
        STATUS         current
        DESCRIPTION    "."
        ::= { tnOpticalPortConfigGroups 393 }

    tnLcI2000PortConfigGroup OBJECT-GROUP
        OBJECTS {
            tnLcI2000PortConfigFunction
        }
        STATUS         current
        DESCRIPTION    "."
        ::= { tnOpticalPortConfigGroups 394 }

    tn30se300PortConfigScalarsGroup OBJECT-GROUP
        OBJECTS {
            tn30se300PortConfigAttributeTotal
        }
        STATUS         current
        DESCRIPTION    "."
        ::= { tnOpticalPortConfigGroups 395 }

    tn30se300PortConfigGroup OBJECT-GROUP
        OBJECTS {
            tn30se300PortConfigFunction
        }
        STATUS         current
        DESCRIPTION    "."
        ::= { tnOpticalPortConfigGroups 396 }

    tn6se300PortConfigScalarsGroup OBJECT-GROUP
        OBJECTS {
            tn6se300PortConfigAttributeTotal
        }
        STATUS         current
        DESCRIPTION    "."
        ::= { tnOpticalPortConfigGroups 397 }

    tn6se300PortConfigGroup OBJECT-GROUP
        OBJECTS {
            tn6se300PortConfigFunction
        }
        STATUS         current
        DESCRIPTION    "."
        ::= { tnOpticalPortConfigGroups 398 }


    tnOtdrwbPortConfigScalarsGroup OBJECT-GROUP
        OBJECTS {
            tnOtdrwbPortConfigAttributeTotal
        }
        STATUS         current
        DESCRIPTION    "."
        ::= { tnOpticalPortConfigGroups 399 }

    tnOtdrwbPortConfigGroup OBJECT-GROUP
        OBJECTS {
            tnOtdrwbPortConfigFunction,
            tnOtdrwbPortConfigConnAddress
        }
        STATUS         current
        DESCRIPTION    "."
        ::= { tnOpticalPortConfigGroups 400 }

    tn8dc30tPortConfigScalarsGroup OBJECT-GROUP
        OBJECTS {
            tn8dc30tPortConfigAttributeTotal
        }
        STATUS         current
        DESCRIPTION    "."
        ::= { tnOpticalPortConfigGroups 401 }

    tn8dc30tPortConfigGroup OBJECT-GROUP
        OBJECTS {
            tn8dc30tPortConfigFunction
        }
        STATUS         current
        DESCRIPTION    "."
        ::= { tnOpticalPortConfigGroups 402 }

    tn16dc65tPortConfigScalarsGroup OBJECT-GROUP
        OBJECTS {
            tn16dc65tPortConfigAttributeTotal
        }
        STATUS         current
        DESCRIPTION    "."
        ::= { tnOpticalPortConfigGroups 403 }

    tn16dc65tPortConfigGroup OBJECT-GROUP
        OBJECTS {
            tn16dc65tPortConfigFunction
        }
        STATUS         current
        DESCRIPTION    "."
        ::= { tnOpticalPortConfigGroups 404 }

    tnD5x500lPortConfigScalarsGroup OBJECT-GROUP
        OBJECTS {
            tnD5x500lPortConfigAttributeTotal
        }
        STATUS         current
        DESCRIPTION    "."
        ::= { tnOpticalPortConfigGroups 405 }

    tnD5x500lPortConfigGroup OBJECT-GROUP
        OBJECTS {
            tnD5x500lPortConfigFunction
        }
        STATUS         current
        DESCRIPTION    "."
        ::= { tnOpticalPortConfigGroups 406 }

    tnLcI2000lPortConfigScalarsGroup OBJECT-GROUP
        OBJECTS {
            tnLcI2000lPortConfigAttributeTotal
        }
        STATUS         current
        DESCRIPTION    "."
        ::= { tnOpticalPortConfigGroups 407 }

    tnLcI2000lPortConfigGroup OBJECT-GROUP
        OBJECTS {
            tnLcI2000lPortConfigFunction
        }
        STATUS         current
        DESCRIPTION    "."
        ::= { tnOpticalPortConfigGroups 408 }

    tnIroadm9rPortConfigScalarsGroup OBJECT-GROUP
        OBJECTS {
            tnIroadm9rPortConfigAttributeTotal
        }
        STATUS         current
        DESCRIPTION    "."
        ::= { tnOpticalPortConfigGroups 409 }

    tnIroadm9rPortConfigGroup OBJECT-GROUP
        OBJECTS {
            tnIroadm9rPortConfigFunction
        }
        STATUS         current
        DESCRIPTION    "."
        ::= { tnOpticalPortConfigGroups 410 }

    tnRa2p96PortConfigScalarsGroup OBJECT-GROUP
        OBJECTS {
            tnRa2p96PortConfigAttributeTotal
        }
        STATUS         current
        DESCRIPTION    "."
        ::= { tnOpticalPortConfigGroups 411 }

    tnRa2p96PortConfigGroup OBJECT-GROUP
        OBJECTS {
            tnRa2p96PortConfigFunction
        }
        STATUS         current
        DESCRIPTION    "."
        ::= { tnOpticalPortConfigGroups 412 }

    tnOtdrmPortConfigScalarsGroup OBJECT-GROUP
        OBJECTS {
            tnOtdrmPortConfigAttributeTotal
        }
        STATUS         current
        DESCRIPTION    "."
        ::= { tnOpticalPortConfigGroups 413 }

    tnOtdrmPortConfigGroup OBJECT-GROUP
        OBJECTS {
            tnOtdrmPortConfigFunction,
            tnOtdrmPortConfigConnAddress
        }
        STATUS         current
        DESCRIPTION    "."
        ::= { tnOpticalPortConfigGroups 414 }

    tn103scecPortConfigScalarsGroup OBJECT-GROUP
        OBJECTS {
            tn103scecPortConfigAttributeTotal
        }
        STATUS         current
        DESCRIPTION    "."
        ::= { tnOpticalPortConfigGroups 415 }

    tnOcsPacketPortConfigGroup OBJECT-GROUP
        OBJECTS {
            tnOcsPacketPortConfigLPTCSFConsequenceAction,
            tnOcsPacketPortConfigLPTSSFConsequenceAction,
            tnOcsPacketLptRFISuppress,
            tnOcsPacketLptHoldoffTime,
            tnOcsPacketLptSendControl,
            tnOcsPacketLlcfDownstreamPotlist,
            tnOcsPacketLlcfUpstreamPotlist
        }
        STATUS         current
        DESCRIPTION    "."
        ::= { tnOpticalPortConfigGroups 416 }

    tn20an80PortConfigScalarsGroup OBJECT-GROUP
        OBJECTS {
            tn20an80PortConfigAttributeTotal
        }
        STATUS         current
        DESCRIPTION    "."
        ::= { tnOpticalPortConfigGroups 417 }

    tn20an80PortConfigGroup OBJECT-GROUP
        OBJECTS {
            tn20an80PortConfigFunction
        }
        STATUS         current
        DESCRIPTION    "."
        ::= { tnOpticalPortConfigGroups 418 }

    tn10an400PortConfigScalarsGroup OBJECT-GROUP
        OBJECTS {
            tn10an400PortConfigAttributeTotal
        }
        STATUS         current
        DESCRIPTION    "."
        ::= { tnOpticalPortConfigGroups 419 }

    tn10an400PortConfigGroup OBJECT-GROUP
        OBJECTS {
            tn10an400PortConfigFunction
        }
        STATUS         current
        DESCRIPTION    "."
        ::= { tnOpticalPortConfigGroups 420 }

    tn8p20PortConfigScalarsGroup OBJECT-GROUP
        OBJECTS {
            tn8p20PortConfigAttributeTotal
        }
        STATUS         current
        DESCRIPTION    "."
        ::= { tnOpticalPortConfigGroups 421 }

    tn8p20PortConfigGroup OBJECT-GROUP
        OBJECTS {
            tn8p20PortConfigFunction
        }
        STATUS         current
        DESCRIPTION    "."
        ::= { tnOpticalPortConfigGroups 422 }

    tnOpsflexPortConfigScalarsGroup OBJECT-GROUP
        OBJECTS {
            tnOpsflexPortConfigAttributeTotal
        }
        STATUS         current
        DESCRIPTION    "."
        ::= { tnOpticalPortConfigGroups 423 }

    tnOpsflexPortConfigGroup OBJECT-GROUP
        OBJECTS {
            tnOpsflexPortConfigFunction
        }
        STATUS         current
        DESCRIPTION    "."
        ::= { tnOpticalPortConfigGroups 424 }

    tnD5x500qPortConfigScalarsGroup OBJECT-GROUP
        OBJECTS {
            tnD5x500qPortConfigAttributeTotal
        }
        STATUS         current
        DESCRIPTION    "."
        ::= { tnOpticalPortConfigGroups 425 }

    tnD5x500qPortConfigGroup OBJECT-GROUP
        OBJECTS {
            tnD5x500qPortConfigFunction
        }
        STATUS         current
        DESCRIPTION    "."
        ::= { tnOpticalPortConfigGroups 426 }

    tn18p40PortConfigScalarsGroup OBJECT-GROUP
        OBJECTS {
            tn18p40PortConfigAttributeTotal
        }
        STATUS         current
        DESCRIPTION    "."
        ::= { tnOpticalPortConfigGroups 427 }

    tn18p40PortConfigGroup OBJECT-GROUP
        OBJECTS {
            tn18p40PortConfigFunction
        }
        STATUS         current
        DESCRIPTION    "."
        ::= { tnOpticalPortConfigGroups 428 }

    tnDa2c4PortConfigScalarsGroup OBJECT-GROUP
        OBJECTS {
            tnDa2c4PortConfigAttributeTotal
        }
        STATUS         current
        DESCRIPTION    "."
        ::= { tnOpticalPortConfigGroups 429 }

    tnDa2c4PortConfigGroup OBJECT-GROUP
        OBJECTS {
            tnDa2c4PortConfigFunction
        }
        STATUS         current
        DESCRIPTION    "."
        ::= { tnOpticalPortConfigGroups 430 }

    tn130sla1PortConfigScalarsGroup OBJECT-GROUP
        OBJECTS {
            tn130sla1PortConfigAttributeTotal
        }
        STATUS         current
        DESCRIPTION    "."
        ::= { tnOpticalPortConfigGroups 431 }

    tn130sla1PortConfigGroup OBJECT-GROUP
        OBJECTS {
            tn130sla1PortConfigFunction
        }
        STATUS         current
        DESCRIPTION    "."
        ::= { tnOpticalPortConfigGroups 432 }

    tn130slx10PortConfigScalarsGroup OBJECT-GROUP
        OBJECTS {
            tn130slx10PortConfigAttributeTotal
        }
        STATUS         current
        DESCRIPTION    "."
        ::= { tnOpticalPortConfigGroups 433 }

    tn130slx10PortConfigGroup OBJECT-GROUP
        OBJECTS {
            tn130slx10PortConfigFunction
        }
        STATUS         current
        DESCRIPTION    "."
        ::= { tnOpticalPortConfigGroups 434 }

    tnPSS12xPowerFilterPortConfigScalarsGroup OBJECT-GROUP
        OBJECTS {
            tnPSS12xPowerFilterPortConfigAttributeTotal
        }
        STATUS         current
        DESCRIPTION    "."
        ::= { tnOpticalPortConfigGroups 435 }

    tnPSS12xPowerFilterPortConfigGroup OBJECT-GROUP
        OBJECTS {
            tnPSS12xPowerFilterPortConfigFunction,
            tnPSS12xExpectedAmps
        }
        STATUS         current
        DESCRIPTION    "."
        ::= { tnOpticalPortConfigGroups 436 }

    tnIroadm20PortConfigScalarsGroup OBJECT-GROUP
        OBJECTS {
            tnIroadm20PortConfigAttributeTotal
        }
        STATUS         current
        DESCRIPTION    "."
        ::= { tnOpticalPortConfigGroups 437 }

    tnIroadm20PortConfigGroup OBJECT-GROUP
        OBJECTS {
            tnIroadm20PortConfigFunction
        }
        STATUS         current
        DESCRIPTION    "."
        ::= { tnOpticalPortConfigGroups 438 }

    tnS2ad200PortConfigScalarsGroup OBJECT-GROUP
        OBJECTS {
            tnS2ad200PortConfigAttributeTotal
        }
        STATUS         current
        DESCRIPTION    "."
        ::= { tnOpticalPortConfigGroups 439 }

    tnS2ad200PortConfigGroup OBJECT-GROUP
        OBJECTS {
            tnS2ad200PortConfigFunction
        }
        STATUS         current
        DESCRIPTION    "."
        ::= { tnOpticalPortConfigGroups 440 }

    tnMsh4fsbPortConfigScalarsGroup OBJECT-GROUP
        OBJECTS {
            tnMsh4fsbPortConfigAttributeTotal
        }
        STATUS         current
        DESCRIPTION    "."
        ::= { tnOpticalPortConfigGroups 441 }

    tnMsh4fsbPortConfigGroup OBJECT-GROUP
        OBJECTS {
            tnMsh4fsbPortConfigFunction
        }
        STATUS         current
        DESCRIPTION    "."
        ::= { tnOpticalPortConfigGroups 442 }

    tn2ux200PortConfigScalarsGroup OBJECT-GROUP
        OBJECTS {
            tn2ux200PortConfigAttributeTotal
        }
        STATUS         current
        DESCRIPTION    "."
        ::= { tnOpticalPortConfigGroups 443 }

    tn2ux200PortConfigGroup OBJECT-GROUP
        OBJECTS {
            tn2ux200PortConfigFunction
        }
        STATUS         current
        DESCRIPTION    "."
        ::= { tnOpticalPortConfigGroups 444 }

    tn4mx200PortConfigScalarsGroup OBJECT-GROUP
        OBJECTS {
            tn4mx200PortConfigAttributeTotal
        }
        STATUS         current
        DESCRIPTION    "."
        ::= { tnOpticalPortConfigGroups 445 }

    tn4mx200PortConfigGroup OBJECT-GROUP
        OBJECTS {
            tn4mx200PortConfigFunction
        }
        STATUS         current
        DESCRIPTION    "."
        ::= { tnOpticalPortConfigGroups 446 }

    tnOpsb5PortConfigScalarsGroup OBJECT-GROUP
        OBJECTS {
            tnOpsb5PortConfigAttributeTotal
        }
        STATUS         current
        DESCRIPTION    "."
        ::= { tnOpticalPortConfigGroups 447 }

    tnOpsb5PortConfigGroup OBJECT-GROUP
        OBJECTS {
            tnOpsb5PortConfigFunction
        }
        STATUS         current
        DESCRIPTION    "."
        ::= { tnOpticalPortConfigGroups 448 }

    tnAswglPortConfigScalarsGroup OBJECT-GROUP
        OBJECTS {
            tnAswglPortConfigAttributeTotal
        }
        STATUS         current
        DESCRIPTION    "."
        ::= { tnOpticalPortConfigGroups 449 }

    tnAswglPortConfigGroup OBJECT-GROUP
        OBJECTS {
            tnAswglPortConfigFunction
        }
        STATUS         current
        DESCRIPTION    "."
        ::= { tnOpticalPortConfigGroups 450 }

    tnIpreampPortConfigScalarsGroup OBJECT-GROUP
        OBJECTS {
            tnIpreampPortConfigAttributeTotal
        }
        STATUS         current
        DESCRIPTION    "."
        ::= { tnOpticalPortConfigGroups 451 }

    tnIpreampPortConfigGroup OBJECT-GROUP
        OBJECTS {
            tnIpreampPortConfigFunction
        }
        STATUS         current
        DESCRIPTION    "."
        ::= { tnOpticalPortConfigGroups 452 }

--    obsolete
--    tn40cx800PortConfigScalarsGroup OBJECT-GROUP ::= { tnOpticalPortConfigGroups 453 }
--    tn40cx800PortConfigGroup        OBJECT-GROUP ::= { tnOpticalPortConfigGroups 454 }

    tnIrdm32PortConfigScalarsGroup OBJECT-GROUP
        OBJECTS {
            tnIrdm32PortConfigAttributeTotal
        }
        STATUS         current
        DESCRIPTION    "."
        ::= { tnOpticalPortConfigGroups 455 }

    tnIrdm32PortConfigGroup OBJECT-GROUP
        OBJECTS {
            tnIrdm32PortConfigFunction
        }
        STATUS         current
        DESCRIPTION    "."
        ::= { tnOpticalPortConfigGroups 456 }

    tnRa4pPortConfigScalarsGroup OBJECT-GROUP
        OBJECTS {
            tnRa4pPortConfigAttributeTotal
        }
        STATUS         current
        DESCRIPTION    "."
        ::= { tnOpticalPortConfigGroups 457 }

    tnRa4pPortConfigGroup OBJECT-GROUP
        OBJECTS {
            tnRa4pPortConfigFunction
        }
        STATUS         current
        DESCRIPTION    "."
        ::= { tnOpticalPortConfigGroups 458 }

    tnEilaPortConfigScalarsGroup OBJECT-GROUP
        OBJECTS {
            tnEilaPortConfigAttributeTotal
        }
        STATUS         current
        DESCRIPTION    "."
        ::= { tnOpticalPortConfigGroups 459 }

    tnEilaPortConfigGroup OBJECT-GROUP
        OBJECTS {
            tnEilaPortConfigFunction
        }
        STATUS         current
        DESCRIPTION    "."
        ::= { tnOpticalPortConfigGroups 460 }

--    obsolete
--    tn8cx800PortConfigScalarsGroup OBJECT-GROUP ::= { tnOpticalPortConfigGroups 461 }
--    tn8cx800PortConfigGroup        OBJECT-GROUP ::= { tnOpticalPortConfigGroups 462 }
--    tn6px800PortConfigScalarsGroup OBJECT-GROUP ::= { tnOpticalPortConfigGroups 463 }
--    tn6px800PortConfigGroup        OBJECT-GROUP ::= { tnOpticalPortConfigGroups 464 }

    tnMcs16x15PortConfigScalarsGroup OBJECT-GROUP
        OBJECTS {
            tnMcs16x15PortConfigAttributeTotal
        }
        STATUS         current
        DESCRIPTION    "."
        ::= { tnOpticalPortConfigGroups 465 }

    tnMcs16x15PortConfigGroup OBJECT-GROUP
        OBJECTS {
            tnMcs16x15PortConfigFunction
        }
        STATUS         current
        DESCRIPTION    "."
        ::= { tnOpticalPortConfigGroups 466 }

    tn10an1tPortConfigScalarsGroup OBJECT-GROUP
        OBJECTS {
            tn10an1tPortConfigAttributeTotal
        }
        STATUS         current
        DESCRIPTION    "."
        ::= { tnOpticalPortConfigGroups 467 }

    tn10an1tPortConfigGroup OBJECT-GROUP
        OBJECTS {
            tn10an1tPortConfigFunction
        }
        STATUS         current
        DESCRIPTION    "."
        ::= { tnOpticalPortConfigGroups 468 }

    tn8uc1tPortConfigScalarsGroup OBJECT-GROUP
        OBJECTS {
            tn8uc1tPortConfigAttributeTotal
        }
        STATUS         current
        DESCRIPTION    "."
        ::= { tnOpticalPortConfigGroups 469 }

    tn8uc1tPortConfigGroup OBJECT-GROUP
        OBJECTS {
            tn8uc1tPortConfigFunction
        }
        STATUS         current
        DESCRIPTION    "."
        ::= { tnOpticalPortConfigGroups 470 }

    tnDfc12PortConfigScalarsGroup OBJECT-GROUP
        OBJECTS {
            tnDfc12PortConfigAttributeTotal
        }
        STATUS         current
        DESCRIPTION    "."
        ::= { tnOpticalPortConfigGroups 471 }

    tnDfc12PortConfigGroup OBJECT-GROUP
        OBJECTS {
            tnDfc12PortConfigFunction
        }
        STATUS         current
        DESCRIPTION    "."
        ::= { tnOpticalPortConfigGroups 472 }

    tnIrdm32lPortConfigScalarsGroup OBJECT-GROUP
        OBJECTS {
            tnIrdm32lPortConfigAttributeTotal
        }
        STATUS         current
        DESCRIPTION    "."
        ::= { tnOpticalPortConfigGroups 473 }

    tnIrdm32lPortConfigGroup OBJECT-GROUP
        OBJECTS {
            tnIrdm32lPortConfigFunction
        }
        STATUS         current
        DESCRIPTION    "."
        ::= { tnOpticalPortConfigGroups 474 }

    tnS4x400PortConfigScalarsGroup OBJECT-GROUP
        OBJECTS {
            tnS4x400PortConfigAttributeTotal
        }
        STATUS         current
        DESCRIPTION    "."
        ::= { tnOpticalPortConfigGroups 475 }

    tnS4x400PortConfigGroup OBJECT-GROUP
        OBJECTS {
            tnS4x400PortConfigFunction
        }
        STATUS         current
        DESCRIPTION    "."
        ::= { tnOpticalPortConfigGroups 476 }

    tnTPS24PS1PortConfigScalarsGroup OBJECT-GROUP
        OBJECTS {
            tnTPS24PS1PortConfigAttributeTotal
        }
        STATUS         current
        DESCRIPTION    "."
        ::= { tnOpticalPortConfigGroups 477 }

    tnTPS24PS1PortConfigGroup OBJECT-GROUP
        OBJECTS {
            tnTPS24PS1PortConfigFunction,
            tnTPS24PS1LptCons,
            tnTPS24PS1LptHoldOffTime,
            tnTPS24PS1LptFlsDelayTime,
            tnTPS24PS1LptTxDisDelayTime,
            tnTPS24PS1LptExtensionTime
        }
        STATUS         current
        DESCRIPTION    "."
        ::= { tnOpticalPortConfigGroups 478 }

    tnTPS24PS2PortConfigScalarsGroup OBJECT-GROUP
        OBJECTS {
            tnTPS24PS2PortConfigAttributeTotal
        }
        STATUS         current
        DESCRIPTION    "."
        ::= { tnOpticalPortConfigGroups 479 }

    tnTPS24PS2PortConfigGroup OBJECT-GROUP
        OBJECTS {
            tnTPS24PS2PortConfigFunction,
            tnTPS24PS2LptCons,
            tnTPS24PS2LptHoldOffTime,
            tnTPS24PS2LptFlsDelayTime,
            tnTPS24PS2LptTxDisDelayTime,
            tnTPS24PS2LptExtensionTime
        }
        STATUS         current
        DESCRIPTION    "."
        ::= { tnOpticalPortConfigGroups 480 }

    tnTPS12PSPortConfigScalarsGroup OBJECT-GROUP
        OBJECTS {
            tnTPS12PSPortConfigAttributeTotal
        }
        STATUS         current
        DESCRIPTION    "."
        ::= { tnOpticalPortConfigGroups 481 }

    tnTPS12PSPortConfigGroup OBJECT-GROUP
        OBJECTS {
            tnTPS12PSPortConfigFunction,
            tnTPS12PSLptCons,
            tnTPS12PSLptHoldOffTime,
            tnTPS12PSLptFlsDelayTime,
            tnTPS12PSLptTxDisDelayTime,
            tnTPS12PSLptExtensionTime
        }
        STATUS         current
        DESCRIPTION    "."
        ::= { tnOpticalPortConfigGroups 482 }

    tnEsrePortConfigScalarsGroup OBJECT-GROUP
        OBJECTS {
            tnEsrePortConfigAttributeTotal
        }
        STATUS         current
        DESCRIPTION    "."
        ::= { tnOpticalPortConfigGroups 483 }

    tnEsrePortConfigGroup OBJECT-GROUP
        OBJECTS {
            tnEsrePortConfigFunction
        }
        STATUS         current
        DESCRIPTION    "."
        ::= { tnOpticalPortConfigGroups 484 }

    tnGenericOtPortConfigScalarsGroup OBJECT-GROUP
        OBJECTS {
            tnGenericOtPortConfigAttributeTotal
        }
        STATUS         current
        DESCRIPTION    "."
        ::= { tnOpticalPortConfigGroups 485 }

    tnGenericOtPortConfigGroup OBJECT-GROUP
        OBJECTS {
            tnGenericOtPortConfigFunction,
            tnGenericOtLineAttributes,
            tnGenericOtClientAttributes
        }
        STATUS         current
        DESCRIPTION    "."
        ::= { tnOpticalPortConfigGroups 486 }

    tn1ety100PortConfigScalarsGroup OBJECT-GROUP
        OBJECTS {
            tn1ety100PortConfigAttributeTotal
        }
        STATUS         current
        DESCRIPTION    "."
        ::= { tnOpticalPortConfigGroups 487 }

    tn1ety100PortConfigGroup OBJECT-GROUP
        OBJECTS {
            tn1ety100PortConfigFunction
        }
        STATUS         current
        DESCRIPTION    "."
        ::= { tnOpticalPortConfigGroups 488 }

--    obsolete
--    tnD1ad400qPortConfigScalarsGroup OBJECT-GROUP ::= { tnOpticalPortConfigGroups 489 }
--    tnD1ad400qPortConfigGroup        OBJECT-GROUP ::= { tnOpticalPortConfigGroups 490 }

    tnOmdclPortConfigScalarsGroup OBJECT-GROUP
        OBJECTS {
            tnOmdclPortConfigAttributeTotal
        }
        STATUS         current
        DESCRIPTION    "."
        ::= { tnOpticalPortConfigGroups 491 }

    tnOmdclPortConfigGroup OBJECT-GROUP
        OBJECTS {
            tnOmdclPortConfigFunction,
            tnOmdclPortConfigTargetLinePpcOut,
            tnOmdclPortConfigTargetLinePpcOutL,
            tnOmdclPortConfigOSCVoaAtten,
            tnOmdclPortConfigSpanLossTh,
            tnOmdclPortConfigAsellEnabled,
            tnOmdclPortConfigTargetPowerWidth,
            tnOmdclPortConfigTargetPowerWidthL,
            tnOmdclPortConfigAsellEnabledL,
            tnOmdclPortConfigIngressTargetPowerWidth,
            tnOmdclPortConfigIngressTargetPowerWidthL
        }
        STATUS         current
        DESCRIPTION    "."
        ::= { tnOpticalPortConfigGroups 492 }

    tnMcs16x15lPortConfigScalarsGroup OBJECT-GROUP
        OBJECTS {
            tnMcs16x15lPortConfigAttributeTotal
        }
        STATUS         current
        DESCRIPTION    "."
        ::= { tnOpticalPortConfigGroups 493}

    tnMcs16x15lPortConfigGroup OBJECT-GROUP
        OBJECTS {
            tnMcs16x15lPortConfigFunction
        }
        STATUS         current
        DESCRIPTION    "."
        ::= { tnOpticalPortConfigGroups 494 }

    tnEilalPortConfigScalarsGroup OBJECT-GROUP
        OBJECTS {
            tnEilalPortConfigAttributeTotal
        }
        STATUS         current
        DESCRIPTION    "."
        ::= { tnOpticalPortConfigGroups 495 }

    tnEilalPortConfigGroup OBJECT-GROUP
        OBJECTS {
            tnEilalPortConfigFunction
        }
        STATUS         current
        DESCRIPTION    "."
        ::= { tnOpticalPortConfigGroups 496 }

    tnRa5pbPortConfigScalarsGroup OBJECT-GROUP
        OBJECTS {
            tnRa5pbPortConfigAttributeTotal
        }
        STATUS         current
        DESCRIPTION    "."
        ::= { tnOpticalPortConfigGroups 497 }

    tnRa5pbPortConfigGroup OBJECT-GROUP
        OBJECTS {
            tnRa5pbPortConfigFunction
        }
        STATUS         current
        DESCRIPTION    "."
        ::= { tnOpticalPortConfigGroups 498 }

    tnMlfsbPortConfigScalarsGroup OBJECT-GROUP
        OBJECTS {
            tnMlfsbPortConfigAttributeTotal
        }
        STATUS         current
        DESCRIPTION    "."
        ::= { tnOpticalPortConfigGroups 499 }

    tnMlfsbPortConfigGroup OBJECT-GROUP
        OBJECTS {
            tnMlfsbPortConfigFunction
        }
        STATUS         current
        DESCRIPTION    "."
        ::= { tnOpticalPortConfigGroups 500 }

    tnPortLptConfigScalarsGroup OBJECT-GROUP
        OBJECTS {
            tnPortLptConfigAttributeTotal
        }
        STATUS         current
        DESCRIPTION    "."
        ::= { tnOpticalPortConfigGroups 501 }

    tnPortLptConfigGroup OBJECT-GROUP
        OBJECTS {
            tnPortLptConfigCons,
            tnPortLptConfigFlsDelayTime,
            tnPortLptConfigTxDisDelayTime,
            tnPortLptConfigExtensionTime
        }
        STATUS         current
        DESCRIPTION    "."
        ::= { tnOpticalPortConfigGroups 502 }

    tnPortConfigScalarsGroup OBJECT-GROUP
        OBJECTS {
            tnPortConfigAttributeTotal
        }
        STATUS         current
        DESCRIPTION    "."
        ::= { tnOpticalPortConfigGroups 503 }

    tnPortConfigGroup OBJECT-GROUP
        OBJECTS {
            tnPortConfigFunction,
            tnPortConfigLosProp
        }
        STATUS         current
        DESCRIPTION    "."
        ::= { tnOpticalPortConfigGroups 504 }

    tn18P400PortConfigScalarsGroup OBJECT-GROUP
        OBJECTS {
            tn18P400PortConfigAttributeTotal
        }
        STATUS         current
        DESCRIPTION    "."
        ::= { tnOpticalPortConfigGroups 505 }

    tn18P400PortConfigGroup OBJECT-GROUP
        OBJECTS {
            tn18P400PortConfigFunction
        }
        STATUS         current
        DESCRIPTION    "."
        ::= { tnOpticalPortConfigGroups 506 }

    tn4uc1tPortConfigScalarsGroup OBJECT-GROUP
        OBJECTS {
            tn4uc1tPortConfigAttributeTotal
        }
        STATUS         current
        DESCRIPTION    "."
        ::= { tnOpticalPortConfigGroups 507 }

    tn4uc1tPortConfigGroup OBJECT-GROUP
        OBJECTS {
            tn4uc1tPortConfigFunction
        }
        STATUS         current
        DESCRIPTION    "."
        ::= { tnOpticalPortConfigGroups 508 }

    tnAsgPortConfigScalarsGroup OBJECT-GROUP
        OBJECTS {
            tnAsgPortConfigAttributeTotal
        }
        STATUS         current
        DESCRIPTION    "."
        ::= { tnOpticalPortConfigGroups 509 }

    tnAsgPortConfigGroup OBJECT-GROUP
        OBJECTS {
            tnAsgPortConfigFunction
        }
        STATUS         current
        DESCRIPTION    "."
        ::= { tnOpticalPortConfigGroups 510 }

    tn12p120sPortConfigScalarsGroup OBJECT-GROUP
        OBJECTS {
            tn12p120sPortConfigAttributeTotal
        }
        STATUS         current
        DESCRIPTION    "."
        ::= { tnOpticalPortConfigGroups 511 }

    tn12p120sPortConfigGroup OBJECT-GROUP
        OBJECTS {
            tn12p120sPortConfigFunction
        }
        STATUS         current
        DESCRIPTION    "."
        ::= { tnOpticalPortConfigGroups 512 }

    tn16p200PortConfigScalarsGroup OBJECT-GROUP
        OBJECTS {
            tn16p200PortConfigAttributeTotal
        }
        STATUS         current
        DESCRIPTION    "."
        ::= { tnOpticalPortConfigGroups 513 }

    tn16p200PortConfigGroup OBJECT-GROUP
        OBJECTS {
            tn16p200PortConfigFunction
        }
        STATUS         current
        DESCRIPTION    "."
        ::= { tnOpticalPortConfigGroups 514 }

    tnIr9PortConfigScalarsGroup OBJECT-GROUP
        OBJECTS {
            tnIr9PortConfigAttributeTotal
        }
        STATUS         current
        DESCRIPTION    "."
        ::= { tnOpticalPortConfigGroups 515 }

    tnIr9PortConfigGroup OBJECT-GROUP
        OBJECTS {
            tnIr9PortConfigFunction
        }
        STATUS         current
        DESCRIPTION    "."
        ::= { tnOpticalPortConfigGroups 516 }

    tnMxn824PortConfigScalarsGroup OBJECT-GROUP
        OBJECTS {
            tnMxn824PortConfigAttributeTotal
        }
        STATUS         current
        DESCRIPTION    "."
        ::= { tnOpticalPortConfigGroups 517 }

    tnMxn824PortConfigGroup OBJECT-GROUP
        OBJECTS {
            tnMxn824PortConfigFunction
        }
        STATUS         current
        DESCRIPTION    "."
        ::= { tnOpticalPortConfigGroups 518 }

    tnAsc4PortConfigScalarsGroup OBJECT-GROUP
        OBJECTS {
            tnAsc4PortConfigAttributeTotal
        }
        STATUS         current
        DESCRIPTION    "."
        ::= { tnOpticalPortConfigGroups 519 }

    tnAsc4PortConfigGroup OBJECT-GROUP
        OBJECTS {
            tnAsc4PortConfigFunction
        }
        STATUS         current
        DESCRIPTION    "."
        ::= { tnOpticalPortConfigGroups 520 }

    tn5mx500PortConfigScalarsGroup OBJECT-GROUP
        OBJECTS {
            tn5mx500PortConfigAttributeTotal
        }
        STATUS         current
        DESCRIPTION    "."
        ::= { tnOpticalPortConfigGroups 521 }

    tn5mx500PortConfigGroup OBJECT-GROUP
        OBJECTS {
            tn5mx500PortConfigFunction
        }
        STATUS         current
        DESCRIPTION    "."
        ::= { tnOpticalPortConfigGroups 522 }

    tn2ux500PortConfigScalarsGroup OBJECT-GROUP
        OBJECTS {
            tn2ux500PortConfigAttributeTotal
        }
        STATUS         current
        DESCRIPTION    "."
        ::= { tnOpticalPortConfigGroups 523 }

    tn2ux500PortConfigGroup OBJECT-GROUP
        OBJECTS {
            tn2ux500PortConfigFunction
        }
        STATUS         current
        DESCRIPTION    "."
        ::= { tnOpticalPortConfigGroups 524 }

    tnMxnPortConfigScalarsGroup OBJECT-GROUP
        OBJECTS {
            tnMxnPortConfigAttributeTotal
        }
        STATUS         current
        DESCRIPTION    "."
        ::= { tnOpticalPortConfigGroups 525 }

    tnMxnPortConfigGroup OBJECT-GROUP
        OBJECTS {
            tnMxnPortConfigAlienWaveBank,
            tnMxnPortConfigPlannedFrequencyIn,
            tnMxnPortConfigPlannedFrequencyOut
        }
        STATUS         current
        DESCRIPTION    "."
        ::= { tnOpticalPortConfigGroups 526 }

    tnAscPortConfigScalarsGroup OBJECT-GROUP
        OBJECTS {
            tnAscPortConfigAttributeTotal
        }
        STATUS         current
        DESCRIPTION    "."
        ::= { tnOpticalPortConfigGroups 527 }

    tnAscPortConfigGroup OBJECT-GROUP
        OBJECTS {
            tnAscPortConfigPowerGain,
            tnAscPortConfigPowerGainL,  -- deprecated
            tnAscPortConfigAmpEnable,
            tnAscPortConfigVoaSet
        }
        STATUS         current
        DESCRIPTION    "."
        ::= { tnOpticalPortConfigGroups 528 }

    tnOpsumPortConfigScalarsGroup OBJECT-GROUP
        OBJECTS {
            tnOpsumPortConfigAttributeTotal
        }
        STATUS         current
        DESCRIPTION    "."
        ::= { tnOpticalPortConfigGroups 529 }

    tnOpsumPortConfigGroup OBJECT-GROUP
        OBJECTS {
            tnOpsumPortConfigFunction
        }
        STATUS         current
        DESCRIPTION    "."
        ::= { tnOpticalPortConfigGroups 530 }

    tnMxn1624PortConfigScalarsGroup OBJECT-GROUP
        OBJECTS {
            tnMxn1624PortConfigAttributeTotal
        }
        STATUS         current
        DESCRIPTION    "."
        ::= { tnOpticalPortConfigGroups 531 }

    tnMxn1624PortConfigGroup OBJECT-GROUP
        OBJECTS {
            tnMxn1624PortConfigFunction
        }
        STATUS         current
        DESCRIPTION    "."
        ::= { tnOpticalPortConfigGroups 532 }

    tnIr4PortConfigScalarsGroup OBJECT-GROUP
        OBJECTS {
            tnIr4PortConfigAttributeTotal
        }
        STATUS         current
        DESCRIPTION    "."
        ::= { tnOpticalPortConfigGroups 533 }

    tnIr4PortConfigGroup OBJECT-GROUP
        OBJECTS {
            tnIr4PortConfigFunction
        }
        STATUS         current
        DESCRIPTION    "."
        ::= { tnOpticalPortConfigGroups 534 }

    tnAsc2PortConfigScalarsGroup OBJECT-GROUP
        OBJECTS {
            tnAsc2PortConfigAttributeTotal
        }
        STATUS         current
        DESCRIPTION    "."
        ::= { tnOpticalPortConfigGroups 535 }

    tnAsc2PortConfigGroup OBJECT-GROUP
        OBJECTS {
            tnAsc2PortConfigFunction
        }
        STATUS         current
        DESCRIPTION    "."
        ::= { tnOpticalPortConfigGroups 536 }

    tnFwPortModuleScalarsGroup OBJECT-GROUP
        OBJECTS {
            tnFwPortModuleAttributeTotal
        }
        STATUS         current
        DESCRIPTION    "."
        ::= { tnOpticalPortConfigGroups 537 }

    tnFwPortModuleGroup OBJECT-GROUP
        OBJECTS {
            tnFwPortModule
        }
        STATUS         current
        DESCRIPTION    "."
        ::= { tnOpticalPortConfigGroups 538 }

    tnSfd48PortConfigScalarsGroup OBJECT-GROUP
        OBJECTS {
            tnSfd48PortConfigAttributeTotal
        }
        STATUS         current
        DESCRIPTION    "."
        ::= { tnOpticalPortConfigGroups 539 }

    tnSfd48PortConfigGroup OBJECT-GROUP
        OBJECTS {
            tnSfd48PortConfigFunction
        }
        STATUS         current
        DESCRIPTION    "."
        ::= { tnOpticalPortConfigGroups 540 }

    tnSfd64PortConfigScalarsGroup OBJECT-GROUP
        OBJECTS {
            tnSfd64PortConfigAttributeTotal
        }
        STATUS         current
        DESCRIPTION    "."
        ::= { tnOpticalPortConfigGroups 541 }

    tnSfd64PortConfigGroup OBJECT-GROUP
        OBJECTS {
            tnSfd64PortConfigFunction
        }
        STATUS         current
        DESCRIPTION    "."
        ::= { tnOpticalPortConfigGroups 542 }

    tnIr32AWPortConfigScalarsGroup OBJECT-GROUP
        OBJECTS {
            tnIr32AWPortConfigAttributeTotal
        }
        STATUS         current
        DESCRIPTION    "."
        ::= { tnOpticalPortConfigGroups 543 }

    tnIr32AWPortConfigGroup OBJECT-GROUP
        OBJECTS {
            tnIr32AWPortConfigFunction
        }
        STATUS         current
        DESCRIPTION    "."
        ::= { tnOpticalPortConfigGroups 544 }

    tnEilaAWPortConfigScalarsGroup OBJECT-GROUP
        OBJECTS {
            tnEilaAWPortConfigAttributeTotal
        }
        STATUS         current
        DESCRIPTION    "."
        ::= { tnOpticalPortConfigGroups 545 }

    tnEilaAWPortConfigGroup OBJECT-GROUP
        OBJECTS {
            tnEilaAWPortConfigFunction
        }
        STATUS         current
        DESCRIPTION    "."
        ::= { tnOpticalPortConfigGroups 546 }

    tn18ce300PortConfigScalarsGroup OBJECT-GROUP
        OBJECTS {
            tn18ce300PortConfigAttributeTotal
        }
        STATUS         current
        DESCRIPTION    "."
        ::= { tnOpticalPortConfigGroups 547 }

    tn18ce300PortConfigGroup OBJECT-GROUP
        OBJECTS {
            tn18ce300PortConfigFunction
        }
        STATUS         current
        DESCRIPTION    "."
        ::= { tnOpticalPortConfigGroups 548 }

    tnGnssModuleScalarsGroup OBJECT-GROUP
        OBJECTS {
            tnGnssModuleAttributeTotal
        }
        STATUS         current
        DESCRIPTION    "."
        ::= { tnOpticalPortConfigGroups 549 }

    tnGnssModuleGroup OBJECT-GROUP
        OBJECTS {
            tnGnssModuleAdminState,
            tnGnssModuleOperState,
            tnGnssModuleReset,
            tnGnssModuleMode,
            tnGnssModuleAugmentationMode,
            tnGnssModuleElevationMask,
            tnGnssModuleSNRMask,
            tnGnssModuleTimeAdvance,
            tnGnssModuleAntennaDelayValue,
            tnGnssModuleForcedAntennaConnected,
            tnGnssModulePtpPTPClockPriority1,
            tnGnssModulePtpPTPClockPriority2,
            tnGnssModulePtpPTPClockDomainNumber,
            tnGnssModulePtpPTPPortTxDestMacAddress,
            tnGnssModulePtpPortAsymmetryCorrection,
            tnGnssModuleSyncEMode,
            tnGnssModuleProvisionedRxSsmQL,
            tnGnssModuleTxSsm,
            tnGnssModuleSignalType,
            tnGnssModuleGnssStatusTracking,
            tnGnssModuleGnssStatusLocationMode,
            tnGnssModuleCoordinateLatitude,
            tnGnssModuleCoordinateLongitude,
            tnGnssModuleCoordinateAltitude,
            tnGnssModuleHorizontalAccuracy,
            tnGnssModuleVerticalAccuracy,
            tnGnssModuleTimeDOP,
            tnGnssModuleHorizontalDOP,
            tnGnssModuleVerticalDOP,
            tnGnssModuleSatelliteStatus,
            tnGnssModulePTPClockProfile,
            tnGnssModulePTPClockType,
            tnGnssModulePTPClockGmClockIdentity,
            tnGnssModulePTPClockClockClass,
            tnGnssModulePTPClockClockRecoveryState,
            tnGnssModulePTPClockPhaseRecoveryState,
            tnGnssModulePTPClockTimeSource,
            tnGnssModulePTPClockFreqTraceabilityStatus,
            tnGnssModulePTPClockTimeTraceabilityStatus,
            tnGnssModulePTPPortmAnnounceMsgRate,
            tnGnssModulePTPPortSyncMessageRate,
            tnGnssModulePTPPortmDelayReqRespMsgRate,
            tnGnssModuleMessageMode,
            tnGnssModuleClockStatusFrequency,
            tnGnssModuleAlmProfName
        }
        STATUS         current
        DESCRIPTION    "."
        ::= { tnOpticalPortConfigGroups 550 }

    tnOpsumlPortConfigScalarsGroup OBJECT-GROUP
        OBJECTS {
            tnOpsumlPortConfigAttributeTotal
        }
        STATUS         current
        DESCRIPTION    "."
        ::= { tnOpticalPortConfigGroups 551 }

    tnOpsumlPortConfigGroup OBJECT-GROUP
        OBJECTS {
            tnOpsumlPortConfigFunction
        }
        STATUS         current
        DESCRIPTION    "."
        ::= { tnOpticalPortConfigGroups 552 }

--------------------------------------------------------------------------------
-- Conformance Port Info Group Definitions
--------------------------------------------------------------------------------
    tnSdhPortInfoScalarsGroup OBJECT-GROUP
        OBJECTS {
            tnSdhPortInfoAttributeTotal
        }
        STATUS         current
        DESCRIPTION    "."
        ::= { tnOpticalPortInfoGroups 1 }

    tnSdhPortInfoGroup OBJECT-GROUP
        OBJECTS {
            tnSdhPortRxSectionTrace,
--            obsolete
--            tnSdhPortTxSynchStatusMessage,
            tnSdhPortTiming,
--            obsolete
--            tnSdhPortRxSynchStatusMessage,
            tnSdhPortRxSectionTraceValid,
            tnSdhPortTxSynchronizeStatusMessage,
            tnSdhPortRxSynchronizeStatusMessage
        }
        STATUS         current
        DESCRIPTION    "."
        ::= { tnOpticalPortInfoGroups 2 }

--    obsolete
--    tnOC48STM16PortInfoScalarsGroup             OBJECT-GROUP ::= { tnOpticalPortInfoGroups 3 }
--    tnOC48STM16PortInfoGroup                    OBJECT-GROUP ::= { tnOpticalPortInfoGroups 4 }
--    tnOC192STM64PortInfoScalarsGroup            OBJECT-GROUP ::= { tnOpticalPortInfoGroups 5 }
--    tnOC192STM64PortInfoGroup                   OBJECT-GROUP ::= { tnOpticalPortInfoGroups 6 }
--    tnQuadOC48STM16MuxPortInfoScalarsGroup      OBJECT-GROUP ::= { tnOpticalPortInfoGroups 7 }
--    tnQuadOC48STM16MuxPortInfoGroup             OBJECT-GROUP ::= { tnOpticalPortInfoGroups 8 }
--    tnQuadOC3or12STM1or4MuxPortInfoScalarsGroup OBJECT-GROUP ::= { tnOpticalPortInfoGroups 9 }
--    tnQuadOC3or12STM1or4MuxPortInfoGroup        OBJECT-GROUP ::= { tnOpticalPortInfoGroups 10 }
--    tnBandFilterPortInfoScalarsGroup            OBJECT-GROUP ::= { tnOpticalPortInfoGroups 11 }
--    tnBandFilterPortInfoGroup                   OBJECT-GROUP ::= { tnOpticalPortInfoGroups 12 }

    tnOscPortInfoScalarsGroup OBJECT-GROUP
        OBJECTS {
            tnOscPortInfoAttributeTotal
        }
        STATUS         current
        DESCRIPTION    "."
        ::= { tnOpticalPortInfoGroups 13 }

    tnOscPortInfoGroup OBJECT-GROUP
        OBJECTS {
            tnOscPortInfoFunction,
            tnOscPortTotalNwPowerIn,
            tnOscPortTotalNwPowerOut,
            tnOscPortPhyDeviceLinkStatus,
            tnOscPortPhyDeviceIdNo,
            tnOscPortPhyDeviceMfgModelNo,
            tnOscPortPhyDeviceMfgRevNo
        }
        STATUS         current
        DESCRIPTION    "."
        ::= { tnOpticalPortInfoGroups 14 }

--    obsolete
--    tnChFilterPortInfoScalarsGroup    OBJECT-GROUP ::= { tnOpticalPortInfoGroups 15 }
--    tnChFilterPortInfoGroup           OBJECT-GROUP ::= { tnOpticalPortInfoGroups 16 }
--    tnChAddDropPortInfoScalarsGroup   OBJECT-GROUP ::= { tnOpticalPortInfoGroups 17 }
--    tnChAddDropPortInfoGroup          OBJECT-GROUP ::= { tnOpticalPortInfoGroups 18 }
--    tnBbaHgPortInfoScalarsGroup       OBJECT-GROUP ::= { tnOpticalPortInfoGroups 19 }
--    tnBbaHgPortInfoGroup              OBJECT-GROUP ::= { tnOpticalPortInfoGroups 20 }
--    tnBbaLgPortInfoScalarsGroup       OBJECT-GROUP ::= { tnOpticalPortInfoGroups 21 }
--    tnBbaLgPortInfoGroup              OBJECT-GROUP ::= { tnOpticalPortInfoGroups 22 }
--    tnPpsPortInfoScalarsGroup         OBJECT-GROUP ::= { tnOpticalPortInfoGroups 23 }
--    tnPpsPortInfoGroup                OBJECT-GROUP ::= { tnOpticalPortInfoGroups 24 }
--    tnDualGigEMuxPortInfoScalarsGroup OBJECT-GROUP ::= { tnOpticalPortInfoGroups 25 }
--    tnDualGigEMuxPortInfoGroup        OBJECT-GROUP ::= { tnOpticalPortInfoGroups 26 }
--    tnRoadmPortInfoScalarsGroup       OBJECT-GROUP ::= { tnOpticalPortInfoGroups 27 }
--    tnRoadmPortInfoGroup              OBJECT-GROUP ::= { tnOpticalPortInfoGroups 28 }
--    tn10GigELANPortInfoScalarsGroup   OBJECT-GROUP ::= { tnOpticalPortInfoGroups 29 }
--    tn10GigELANPortInfoGroup          OBJECT-GROUP ::= { tnOpticalPortInfoGroups 30 }

    tnDcmPortInfoScalarsGroup OBJECT-GROUP
        OBJECTS {
            tnDcmPortInfoAttributeTotal
        }
        STATUS         current
        DESCRIPTION    "."
        ::= { tnOpticalPortInfoGroups 31 }

    tnDcmPortInfoGroup OBJECT-GROUP
        OBJECTS {
            tnDcmPortInfoFunction,
            tnDcmPortInfoIroadmConnAddress
        }
        STATUS         current
        DESCRIPTION    "."
        ::= { tnOpticalPortInfoGroups 32 }

--    obsolete
--    tnDecaGigEMuxPortInfoScalarsGroup OBJECT-GROUP ::= { tnOpticalPortInfoGroups 33 }
--    tnDecaGigEMuxPortInfoGroup        OBJECT-GROUP ::= { tnOpticalPortInfoGroups 34 }

    tnSonetPortInfoScalarsGroup OBJECT-GROUP
        OBJECTS {
            tnSonetPortInfoAttributeTotal
        }
        STATUS         current
        DESCRIPTION    "."
        ::= { tnOpticalPortInfoGroups 35 }

    tnSonetPortInfoGroup OBJECT-GROUP
        OBJECTS {
            tnSonetPortRxSectionTrace,
            tnSonetPortTxSynchStatusMessage,
            tnSonetPortTiming,
            tnSonetPortRxSynchStatusMessage,
            tnSonetPortRxSectionTraceValid
        }
        STATUS         current
        DESCRIPTION    "."
        ::= { tnOpticalPortInfoGroups 36 }

--    obsolete
--    tnExternalDcuPortInfoScalarsGroup OBJECT-GROUP ::= { tnOpticalPortInfoGroups 37 }
--    tnExternalDcuPortInfoGroup        OBJECT-GROUP ::= { tnOpticalPortInfoGroups 38 }

    tnDigitalWrapperPortInfoScalarsGroup OBJECT-GROUP
        OBJECTS {
            tnDigitalWrapperPortInfoAttributeTotal
        }
        STATUS         current
        DESCRIPTION    "."
        ::= { tnOpticalPortInfoGroups 39 }

    tnDigitalWrapperPortInfoGroup OBJECT-GROUP
        OBJECTS {
            tnDwPortRxPMTTI,
            tnDwPortRxPMExpectedTTI,
            tnDwPortTxPMTTI
        }
        STATUS         current
        DESCRIPTION    "."
        ::= { tnOpticalPortInfoGroups 40 }

--    obsolete
--    tnMsaHgPortInfoScalarsGroup OBJECT-GROUP ::= { tnOpticalPortInfoGroups 41 }
--    tnMsaHgPortInfoGroup        OBJECT-GROUP ::= { tnOpticalPortInfoGroups 42 }
--    tnWssX9PortInfoScalarsGroup OBJECT-GROUP ::= { tnOpticalPortInfoGroups 43 }
--    tnWssX9PortInfoGroup        OBJECT-GROUP ::= { tnOpticalPortInfoGroups 44 }

    tnSfpPortInfoScalarsGroup OBJECT-GROUP
        OBJECTS {
            tnSfpPortInfoAttributeTotal
        }
        STATUS         current
        DESCRIPTION    "."
        ::= { tnOpticalPortInfoGroups 45 }

    tnSfpPortInfoGroup OBJECT-GROUP
        OBJECTS {
            tnSfpPortModulePresentType,
            tnSfpPortModuleVendorSerNo,
            tnSfpPortModuleState,
            tnSfpPortModuleVendor,
            tnSfpPortTxDisable,
            tnSfpPortWavelength,
            tnSfpPortModuleType,
            tnSfpPortCLEI,
            tnSfpPortUnitPartNum,
            tnSfpPortSWPartNum,
            tnSfpPortFactoryID,
            tnSfpPortDate,
            tnSfpPortExtraData,
            tnSfpPortMaximumCaseTemperature,
            tnSfpPortInterchangeabilityMarking,
            tnSfpPortAcronymCode,
            tnSfpPortPowerClass,
            tnSfpPortFirmwareVersion,
            tnSfpPortMaximumPowerConsumption
        }
        STATUS         current
        DESCRIPTION    "."
        ::= { tnOpticalPortInfoGroups 46 }

--    obsolete
--    tn1xMR2dot5GPortInfoScalarsGroup OBJECT-GROUP ::= { tnOpticalPortInfoGroups 47 }
--    tn1xMR2dot5GPortInfoGroup        OBJECT-GROUP ::= { tnOpticalPortInfoGroups 48 }

    tnNetworkPortInfoScalarsGroup OBJECT-GROUP
        OBJECTS {
            tnNetworkPortInfoAttributeTotal
        }
        STATUS         current
        DESCRIPTION    "."
        ::= { tnOpticalPortInfoGroups 49 }

    tnNetworkPortInfoGroup OBJECT-GROUP
        OBJECTS {
--          obsolete
--            tnNwPortOchRxStatus,
--            tnNwPortOchTxStatus,
            tnNwPortPresentChannel
        }
        STATUS         current
        DESCRIPTION    "."
        ::= { tnOpticalPortInfoGroups 50 }

    tnOpsaPortInfoScalarsGroup OBJECT-GROUP
        OBJECTS {
            tnOpsaPortInfoAttributeTotal
        }
        STATUS         current
        DESCRIPTION    "."
        ::= { tnOpticalPortInfoGroups 51 }

    tnOpsaPortInfoGroup OBJECT-GROUP
        OBJECTS {
            tnOpsaPortInfoFunction,
            tnOpsaPortReceivedPower,              -- deprecated
            tnOpsaPortPresentTransmitAttenuation  -- deprecated
        }
        STATUS         current
        DESCRIPTION    "."
        ::= { tnOpticalPortInfoGroups 52 }

    tn11stmm10PortInfoScalarsGroup OBJECT-GROUP
        OBJECTS {
            tn11stmm10PortInfoAttributeTotal
        }
        STATUS         current
        DESCRIPTION    "."
        ::= { tnOpticalPortInfoGroups 53 }

    tn11stmm10PortInfoGroup OBJECT-GROUP
        OBJECTS {
            tn11stmm10PortInfoFunction
        }
        STATUS         current
        DESCRIPTION    "."
        ::= { tnOpticalPortInfoGroups 54 }

    tn11star1PortInfoScalarsGroup OBJECT-GROUP
        OBJECTS {
            tn11star1PortInfoAttributeTotal
        }
        STATUS         current
        DESCRIPTION    "."
        ::= { tnOpticalPortInfoGroups 55 }

    tn11star1PortInfoGroup OBJECT-GROUP
        OBJECTS {
            tn11star1PortInfoFunction
        }
        STATUS         current
        DESCRIPTION    "."
        ::= { tnOpticalPortInfoGroups 56 }

    tnAhphgPortInfoScalarsGroup OBJECT-GROUP
        OBJECTS {
            tnAhphgPortInfoAttributeTotal
        }
        STATUS         current
        DESCRIPTION    "."
        ::= { tnOpticalPortInfoGroups 57 }

    tnAhphgPortInfoGroup OBJECT-GROUP
        OBJECTS {
            tnAhphgPortInfoFunction
        }
        STATUS         current
        DESCRIPTION    "."
        ::= { tnOpticalPortInfoGroups 58 }

    tnAlphgPortInfoScalarsGroup OBJECT-GROUP
        OBJECTS {
            tnAlphgPortInfoAttributeTotal
        }
        STATUS         current
        DESCRIPTION    "."
        ::= { tnOpticalPortInfoGroups 59 }

    tnAlphgPortInfoGroup OBJECT-GROUP
        OBJECTS {
            tnAlphgPortInfoFunction
        }
        STATUS         current
        DESCRIPTION    "."
        ::= { tnOpticalPortInfoGroups 60 }

    tnCwr8PortInfoScalarsGroup OBJECT-GROUP
        OBJECTS {
            tnCwr8PortInfoAttributeTotal
        }
        STATUS         current
        DESCRIPTION    "."
        ::= { tnOpticalPortInfoGroups 61 }

    tnCwr8PortInfoGroup OBJECT-GROUP
        OBJECTS {
            tnCwr8PortInfoFunction,
--            obsolete
--            tnCwr8PortTotalNwPowerIn,
--            tnCwr8PortTotalNwPowerOut,
            tnCwr8PortRelativeAttenuationMin,
            tnCwr8PortAverageAttenuationOut
        }
        STATUS         current
        DESCRIPTION    "."
        ::= { tnOpticalPortInfoGroups 62 }

    tn11stge12PortInfoScalarsGroup OBJECT-GROUP
        OBJECTS {
            tn11stge12PortInfoAttributeTotal
        }
        STATUS         current
        DESCRIPTION    "."
        ::= { tnOpticalPortInfoGroups 63 }

    tn11stge12PortInfoGroup OBJECT-GROUP
        OBJECTS {
            tn11stge12PortInfoFunction
        }
        STATUS         current
        DESCRIPTION    "."
        ::= { tnOpticalPortInfoGroups 64 }

    tn11dpge12PortInfoScalarsGroup OBJECT-GROUP
        OBJECTS {
            tn11dpge12PortInfoAttributeTotal
        }
        STATUS         current
        DESCRIPTION    "."
        ::= { tnOpticalPortInfoGroups 65 }

    tn11dpge12PortInfoGroup OBJECT-GROUP
        OBJECTS {
            tn11dpge12PortInfoFunction,
            tn11dpge12PortAvailableBandwidth,
            tn11dpge12PortTotalVTS,
            tn11dpge12PortIngAvailableBandwidth,
            tn11dpge12PortEgrAvailableBandwidth
        }
        STATUS         current
        DESCRIPTION    "."
        ::= { tnOpticalPortInfoGroups 66 }

--    obsolete
--    tnDwdmGpPhyPortInfoGroup OBJECT-GROUP ::= { tnOpticalPortInfoGroups 67 }

    tnDwdmCmnLinePortInfoGroup OBJECT-GROUP
        OBJECTS {
            tnDwdmCmnLinePortOtu2IncomingTti,
            tnDwdmCmnLinePortOtu2TtiStatus,
            tnDwdmCmnLinePortOdu2IncomingTti,
            tnDwdmCmnLinePortOdu2TtiStatus,
--            obsolete
--            tnDwdmCmnLinePortAvailableBandwidth,
            tnDwdmCmnLinePortOtu2PreFec,
            tnDwdmCmnLinePortOtu2PostFec,
            tnDwdmCmnLinePortOdu2IncFwFTFLTypeID,
            tnDwdmCmnLinePortOdu2IncFwFTFLOperID,
            tnDwdmCmnLinePortOdu2IncBwFTFLTypeID,
            tnDwdmCmnLinePortOdu2IncBwFTFLOperID,
            tnDwdmCmnLinePortOdu2IncResRow2,
            tnDwdmCmnLinePortOdu2IncResRow4,
            tnDwdmCmnLinePortOdu2IncExp,
            tnDwdmCmnLinePortOtu2IncRes,
            tnDwdmCmnLinePortDMInfoCurrentStatus,
            tnDwdmCmnLinePortDMInfoCurrentValue,
            tnDwdmCmnLinePortOtsigId,
            tnDwdmCmnLinePortOtsigModuleCapabilityFileName,
            tnDwdmCmnLinePortDisruptionTime
        }
        STATUS         current
        DESCRIPTION    "."
        ::= { tnOpticalPortInfoGroups 68 }

    tnDwdmCmnClientPortInfoGroup OBJECT-GROUP
        OBJECTS {
            tnDwdmCmnClientPortOtu2IncomingTti,
            tnDwdmCmnClientPortOtu2TtiStatus,
            tnDwdmCmnClientPortOdu2IncomingTti,
            tnDwdmCmnClientPortOdu2TtiStatus,
--            obsolete
--            tnDwdmCmnClientPortAvailableBandwidth,
            tnDwdmCmnClientPortBroadcastPortMap,
            tnDwdmCmnClientPortOtu2PreFec,
            tnDwdmCmnClientPortOtu2PostFec,
            tnDwdmCmnClientPortOdu2IncFwFTFLTypeID,
            tnDwdmCmnClientPortOdu2IncFwFTFLOperID,
            tnDwdmCmnClientPortOdu2IncBwFTFLTypeID,
            tnDwdmCmnClientPortOdu2IncBwFTFLOperID,
            tnDwdmCmnClientPortOdu2IncResRow2,
            tnDwdmCmnClientPortOdu2IncResRow4,
            tnDwdmCmnClientPortOdu2IncExp,
            tnDwdmCmnClientPortOtu2IncRes,
            tnDwdmCmnClientPortEthPrefec,
            tnDwdmCmnClientPortEthPostfec
        }
        STATUS         current
        DESCRIPTION    "."
        ::= { tnOpticalPortInfoGroups 69 }

    tnRsmonIngrPortInfoGroup OBJECT-GROUP
        OBJECTS {
            tnRsmonIngrPortIncomingTti,
            tnRsmonIngrPortTtiStatus
        }
        STATUS         current
        DESCRIPTION    "."
        ::= { tnOpticalPortInfoGroups 70 }

    tnOtPortInfoGroup OBJECT-GROUP
        OBJECTS {
            tnOtPortRxPower,
            tnOtPortTxPower,
            tnOtPortBias,
            tnOtPortTemperature,
            tnOtPortTxPowerLaser,
            tnOtPortRxLanePowers,
            tnOtPortTxLanePowers,
            tnOtPortRxLaneBslPowers,
            tnOtPortTxLaneBslPowers,
            tnOtPortQsfpCurrentBias,
            tnOtPortQsfpVoltage,
            tnOtPortSupplyVoltage,
            tnOtPortSupplyCurrent,
            tnOtPortSupplyPower,
            tnOtPortTxLaserAge,
            tnOtPortLaserTemp,
            tnOtPortRxQmargin30s,
            tnOtPortRxQmargin5s,
            tnOtPortRxQfactor30s,
            tnOtPortRxQfactor5s,
            tnOtPortNEQfactor1s,
            tnOtPortFEQfactor1s,
            tnOtPortTuningSynchroStateRx,
            tnOtPortTuningSynchroStateTx
        }
        STATUS         current
        DESCRIPTION    "."
        ::= { tnOpticalPortInfoGroups 71 }

    tnWaveKeyPortInfoGroup OBJECT-GROUP
        OBJECTS {
            tnWaveKeyPortNwPowerIn,
            tnWaveKeyPortNwPowerOut,
--            obsolete
--            tnWavekeyPortWTDecoderUsageStatusIn,
--            tnWavekeyPortWTDecoderUsageStatusOut,
            tnWaveKeyPortWTDecoderMeasurementTypeIn,
            tnWaveKeyPortWTDecoderMeasurementTypeOut,
            tnWaveKeyPortNwPowerInL,
            tnWaveKeyPortNwPowerOutL,
            tnWaveKeyPortWTDecoderMeasurementTypeInL,
            tnWaveKeyPortWTDecoderMeasurementTypeOutL
        }
        STATUS         current
        DESCRIPTION    "."
        ::= { tnOpticalPortInfoGroups 72 }

    tnOmdPortInfoGroup OBJECT-GROUP
        OBJECTS {
            tnOmdPortReceivedPower,
            tnOmdPortTransmittedPower
        }
        STATUS         current
        DESCRIPTION    "."
        ::= { tnOpticalPortInfoGroups 73 }

    tn4dpa4PortInfoScalarsGroup OBJECT-GROUP
        OBJECTS {
            tn4dpa4PortInfoAttributeTotal
        }
        STATUS         current
        DESCRIPTION    "."
        ::= { tnOpticalPortInfoGroups 74 }

    tn4dpa4PortInfoGroup OBJECT-GROUP
        OBJECTS {
            tn4dpa4PortInfoFunction
        }
        STATUS         current
        DESCRIPTION    "."
        ::= { tnOpticalPortInfoGroups 75 }

    tnCwr8c88PortInfoScalarsGroup OBJECT-GROUP
        OBJECTS {
            tnCwr8c88PortInfoAttributeTotal
        }
        STATUS         current
        DESCRIPTION    "."
        ::= { tnOpticalPortInfoGroups 76 }

    tnCwr8c88PortInfoGroup OBJECT-GROUP
        OBJECTS {
            tnCwr8c88PortInfoFunction,
            tnCwr8c88PortRelativeAttenuationMin,
            tnCwr8c88PortAverageAttenuationOut
        }
        STATUS         current
        DESCRIPTION    "."
        ::= { tnOpticalPortInfoGroups 77 }

    tnAhplgPortInfoScalarsGroup OBJECT-GROUP
        OBJECTS {
            tnAhplgPortInfoAttributeTotal
        }
        STATUS         current
        DESCRIPTION    "."
        ::= { tnOpticalPortInfoGroups 78 }

    tnAhplgPortInfoGroup OBJECT-GROUP
        OBJECTS {
            tnAhplgPortInfoFunction
        }
        STATUS         current
        DESCRIPTION    "."
        ::= { tnOpticalPortInfoGroups 79 }

    tnTimeSlotLinePortInfoGroup OBJECT-GROUP
        OBJECTS {
            tnTimeSlotLinePortFarEndIfType,
            tnTimeSlotLinePortFarEndInterfaceIndex,
            tnTimeSlotLinePortNearEndIfType,
            tnTimeSlotLinePortNearEndInterfaceIndex
        }
        STATUS         current
        DESCRIPTION    "."
        ::= { tnOpticalPortInfoGroups 80 }

    tnDwdmCmnOtu1Odu1LinePortInfoGroup OBJECT-GROUP
        OBJECTS {
            tnDwdmCmnLinePortOtu1IncomingTti,
            tnDwdmCmnLinePortOtu1TtiStatus,
            tnDwdmCmnLinePortOdu1IncomingTti,
            tnDwdmCmnLinePortOdu1TtiStatus
        }
        STATUS         current
        DESCRIPTION    "."
        ::= { tnOpticalPortInfoGroups 81 }

    tnDwdmCmnOtu1Odu1ClientPortInfoGroup OBJECT-GROUP
        OBJECTS {
            tnDwdmCmnClientPortOtu1IncomingTti,
            tnDwdmCmnClientPortOtu1TtiStatus,
            tnDwdmCmnClientPortOdu1IncomingTti,
            tnDwdmCmnClientPortOdu1TtiStatus,
            tnDwdmCmnClientPortOtu1PreFec,
            tnDwdmCmnClientPortOtu1PostFec
        }
        STATUS         current
        DESCRIPTION    "."
        ::= { tnOpticalPortInfoGroups 82 }

    tn43stx4PortInfoScalarsGroup OBJECT-GROUP
        OBJECTS {
            tn43stx4PortInfoAttributeTotal
        }
        STATUS         current
        DESCRIPTION    "."
        ::= { tnOpticalPortInfoGroups 83 }

    tn43stx4PortInfoGroup OBJECT-GROUP
        OBJECTS {
            tn43stx4PortInfoFunction
        }
        STATUS         current
        DESCRIPTION    "."
        ::= { tnOpticalPortInfoGroups 84 }

    tnDwdmCmnOtu3Odu3LinePortInfoGroup OBJECT-GROUP
        OBJECTS {
            tnDwdmCmnLinePortOtu3IncomingTti,
            tnDwdmCmnLinePortOtu3TtiStatus,
            tnDwdmCmnLinePortOdu3IncomingTti,
            tnDwdmCmnLinePortOdu3TtiStatus,
            tnDwdmCmnLinePortOtu3PreFec,
            tnDwdmCmnLinePortOtu3PostFec,
            tnDwdmCmnLinePortOdu3IncFwFTFLTypeID,
            tnDwdmCmnLinePortOdu3IncFwFTFLOperID,
            tnDwdmCmnLinePortOdu3IncBwFTFLTypeID,
            tnDwdmCmnLinePortOdu3IncBwFTFLOperID,
            tnDwdmCmnLinePortOdu3IncResRow2,
            tnDwdmCmnLinePortOdu3IncResRow4,
            tnDwdmCmnLinePortOdu3IncExp,
            tnDwdmCmnLinePortOtu3IncRes
        }
        STATUS         current
        DESCRIPTION    "."
        ::= { tnOpticalPortInfoGroups 85 }

    tnAlpfgkPortInfoScalarsGroup OBJECT-GROUP
        OBJECTS {
            tnAlpfgkPortInfoAttributeTotal
        }
        STATUS         current
        DESCRIPTION    "."
        ::= { tnOpticalPortInfoGroups 86 }

    tnAlpfgkPortInfoGroup OBJECT-GROUP
        OBJECTS {
            tnAlpfgkPortInfoFunction
        }
        STATUS         current
        DESCRIPTION    "."
        ::= { tnOpticalPortInfoGroups 87 }

    tn4dpa2PortInfoScalarsGroup OBJECT-GROUP
        OBJECTS {
            tn4dpa2PortInfoAttributeTotal
        }
        STATUS         current
        DESCRIPTION    "."
        ::= { tnOpticalPortInfoGroups 88 }

    tn4dpa2PortInfoGroup OBJECT-GROUP
        OBJECTS {
            tn4dpa2PortInfoFunction
        }
        STATUS         current
        DESCRIPTION    "."
        ::= { tnOpticalPortInfoGroups 89 }

    tn43sta1pPortInfoScalarsGroup OBJECT-GROUP
        OBJECTS {
            tn43sta1pPortInfoAttributeTotal
        }
        STATUS         current
        DESCRIPTION    "."
        ::= { tnOpticalPortInfoGroups 90 }

    tn43sta1pPortInfoGroup OBJECT-GROUP
        OBJECTS {
            tn43sta1pPortInfoFunction
        }
        STATUS         current
        DESCRIPTION    "."
        ::= { tnOpticalPortInfoGroups 91 }

    tn43stx4pPortInfoScalarsGroup OBJECT-GROUP
        OBJECTS {
            tn43stx4pPortInfoAttributeTotal
        }
        STATUS         current
        DESCRIPTION    "."
        ::= { tnOpticalPortInfoGroups 92 }

    tn43stx4pPortInfoGroup OBJECT-GROUP
        OBJECTS {
            tn43stx4pPortInfoFunction
        }
        STATUS         current
        DESCRIPTION    "."
        ::= { tnOpticalPortInfoGroups 93 }

    tnRsmonEgrPortInfoGroup OBJECT-GROUP
        OBJECTS {
            tnRsmonEgrPortIncomingTti,
            tnRsmonEgrPortTtiStatus
        }
        STATUS         current
        DESCRIPTION    "."
        ::= { tnOpticalPortInfoGroups 96 }

    tnA2325aPortInfoScalarsGroup OBJECT-GROUP
        OBJECTS {
            tnA2325aPortInfoAttributeTotal
        }
        STATUS         current
        DESCRIPTION    "."
        ::= { tnOpticalPortInfoGroups 97 }

    tnA2325aPortInfoGroup OBJECT-GROUP
        OBJECTS {
            tnA2325aPortInfoFunction
        }
        STATUS         current
        DESCRIPTION    "."
        ::= { tnOpticalPortInfoGroups 98 }

    tn11qpa4PortInfoScalarsGroup OBJECT-GROUP
        OBJECTS {
            tn11qpa4PortInfoAttributeTotal
        }
        STATUS         current
        DESCRIPTION    "."
        ::= { tnOpticalPortInfoGroups 99 }

    tn11qpa4PortInfoGroup OBJECT-GROUP
        OBJECTS {
            tn11qpa4PortInfoFunction
        }
        STATUS         current
        DESCRIPTION    "."
        ::= { tnOpticalPortInfoGroups 100 }

    tn112scx10PortInfoScalarsGroup OBJECT-GROUP
        OBJECTS {
            tn112scx10PortInfoAttributeTotal
        }
        STATUS         current
        DESCRIPTION    "."
        ::= { tnOpticalPortInfoGroups 101 }

    tn112scx10PortInfoGroup OBJECT-GROUP
        OBJECTS {
            tn112scx10PortInfoFunction
        }
        STATUS         current
        DESCRIPTION    "."
        ::= { tnOpticalPortInfoGroups 102 }

    tn112sca1PortInfoScalarsGroup OBJECT-GROUP
        OBJECTS {
            tn112sca1PortInfoAttributeTotal
        }
        STATUS         current
        DESCRIPTION    "."
        ::= { tnOpticalPortInfoGroups 103 }

    tn112sca1PortInfoGroup OBJECT-GROUP
        OBJECTS {
            tn112sca1PortInfoFunction
        }
        STATUS         current
        DESCRIPTION    "."
        ::= { tnOpticalPortInfoGroups 104 }

    tnDwdmCmnOtu4Odu4LinePortInfoGroup OBJECT-GROUP
        OBJECTS {
            tnDwdmCmnLinePortOtu4IncomingTti,
            tnDwdmCmnLinePortOtu4TtiStatus,
            tnDwdmCmnLinePortOdu4IncomingTti,
            tnDwdmCmnLinePortOdu4TtiStatus,
            tnDwdmCmnLinePortOtu4PreFec,
            tnDwdmCmnLinePortOtu4PostFec,
            tnDwdmCmnLinePortOdu4DMInfoCurrentStatus,
            tnDwdmCmnLinePortOdu4DMInfoCurrentValue
        }
        STATUS         current
        DESCRIPTION    "."
        ::= { tnOpticalPortInfoGroups 105 }

    tnDwdmCmnOtu4Odu4ClientPortInfoGroup OBJECT-GROUP
        OBJECTS {
            tnDwdmCmnClientPortOtu4IncomingTti,
            tnDwdmCmnClientPortOtu4TtiStatus,
            tnDwdmCmnClientPortOdu4IncomingTti,
            tnDwdmCmnClientPortOdu4TtiStatus,
            tnDwdmCmnClientPortOtu1PreFec,
            tnDwdmCmnClientPortOtu1PostFec
        }
        STATUS         current
        DESCRIPTION    "."
        ::= { tnOpticalPortInfoGroups 106 }

    tnAlpfgtPortInfoScalarsGroup OBJECT-GROUP
        OBJECTS {
            tnAlpfgtPortInfoAttributeTotal
        }
        STATUS         current
        DESCRIPTION    "."
        ::= { tnOpticalPortInfoGroups 107 }

    tnAlpfgtPortInfoGroup OBJECT-GROUP
        OBJECTS {
            tnAlpfgtPortInfoFunction
        }
        STATUS         current
        DESCRIPTION    "."
        ::= { tnOpticalPortInfoGroups 108 }

    tnOsctPortInfoScalarsGroup OBJECT-GROUP
        OBJECTS {
            tnOsctPortInfoAttributeTotal
        }
        STATUS         current
        DESCRIPTION    "."
        ::= { tnOpticalPortInfoGroups 109 }

    tnOsctPortInfoGroup OBJECT-GROUP
        OBJECTS {
            tnOsctPortInfoFunction
        }
        STATUS         current
        DESCRIPTION    "."
        ::= { tnOpticalPortInfoGroups 110 }

    tnWtocmPortInfoScalarsGroup OBJECT-GROUP
        OBJECTS {
            tnWtocmPortInfoAttributeTotal
        }
        STATUS         current
        DESCRIPTION    "."
        ::= { tnOpticalPortInfoGroups 111 }

    tnWtocmPortInfoGroup OBJECT-GROUP
        OBJECTS {
            tnWtocmPortInfoFunction,
            tnWtocmPortInfoPower,
            tnWtocmPortInfoPowerMonitoredPort
        }
        STATUS         current
        DESCRIPTION    "."
        ::= { tnOpticalPortInfoGroups 112 }

    tnWr2c88PortInfoScalarsGroup OBJECT-GROUP
        OBJECTS {
            tnWr2c88PortInfoAttributeTotal
        }
        STATUS         current
        DESCRIPTION    "."
        ::= { tnOpticalPortInfoGroups 113 }

    tnWr2c88PortInfoGroup OBJECT-GROUP
        OBJECTS {
            tnWr2c88PortInfoFunction,
            tnWr2c88PortRelativeAttenuationMin,
            tnWr2c88PortAverageAttenuationOut
        }
        STATUS         current
        DESCRIPTION    "."
        ::= { tnOpticalPortInfoGroups 114 }

    tnAm2017bPortInfoScalarsGroup OBJECT-GROUP
        OBJECTS {
            tnAm2017bPortInfoAttributeTotal
        }
        STATUS         current
        DESCRIPTION    "."
        ::= { tnOpticalPortInfoGroups 115 }

    tnAm2017bPortInfoGroup OBJECT-GROUP
        OBJECTS {
            tnAm2017bPortInfoFunction
        }
        STATUS         current
        DESCRIPTION    "."
        ::= { tnOpticalPortInfoGroups 116 }


    tnAm2325bPortInfoScalarsGroup OBJECT-GROUP
        OBJECTS {
            tnAm2325bPortInfoAttributeTotal
        }
        STATUS         current
        DESCRIPTION    "."
        ::= { tnOpticalPortInfoGroups 117 }

    tnAm2325bPortInfoGroup OBJECT-GROUP
        OBJECTS {
            tnAm2325bPortInfoFunction
        }
        STATUS         current
        DESCRIPTION    "."
        ::= { tnOpticalPortInfoGroups 118 }

    tn1dpp21PortInfoScalarsGroup OBJECT-GROUP
        OBJECTS {
            tn1dpp21PortInfoAttributeTotal
        }
        STATUS         current
        DESCRIPTION    "."
        ::= { tnOpticalPortInfoGroups 119 }

    tn1dpp21PortInfoGroup OBJECT-GROUP
        OBJECTS {
            tn1dpp21PortInfoFunction,
            tn1dpp21PortClockSourceIncomingQLStatus,
            tn1dpp21PortClockSourceIncomingQL
        }
        STATUS         current
        DESCRIPTION    "."
        ::= { tnOpticalPortInfoGroups 120 }

--    obsolete
--    tnE1T1PortInfoGroup OBJECT-GROUP ::= { tnOpticalPortInfoGroups 121 }

    tnMvacPortInfoScalarsGroup OBJECT-GROUP
        OBJECTS {
            tnMvacPortInfoAttributeTotal
        }
        STATUS         current
        DESCRIPTION    "."
        ::= { tnOpticalPortInfoGroups 122 }

    tnMvacPortInfoGroup OBJECT-GROUP
        OBJECTS {
            tnMvacPortInfoFunction
        }
        STATUS         current
        DESCRIPTION    "."
        ::= { tnOpticalPortInfoGroups 123 }

    tn43scx4PortInfoScalarsGroup OBJECT-GROUP
        OBJECTS {
            tn43scx4PortInfoAttributeTotal
        }
        STATUS         current
        DESCRIPTION    "."
        ::= { tnOpticalPortInfoGroups 126 }

    tn43scx4PortInfoGroup OBJECT-GROUP
        OBJECTS {
            tn43scx4PortInfoFunction
        }
        STATUS         current
        DESCRIPTION    "."
        ::= { tnOpticalPortInfoGroups 127 }

    tnRa2pPortInfoScalarsGroup OBJECT-GROUP
        OBJECTS {
            tnRa2pPortInfoAttributeTotal
        }
        STATUS         current
        DESCRIPTION    "."
        ::= { tnOpticalPortInfoGroups 128 }

    tnRa2pPortInfoGroup OBJECT-GROUP
        OBJECTS {
            tnRa2pPortInfoFunction
        }
        STATUS         current
        DESCRIPTION    "."
        ::= { tnOpticalPortInfoGroups 129 }

    tnAm2318aPortInfoScalarsGroup OBJECT-GROUP
        OBJECTS {
            tnAm2318aPortInfoAttributeTotal
        }
        STATUS         current
        DESCRIPTION    "."
        ::= { tnOpticalPortInfoGroups 130 }

    tnAm2318aPortInfoGroup OBJECT-GROUP
        OBJECTS {
            tnAm2318aPortInfoFunction
        }
        STATUS         current
        DESCRIPTION    "."
        ::= { tnOpticalPortInfoGroups 131 }

    tnAm2125aPortInfoScalarsGroup OBJECT-GROUP
        OBJECTS {
            tnAm2125aPortInfoAttributeTotal
        }
        STATUS         current
        DESCRIPTION    "."
        ::= { tnOpticalPortInfoGroups 132 }

    tnAm2125aPortInfoGroup OBJECT-GROUP
        OBJECTS {
            tnAm2125aPortInfoFunction
        }
        STATUS         current
        DESCRIPTION    "."
        ::= { tnOpticalPortInfoGroups 133 }

    tnWr8c88aPortInfoScalarsGroup OBJECT-GROUP
        OBJECTS {
            tnWr8c88aPortInfoAttributeTotal
        }
        STATUS         current
        DESCRIPTION    "."
        ::= { tnOpticalPortInfoGroups 134 }

    tnWr8c88aPortInfoGroup OBJECT-GROUP
        OBJECTS {
            tnWr8c88aPortInfoFunction
        }
        STATUS         current
        DESCRIPTION    "."
        ::= { tnOpticalPortInfoGroups 135 }

    tn11dpe12ePortInfoScalarsGroup OBJECT-GROUP
        OBJECTS {
            tn11dpe12ePortInfoAttributeTotal
        }
        STATUS         current
        DESCRIPTION    "."
        ::= { tnOpticalPortInfoGroups 136 }

    tn11dpe12ePortInfoGroup OBJECT-GROUP
        OBJECTS {
            tn11dpe12ePortInfoFunction,
            tn11dpe12ePortTotalVTS,
            tn11dpe12ePortIngAvailableBandwidth,
            tn11dpe12ePortEgrAvailableBandwidth
        }
        STATUS         current
        DESCRIPTION    "."
        ::= { tnOpticalPortInfoGroups 137 }

    tn112sx10lPortInfoScalarsGroup OBJECT-GROUP
        OBJECTS {
            tn112sx10lPortInfoAttributeTotal
        }
        STATUS         current
        DESCRIPTION    "."
        ::= { tnOpticalPortInfoGroups 138 }

    tn112sx10lPortInfoGroup OBJECT-GROUP
        OBJECTS {
            tn112sx10lPortInfoFunction
        }
        STATUS         current
        DESCRIPTION    "."
        ::= { tnOpticalPortInfoGroups 139 }

    tn112sa1lPortInfoScalarsGroup OBJECT-GROUP
        OBJECTS {
            tn112sa1lPortInfoAttributeTotal
        }
        STATUS         current
        DESCRIPTION    "."
        ::= { tnOpticalPortInfoGroups 140 }

    tn112sa1lPortInfoGroup OBJECT-GROUP
        OBJECTS {
            tn112sa1lPortInfoFunction
        }
        STATUS         current
        DESCRIPTION    "."
        ::= { tnOpticalPortInfoGroups 141 }

    tn11dpm12PortInfoScalarsGroup OBJECT-GROUP
        OBJECTS {
            tn11dpm12PortInfoAttributeTotal
        }
        STATUS         current
        DESCRIPTION    "."
        ::= { tnOpticalPortInfoGroups 142 }

    tn11dpm12PortInfoGroup OBJECT-GROUP
        OBJECTS {
            tn11dpm12PortInfoFunction
        }
        STATUS         current
        DESCRIPTION    "."
        ::= { tnOpticalPortInfoGroups 143 }

    tnRamanPortInfoGroup OBJECT-GROUP
        OBJECTS {
            tnRamanPortTotalPowerIn,
            tnRamanPortTotalPowerOut,
            tnRamanPortSignalPowerOut,
            tnRamanPortAsePowerOut,
            tnRamanPortGain,
            tnRamanPortPump1Power,
            tnRamanPortPump2Power,
            tnRamanPortPump3Power,
            tnRamanPortPump4Power,
            tnRamanPortPump5Power,
            tnRamanPortBRRbaseline,
            tnRamanPortPumpPowers,
            tnRamanPortBRRCurrent,
            tnRamanPortORLCurrentValue,
            tnRamanPortSpanLoss
        }
        STATUS         current
        DESCRIPTION    "."
        ::= { tnOpticalPortInfoGroups 144 }

    tnMesh4PortInfoScalarsGroup OBJECT-GROUP
        OBJECTS {
            tnMesh4PortInfoAttributeTotal
        }
        STATUS         current
        DESCRIPTION    "."
        ::= { tnOpticalPortInfoGroups 145 }

    tnMesh4PortInfoGroup OBJECT-GROUP
        OBJECTS {
            tnMesh4PortInfoFunction
        }
        STATUS         current
        DESCRIPTION    "."
        ::= { tnOpticalPortInfoGroups 146 }

--    obsolete
--    tnTcmPortInfoScalarsGroup OBJECT-GROUP ::= { tnOpticalPortInfoGroups 147 }
--    tnTcmPortInfoGroup        OBJECT-GROUP ::= { tnOpticalPortInfoGroups 148 }

    tn43sca1PortInfoScalarsGroup OBJECT-GROUP
        OBJECTS {
            tn43sca1PortInfoAttributeTotal
        }
        STATUS         current
        DESCRIPTION    "."
        ::= { tnOpticalPortInfoGroups 149 }

    tn43sca1PortInfoGroup OBJECT-GROUP
        OBJECTS {
            tn43sca1PortInfoFunction
        }
        STATUS         current
        DESCRIPTION    "."
        ::= { tnOpticalPortInfoGroups 150 }

    tn43scx4lPortInfoScalarsGroup OBJECT-GROUP
        OBJECTS {
            tn43scx4lPortInfoAttributeTotal
        }
        STATUS         current
        DESCRIPTION    "."
        ::= { tnOpticalPortInfoGroups 151 }

    tn43scx4lPortInfoGroup OBJECT-GROUP
        OBJECTS {
            tn43scx4lPortInfoFunction
        }
        STATUS         current
        DESCRIPTION    "."
        ::= { tnOpticalPortInfoGroups 152 }

    tnAm2125bPortInfoScalarsGroup OBJECT-GROUP
        OBJECTS {
            tnAm2125bPortInfoAttributeTotal
        }
        STATUS         current
        DESCRIPTION    "."
        ::= { tnOpticalPortInfoGroups 153 }

    tnAm2125bPortInfoGroup OBJECT-GROUP
        OBJECTS {
            tnAm2125bPortInfoFunction
        }
        STATUS         current
        DESCRIPTION    "."
        ::= { tnOpticalPortInfoGroups 154 }

    tn112snx10PortInfoScalarsGroup OBJECT-GROUP
        OBJECTS {
            tn112snx10PortInfoAttributeTotal
        }
        STATUS         current
        DESCRIPTION    "."
        ::= { tnOpticalPortInfoGroups 155 }

    tn112snx10PortInfoGroup OBJECT-GROUP
        OBJECTS {
            tn112snx10PortInfoFunction
        }
        STATUS         current
        DESCRIPTION    "."
        ::= { tnOpticalPortInfoGroups 156 }

    tn112sna1PortInfoScalarsGroup OBJECT-GROUP
        OBJECTS {
            tn112sna1PortInfoAttributeTotal
        }
        STATUS         current
        DESCRIPTION    "."
        ::= { tnOpticalPortInfoGroups 157 }

    tn112sna1PortInfoGroup OBJECT-GROUP
        OBJECTS {
            tn112sna1PortInfoFunction
        }
        STATUS         current
        DESCRIPTION    "."
        ::= { tnOpticalPortInfoGroups 158 }

--    obsolete
--    tn11qta4PortInfoScalarsGroup OBJECT-GROUP ::= { tnOpticalPortInfoGroups 159 }
--    tn11qta4PortInfoGroup        OBJECT-GROUP ::= { tnOpticalPortInfoGroups 160 }

    tn1dpp24mPortInfoScalarsGroup OBJECT-GROUP
        OBJECTS {
            tn1dpp24mPortInfoAttributeTotal
        }
        STATUS         current
        DESCRIPTION    "."
        ::= { tnOpticalPortInfoGroups 161 }

    tn1dpp24mPortInfoGroup OBJECT-GROUP
        OBJECTS {
            tn1dpp24mPortInfoFunction
--            obsolete
--            tn1dpp24mPortClockSourceIncomingQLStatus,
--            tn1dpp24mPortClockSourceIncomingQL
        }
        STATUS         current
        DESCRIPTION    "."
        ::= { tnOpticalPortInfoGroups 162 }

    tnDwdmCmnOtu3Odu3ClientPortInfoGroup OBJECT-GROUP
        OBJECTS {
            tnDwdmCmnClientPortOtu3IncomingTti,
            tnDwdmCmnClientPortOtu3TtiStatus,
            tnDwdmCmnClientPortOdu3IncomingTti,
            tnDwdmCmnClientPortOdu3TtiStatus,
            tnDwdmCmnClientPortOtu3PreFec,
            tnDwdmCmnClientPortOtu3PostFec
        }
        STATUS         current
        DESCRIPTION    "."
        ::= { tnOpticalPortInfoGroups 163 }

    tnul43scupPortInfoScalarsGroup OBJECT-GROUP
        OBJECTS {
            tnul43scupPortInfoAttributeTotal
        }
        STATUS         current
        DESCRIPTION    "."
        ::= { tnOpticalPortInfoGroups 164 }

    tnul43scupPortInfoGroup OBJECT-GROUP
        OBJECTS {
            tnul43scupPortInfoFunction
        }
        STATUS         current
        DESCRIPTION    "."
        ::= { tnOpticalPortInfoGroups 165 }

    tnul11qcupPortInfoScalarsGroup OBJECT-GROUP
        OBJECTS {
            tnul11qcupPortInfoAttributeTotal
        }
        STATUS         current
        DESCRIPTION    "."
        ::= { tnOpticalPortInfoGroups 166 }

    tnul11qcupPortInfoGroup OBJECT-GROUP
        OBJECTS {
            tnul11qcupPortInfoFunction
        }
        STATUS         current
        DESCRIPTION    "."
        ::= { tnOpticalPortInfoGroups 167 }

    tn11qpen4PortInfoScalarsGroup OBJECT-GROUP
        OBJECTS {
            tn11qpen4PortInfoAttributeTotal
        }
        STATUS         current
        DESCRIPTION    "."
        ::= { tnOpticalPortInfoGroups 168 }

    tn11qpen4PortInfoGroup OBJECT-GROUP
        OBJECTS {
            tn11qpen4PortInfoFunction,
            tn11qpen4PortInfoEncryptionCurrentKeyInfo,
            tn11qpen4PortInfoEncryptionNextKeyInfo
        }
        STATUS         current
        DESCRIPTION    "."
        ::= { tnOpticalPortInfoGroups 169 }

    tn43scx4ePortInfoScalarsGroup OBJECT-GROUP
        OBJECTS {
            tn43scx4ePortInfoAttributeTotal
        }
        STATUS         current
        DESCRIPTION    "."
        ::= { tnOpticalPortInfoGroups 170 }

    tn43scx4ePortInfoGroup OBJECT-GROUP
        OBJECTS {
            tn43scx4ePortInfoFunction
        }
        STATUS         current
        DESCRIPTION    "."
        ::= { tnOpticalPortInfoGroups 171 }

    tnWssAttenPortInfoScalarsGroup OBJECT-GROUP
        OBJECTS {
            tnWssAttenPortInfoAttributeTotal
        }
        STATUS         current
        DESCRIPTION    "."
        ::= { tnOpticalPortInfoGroups 172 }

    tnWssAttenPortInfoGroup OBJECT-GROUP
        OBJECTS {
            tnWssAttenPortInfoWssCurrentRelativeAtten,
            tnWssAttenPortInfoApplicability
        }
        STATUS         current
        DESCRIPTION    "."
        ::= { tnOpticalPortInfoGroups 173 }

    tn43scge1PortInfoScalarsGroup OBJECT-GROUP
        OBJECTS {
            tn43scge1PortInfoAttributeTotal
        }
        STATUS         current
        DESCRIPTION    "."
        ::= { tnOpticalPortInfoGroups 174 }

    tn43scge1PortInfoGroup OBJECT-GROUP
        OBJECTS {
            tn43scge1PortInfoFunction
        }
        STATUS         current
        DESCRIPTION    "."
        ::= { tnOpticalPortInfoGroups 175 }

    tn11qpe24PortInfoScalarsGroup OBJECT-GROUP
        OBJECTS {
            tn11qpe24PortInfoAttributeTotal
        }
        STATUS         current
        DESCRIPTION    "."
        ::= { tnOpticalPortInfoGroups 176 }

    tn11qpe24PortInfoGroup OBJECT-GROUP
        OBJECTS {
            tn11qpe24PortInfoFunction
        }
        STATUS         current
        DESCRIPTION    "."
        ::= { tnOpticalPortInfoGroups 177 }

    tn11star1aPortInfoScalarsGroup OBJECT-GROUP
        OBJECTS {
            tn11star1aPortInfoAttributeTotal
        }
        STATUS         current
        DESCRIPTION    "."
        ::= { tnOpticalPortInfoGroups 178 }

    tn11star1aPortInfoGroup OBJECT-GROUP
        OBJECTS {
            tn11star1aPortInfoFunction
        }
        STATUS         current
        DESCRIPTION    "."
        ::= { tnOpticalPortInfoGroups 179 }

    tnMvac8bPortInfoScalarsGroup OBJECT-GROUP
        OBJECTS {
            tnMvac8bPortInfoAttributeTotal
        }
        STATUS         current
        DESCRIPTION    "."
        ::= { tnOpticalPortInfoGroups 180 }

    tnMvac8bPortInfoGroup OBJECT-GROUP
        OBJECTS {
            tnMvac8bPortInfoFunction
        }
        STATUS         current
        DESCRIPTION    "."
        ::= { tnOpticalPortInfoGroups 181 }

    tnWr8c88afPortInfoScalarsGroup OBJECT-GROUP
        OBJECTS {
            tnWr8c88afPortInfoAttributeTotal
        }
        STATUS         current
        DESCRIPTION    "."
        ::= { tnOpticalPortInfoGroups 182 }

    tnWr8c88afPortInfoGroup OBJECT-GROUP
        OBJECTS {
            tnWr8c88afPortInfoFunction
        }
        STATUS         current
        DESCRIPTION    "."
        ::= { tnOpticalPortInfoGroups 183 }

    tncl10an10gPortInfoScalarsGroup OBJECT-GROUP
        OBJECTS {
            tncl10an10gPortInfoAttributeTotal
        }
        STATUS         current
        DESCRIPTION    "."
        ::= { tnOpticalPortInfoGroups 184 }

    tncl10an10gPortInfoGroup OBJECT-GROUP
        OBJECTS {
            tncl10an10gPortInfoFunction
        }
        STATUS         current
        DESCRIPTION    "."
        ::= { tnOpticalPortInfoGroups 185 }

    tncl24anmPortInfoScalarsGroup OBJECT-GROUP
        OBJECTS {
            tncl24anmPortInfoAttributeTotal
        }
        STATUS         current
        DESCRIPTION    "."
        ::= { tnOpticalPortInfoGroups 186 }

    tncl24anmPortInfoGroup OBJECT-GROUP
        OBJECTS {
            tncl24anmPortInfoFunction
        }
        STATUS         current
        DESCRIPTION    "."
        ::= { tnOpticalPortInfoGroups 187 }

    tnOpsbPortInfoScalarsGroup OBJECT-GROUP
        OBJECTS {
            tnOpsbPortInfoAttributeTotal
        }
        STATUS         current
        DESCRIPTION    "."
        ::= { tnOpticalPortInfoGroups 188 }

    tnOpsbPortInfoGroup OBJECT-GROUP
        OBJECTS {
            tnOpsbPortInfoFunction
        }
        STATUS         current
        DESCRIPTION    "."
        ::= { tnOpticalPortInfoGroups 189 }

    tnOpsPortInfoScalarsGroup OBJECT-GROUP
        OBJECTS {
            tnOpsPortInfoAttributeTotal
        }
        STATUS         current
        DESCRIPTION    "."
        ::= { tnOpticalPortInfoGroups 190 }

    tnOpsPortInfoGroup OBJECT-GROUP
        OBJECTS {
            tnOpsPortInfoReceivedPower,
            tnOpsPortInfoPresentTransmitAttenuation,
            tnOpsPortInfoChannelMeasuredPsd,
            tnOpsPortInfoChanMeasuredPower,
            tnOpsPortInfoExpectedInputPowerDev
        }
        STATUS         current
        DESCRIPTION    "."
        ::= { tnOpticalPortInfoGroups 191 }

    tn11dpe12aPortInfoScalarsGroup OBJECT-GROUP
        OBJECTS {
            tn11dpe12aPortInfoAttributeTotal
        }
        STATUS         current
        DESCRIPTION    "."
        ::= { tnOpticalPortInfoGroups 192 }

    tn11dpe12aPortInfoGroup OBJECT-GROUP
        OBJECTS {
            tn11dpe12aPortInfoFunction,
            tn11dpe12aPortInfoTotalVTS,
            tn11dpe12aPortInfoIngAvailableBandwidth,
            tn11dpe12aPortInfoEgrAvailableBandwidth
        }
        STATUS         current
        DESCRIPTION    "."
        ::= { tnOpticalPortInfoGroups 193 }

    tnul130scupPortInfoScalarsGroup OBJECT-GROUP
        OBJECTS {
            tnul130scupPortInfoAttributeTotal
        }
        STATUS         current
        DESCRIPTION    "."
        ::= { tnOpticalPortInfoGroups 194 }

    tnul130scupPortInfoGroup OBJECT-GROUP
        OBJECTS {
            tnul130scupPortInfoFunction
        }
        STATUS         current
        DESCRIPTION    "."
        ::= { tnOpticalPortInfoGroups 195 }

    tn130scx10PortInfoScalarsGroup OBJECT-GROUP
        OBJECTS {
            tn130scx10PortInfoAttributeTotal
        }
        STATUS         current
        DESCRIPTION    "."
        ::= { tnOpticalPortInfoGroups 196 }

    tn130scx10PortInfoGroup OBJECT-GROUP
        OBJECTS {
            tn130scx10PortInfoFunction
        }
        STATUS         current
        DESCRIPTION    "."
        ::= { tnOpticalPortInfoGroups 197 }

    tnA2p2125PortInfoScalarsGroup OBJECT-GROUP
        OBJECTS {
            tnA2p2125PortInfoAttributeTotal
        }
        STATUS         current
        DESCRIPTION    "."
        ::= { tnOpticalPortInfoGroups 198 }

    tnA2p2125PortInfoGroup OBJECT-GROUP
        OBJECTS {
            tnA2p2125PortInfoFunction
        }
        STATUS         current
        DESCRIPTION    "."
        ::= { tnOpticalPortInfoGroups 199 }

    tn4qpa8PortInfoScalarsGroup OBJECT-GROUP
        OBJECTS {
            tn4qpa8PortInfoAttributeTotal
        }
        STATUS         current
        DESCRIPTION    "."
        ::= { tnOpticalPortInfoGroups 200 }

    tn4qpa8PortInfoGroup OBJECT-GROUP
        OBJECTS {
            tn4qpa8PortInfoFunction
        }
        STATUS         current
        DESCRIPTION    "."
        ::= { tnOpticalPortInfoGroups 201 }

    tnOt112pdm11PortInfoScalarsGroup OBJECT-GROUP
        OBJECTS {
            tnOt112pdm11PortInfoAttributeTotal
        }
        STATUS         current
        DESCRIPTION    "."
        ::= { tnOpticalPortInfoGroups 202 }

    tnOt112pdm11PortInfoGroup OBJECT-GROUP
        OBJECTS {
            tnOt112pdm11PortInfoFunction
        }
        STATUS         current
        DESCRIPTION    "."
        ::= { tnOpticalPortInfoGroups 203 }

    tnWtocmaPortInfoScalarsGroup OBJECT-GROUP
        OBJECTS {
            tnWtocmaPortInfoAttributeTotal
        }
        STATUS         current
        DESCRIPTION    "."
        ::= { tnOpticalPortInfoGroups 204 }

    tnWtocmaPortInfoGroup OBJECT-GROUP
        OBJECTS {
            tnWtocmaPortInfoFunction,
            tnWtocmaPortInfoPower,
            tnWtocmaPortInfoPowerMonitoredPort
        }
        STATUS         current
        DESCRIPTION    "."
        ::= { tnOpticalPortInfoGroups 205 }

    tnPtpctlPortInfoScalarsGroup OBJECT-GROUP
        OBJECTS {
            tnPtpctlPortInfoAttributeTotal
        }
        STATUS         current
        DESCRIPTION    "."
        ::= { tnOpticalPortInfoGroups 206 }

    tnPtpctlPortInfoGroup OBJECT-GROUP
        OBJECTS {
            tnPtpctlPortInfoFunction
        }
        STATUS         current
        DESCRIPTION    "."
        ::= { tnOpticalPortInfoGroups 207 }

    tnPtpioPortInfoScalarsGroup OBJECT-GROUP
        OBJECTS {
            tnPtpioPortInfoAttributeTotal
        }
        STATUS         current
        DESCRIPTION    "."
        ::= { tnOpticalPortInfoGroups 208 }

    tnPtpioPortInfoGroup OBJECT-GROUP
        OBJECTS {
            tnPtpioPortInfoFunction
        }
        STATUS         current
        DESCRIPTION    "."
        ::= { tnOpticalPortInfoGroups 209 }

    tnIo24et1gbPortInfoScalarsGroup OBJECT-GROUP
        OBJECTS {
            tnIo24et1gbPortInfoAttributeTotal
        }
        STATUS         current
        DESCRIPTION    "."
        ::= { tnOpticalPortInfoGroups 210 }

    tnIo24et1gbPortInfoGroup OBJECT-GROUP
        OBJECTS {
            tnIo24et1gbPortInfoFunction
        }
        STATUS         current
        DESCRIPTION    "."
        ::= { tnOpticalPortInfoGroups 211 }

    tnIo4an10gPortInfoScalarsGroup OBJECT-GROUP
        OBJECTS {
            tnIo4an10gPortInfoAttributeTotal
        }
        STATUS         current
        DESCRIPTION    "."
        ::= { tnOpticalPortInfoGroups 212 }

    tnIo4an10gPortInfoGroup OBJECT-GROUP
        OBJECTS {
            tnIo4an10gPortInfoFunction
        }
        STATUS         current
        DESCRIPTION    "."
        ::= { tnOpticalPortInfoGroups 213 }

    tnIo8et1gbPortInfoScalarsGroup OBJECT-GROUP
        OBJECTS {
            tnIo8et1gbPortInfoAttributeTotal
        }
        STATUS         current
        DESCRIPTION    "."
        ::= { tnOpticalPortInfoGroups 214 }

    tnIo8et1gbPortInfoGroup OBJECT-GROUP
        OBJECTS {
            tnIo8et1gbPortInfoFunction
        }
        STATUS         current
        DESCRIPTION    "."
        ::= { tnOpticalPortInfoGroups 215 }

    tnIo10et10gPortInfoScalarsGroup OBJECT-GROUP
        OBJECTS {
            tnIo10et10gPortInfoAttributeTotal
        }
        STATUS         current
        DESCRIPTION    "."
        ::= { tnOpticalPortInfoGroups 216 }

    tnIo10et10gPortInfoGroup OBJECT-GROUP
        OBJECTS {
            tnIo10et10gPortInfoFunction
        }
        STATUS         current
        DESCRIPTION    "."
        ::= { tnOpticalPortInfoGroups 217 }

    tnUl11qcupcPortInfoScalarsGroup OBJECT-GROUP
        OBJECTS {
            tnUl11qcupcPortInfoAttributeTotal
        }
        STATUS         current
        DESCRIPTION    "."
        ::= { tnOpticalPortInfoGroups 218 }

    tnUl11qcupcPortInfoGroup OBJECT-GROUP
        OBJECTS {
            tnUl11qcupcPortInfoFunction
        }
        STATUS         current
        DESCRIPTION    "."
        ::= { tnOpticalPortInfoGroups 219 }

    tnOt520scx4PortInfoScalarsGroup OBJECT-GROUP
        OBJECTS {
            tnOt520scx4PortInfoAttributeTotal
        }
        STATUS         current
        DESCRIPTION    "."
        ::= { tnOpticalPortInfoGroups 220 }

    tnOt520scx4PortInfoGroup OBJECT-GROUP
        OBJECTS {
            tnOt520scx4PortInfoFunction
        }
        STATUS         current
        DESCRIPTION    "."
        ::= { tnOpticalPortInfoGroups 221 }

    tnSkewInfoGroup OBJECT-GROUP
        OBJECTS {
            tnSkewInfoString
        }
        STATUS         current
        DESCRIPTION    "."
        ::= { tnOpticalPortInfoGroups 222 }

    tnPowerFilterPortInfoScalarsGroup OBJECT-GROUP
        OBJECTS {
            tnPowerFilterPortInfoAttributeTotal
        }
        STATUS         current
        DESCRIPTION    "."
        ::= { tnOpticalPortInfoGroups 223 }

    tnPowerFilterPortInfoGroup OBJECT-GROUP
        OBJECTS {
            tnPowerFilterPortInfoFunction
        }
        STATUS         current
        DESCRIPTION    "."
        ::= { tnOpticalPortInfoGroups 224 }

    tn11ope8PortInfoScalarsGroup OBJECT-GROUP
        OBJECTS {
            tn11ope8PortInfoAttributeTotal
        }
        STATUS         current
        DESCRIPTION    "."
        ::= { tnOpticalPortInfoGroups 225 }

    tn11ope8PortInfoGroup OBJECT-GROUP
        OBJECTS {
            tn11ope8PortInfoFunction
        }
        STATUS         current
        DESCRIPTION    "."
        ::= { tnOpticalPortInfoGroups 226 }

    tn11qce12xPortInfoScalarsGroup OBJECT-GROUP
        OBJECTS {
            tn11qce12xPortInfoAttributeTotal
        }
        STATUS         current
        DESCRIPTION    "."
        ::= { tnOpticalPortInfoGroups 227 }

    tn11qce12xPortInfoGroup OBJECT-GROUP
        OBJECTS {
            tn11qce12xPortInfoFunction
        }
        STATUS         current
        DESCRIPTION    "."
        ::= { tnOpticalPortInfoGroups 228 }

    tnAm2625aPortInfoScalarsGroup OBJECT-GROUP
        OBJECTS {
            tnAm2625aPortInfoAttributeTotal
        }
        STATUS         current
        DESCRIPTION    "."
        ::= { tnOpticalPortInfoGroups 229 }

    tnAm2625aPortInfoGroup OBJECT-GROUP
        OBJECTS {
            tnAm2625aPortInfoFunction
        }
        STATUS         current
        DESCRIPTION    "."
        ::= { tnOpticalPortInfoGroups 230 }

    tnAm2032aPortInfoScalarsGroup OBJECT-GROUP
        OBJECTS {
            tnAm2032aPortInfoAttributeTotal
        }
        STATUS         current
        DESCRIPTION    "."
        ::= { tnOpticalPortInfoGroups 231 }

    tnAm2032aPortInfoGroup OBJECT-GROUP
        OBJECTS {
            tnAm2032aPortInfoFunction
        }
        STATUS         current
        DESCRIPTION    "."
        ::= { tnOpticalPortInfoGroups 232 }

    tnOt260scx2PortInfoScalarsGroup OBJECT-GROUP
        OBJECTS {
            tnOt260scx2PortInfoAttributeTotal
        }
        STATUS         current
        DESCRIPTION    "."
        ::= { tnOpticalPortInfoGroups 233 }

    tnOt260scx2PortInfoGroup OBJECT-GROUP
        OBJECTS {
            tnOt260scx2PortInfoFunction
        }
        STATUS         current
        DESCRIPTION    "."
        ::= { tnOpticalPortInfoGroups 234 }

    tnOt130snx10PortInfoScalarsGroup OBJECT-GROUP
        OBJECTS {
            tnOt130snx10PortInfoAttributeTotal
        }
        STATUS         current
        DESCRIPTION    "."
        ::= { tnOpticalPortInfoGroups 235 }

    tnOt130snx10PortInfoGroup OBJECT-GROUP
        OBJECTS {
            tnOt130snx10PortInfoFunction
        }
        STATUS         current
        DESCRIPTION    "."
        ::= { tnOpticalPortInfoGroups 236 }

    tnIo24anmbPortInfoScalarsGroup OBJECT-GROUP
        OBJECTS {
            tnIo24anmbPortInfoAttributeTotal
        }
        STATUS         current
        DESCRIPTION    "."
        ::= { tnOpticalPortInfoGroups 237 }

    tnIo24anmbPortInfoGroup OBJECT-GROUP
        OBJECTS {
            tnIo24anmbPortInfoFunction
        }
        STATUS         current
        DESCRIPTION    "."
        ::= { tnOpticalPortInfoGroups 238 }

    tnOt11dpm8PortInfoScalarsGroup OBJECT-GROUP
        OBJECTS {
            tnOt11dpm8PortInfoAttributeTotal
        }
        STATUS         current
        DESCRIPTION    "."
        ::= { tnOpticalPortInfoGroups 239 }

    tnOt11dpm8PortInfoGroup OBJECT-GROUP
        OBJECTS {
            tnOt11dpm8PortInfoFunction
        }
        STATUS         current
        DESCRIPTION    "."
        ::= { tnOpticalPortInfoGroups 240 }

    tnOt11dpm4mPortInfoScalarsGroup OBJECT-GROUP
        OBJECTS {
            tnOt11dpm4mPortInfoAttributeTotal
        }
        STATUS         current
        DESCRIPTION    "."
        ::= { tnOpticalPortInfoGroups 241 }

    tnOt11dpm4mPortInfoGroup OBJECT-GROUP
        OBJECTS {
            tnOt11dpm4mPortInfoFunction
        }
        STATUS         current
        DESCRIPTION    "."
        ::= { tnOpticalPortInfoGroups 242 }

    tnUl130scupbPortInfoScalarsGroup OBJECT-GROUP
        OBJECTS {
            tnUl130scupbPortInfoAttributeTotal
        }
        STATUS         current
        DESCRIPTION    "."
        ::= { tnOpticalPortInfoGroups 243 }

    tnUl130scupbPortInfoGroup OBJECT-GROUP
        OBJECTS {
            tnUl130scupbPortInfoFunction
        }
        STATUS         current
        DESCRIPTION    "."
        ::= { tnOpticalPortInfoGroups 244 }

    tnOt112sdx11PortInfoScalarsGroup OBJECT-GROUP
        OBJECTS {
            tnOt112sdx11PortInfoAttributeTotal
        }
        STATUS         current
        DESCRIPTION    "."
        ::= { tnOpticalPortInfoGroups 245 }

    tnOt112sdx11PortInfoGroup OBJECT-GROUP
        OBJECTS {
            tnOt112sdx11PortInfoFunction,
            tnOt112sdx11PortInfoAggrRate
        }
        STATUS         current
        DESCRIPTION    "."
        ::= { tnOpticalPortInfoGroups 246 }

    tnAa2donwPortInfoScalarsGroup OBJECT-GROUP
        OBJECTS {
            tnAa2donwPortInfoAttributeTotal
        }
        STATUS         current
        DESCRIPTION    "."
        ::= { tnOpticalPortInfoGroups 247 }

    tnAa2donwPortInfoGroup OBJECT-GROUP
        OBJECTS {
            tnAa2donwPortInfoFunction
        }
        STATUS         current
        DESCRIPTION    "."
        ::= { tnOpticalPortInfoGroups 248 }

    tnOt130sca1PortInfoScalarsGroup OBJECT-GROUP
        OBJECTS {
            tnOt130sca1PortInfoAttributeTotal
        }
        STATUS         current
        DESCRIPTION    "."
        ::= { tnOpticalPortInfoGroups 249 }

    tnOt130sca1PortInfoGroup OBJECT-GROUP
        OBJECTS {
            tnOt130sca1PortInfoFunction
        }
        STATUS         current
        DESCRIPTION    "."
        ::= { tnOpticalPortInfoGroups 250 }

    tnIo10an10gbPortInfoScalarsGroup OBJECT-GROUP
        OBJECTS {
            tnIo10an10gbPortInfoAttributeTotal
        }
        STATUS         current
        DESCRIPTION    "."
        ::= { tnOpticalPortInfoGroups 251 }

    tnIo10an10gbPortInfoGroup OBJECT-GROUP
        OBJECTS {
            tnIo10an10gbPortInfoFunction
        }
        STATUS         current
        DESCRIPTION    "."
        ::= { tnOpticalPortInfoGroups 252 }

    tnIo10et10gbPortInfoScalarsGroup OBJECT-GROUP
        OBJECTS {
            tnIo10et10gbPortInfoAttributeTotal
        }
        STATUS         current
        DESCRIPTION    "."
        ::= { tnOpticalPortInfoGroups 253 }

    tnIo10et10gbPortInfoGroup OBJECT-GROUP
        OBJECTS {
            tnIo10et10gbPortInfoFunction
        }
        STATUS         current
        DESCRIPTION    "."
        ::= { tnOpticalPortInfoGroups 254 }

    tnWr20tfPortInfoScalarsGroup OBJECT-GROUP
        OBJECTS {
            tnWr20tfPortInfoAttributeTotal
        }
        STATUS         current
        DESCRIPTION    "."
        ::= { tnOpticalPortInfoGroups 255 }

    tnWr20tfPortInfoGroup OBJECT-GROUP
        OBJECTS {
            tnWr20tfPortInfoFunction
        }
        STATUS         current
        DESCRIPTION    "."
        ::= { tnOpticalPortInfoGroups 256 }

    tnWssPortInfoScalarsGroup OBJECT-GROUP
        OBJECTS {
            tnWssPortInfoAttributeTotal
        }
        STATUS         current
        DESCRIPTION    "."
        ::= { tnOpticalPortInfoGroups 257 }

    tnWssPortInfoGroup OBJECT-GROUP
        OBJECTS {
            tnWssPortInfoRelativeAttenuationMinIn,
            tnWssPortInfoRelativeAttenuationMinOut,
            tnWssPortInfoRelativeAverageAttenuationIn,
            tnWssPortInfoRelativeAverageAttenuationOut,
            tnWssPortInfoLossFromInToCommon,
            tnWssPortInfoCurrentLossFromInToCommon
        }
        STATUS         current
        DESCRIPTION    "."
        ::= { tnOpticalPortInfoGroups 258 }

    tnWtocmfPortInfoScalarsGroup OBJECT-GROUP
        OBJECTS {
            tnWtocmfPortInfoAttributeTotal
        }
        STATUS         current
        DESCRIPTION    "."
        ::= { tnOpticalPortInfoGroups 259 }

    tnWtocmfPortInfoGroup OBJECT-GROUP
        OBJECTS {
            tnWtocmfPortInfoFunction
        }
        STATUS         current
        DESCRIPTION    "."
        ::= { tnOpticalPortInfoGroups 260 }

    tnAswgPortInfoScalarsGroup OBJECT-GROUP
        OBJECTS {
            tnAswgPortInfoAttributeTotal
        }
        STATUS         current
        DESCRIPTION    "."
        ::= { tnOpticalPortInfoGroups 261 }

    tnAswgPortInfoGroup OBJECT-GROUP
        OBJECTS {
            tnAswgPortInfoFunction
        }
        STATUS         current
        DESCRIPTION    "."
        ::= { tnOpticalPortInfoGroups 262 }

    tnA4pswgPortInfoScalarsGroup OBJECT-GROUP
        OBJECTS {
            tnA4pswgPortInfoAttributeTotal
        }
        STATUS         current
        DESCRIPTION    "."
        ::= { tnOpticalPortInfoGroups 263 }

    tnA4pswgPortInfoGroup OBJECT-GROUP
        OBJECTS {
            tnA4pswgPortInfoFunction
        }
        STATUS         current
        DESCRIPTION    "."
        ::= { tnOpticalPortInfoGroups 264 }

    tnOtdrPortInfoScalarsGroup OBJECT-GROUP
        OBJECTS {
            tnOtdrPortInfoAttributeTotal
        }
        STATUS         current
        DESCRIPTION    "."
        ::= { tnOpticalPortInfoGroups 265 }

    tnOtdrPortInfoGroup OBJECT-GROUP
        OBJECTS {
            tnOtdrPortInfoFunction
        }
        STATUS         current
        DESCRIPTION    "."
        ::= { tnOpticalPortInfoGroups 266 }

    tnWr20tfmPortInfoScalarsGroup OBJECT-GROUP
        OBJECTS {
            tnWr20tfmPortInfoAttributeTotal
        }
        STATUS         current
        DESCRIPTION    "."
        ::= { tnOpticalPortInfoGroups 267 }

    tnWr20tfmPortInfoGroup OBJECT-GROUP
        OBJECTS {
            tnWr20tfmPortInfoFunction,
            tnWr20tfmPortInfoTestingActive
        }
        STATUS         current
        DESCRIPTION    "."
        ::= { tnOpticalPortInfoGroups 268 }

    tnAar8aPortInfoScalarsGroup OBJECT-GROUP
        OBJECTS {
            tnAar8aPortInfoAttributeTotal
        }
        STATUS         current
        DESCRIPTION    "."
        ::= { tnOpticalPortInfoGroups 269 }

    tnAar8aPortInfoGroup OBJECT-GROUP
        OBJECTS {
            tnAar8aPortInfoFunction
        }
        STATUS         current
        DESCRIPTION    "."
        ::= { tnOpticalPortInfoGroups 270 }

    tnMcs8x16PortInfoScalarsGroup OBJECT-GROUP
        OBJECTS {
            tnMcs8x16PortInfoAttributeTotal
        }
        STATUS         current
        DESCRIPTION    "."
        ::= { tnOpticalPortInfoGroups 271 }

    tnMcs8x16PortInfoGroup OBJECT-GROUP
        OBJECTS {
            tnMcs8x16PortInfoFunction,
            tnMcs8x16PortInfoAddInsertionLossToSig1,
            tnMcs8x16PortInfoAddInsertionLossToSig2,
            tnMcs8x16PortInfoAddInsertionLossToSig3,
            tnMcs8x16PortInfoAddInsertionLossToSig4,
            tnMcs8x16PortInfoAddInsertionLossToSig5,
            tnMcs8x16PortInfoAddInsertionLossToSig6,
            tnMcs8x16PortInfoAddInsertionLossToSig7,
            tnMcs8x16PortInfoAddInsertionLossToSig8,
            tnMcs8x16PortInfoDropInsertionLossFromSig1,
            tnMcs8x16PortInfoDropInsertionLossFromSig2,
            tnMcs8x16PortInfoDropInsertionLossFromSig3,
            tnMcs8x16PortInfoDropInsertionLossFromSig4,
            tnMcs8x16PortInfoDropInsertionLossFromSig5,
            tnMcs8x16PortInfoDropInsertionLossFromSig6,
            tnMcs8x16PortInfoDropInsertionLossFromSig7,
            tnMcs8x16PortInfoDropInsertionLossFromSig8
        }
        STATUS         current
        DESCRIPTION    "."
        ::= { tnOpticalPortInfoGroups 272 }

    tnMsh8fsmPortInfoScalarsGroup OBJECT-GROUP
        OBJECTS {
            tnMsh8fsmPortInfoAttributeTotal
        }
        STATUS         current
        DESCRIPTION    "."
        ::= { tnOpticalPortInfoGroups 273 }

    tnMsh8fsmPortInfoGroup OBJECT-GROUP
        OBJECTS {
            tnMsh8fsmPortInfoFunction
        }
        STATUS         current
        DESCRIPTION    "."
        ::= { tnOpticalPortInfoGroups 274 }

    tnMcsPortInfoScalarsGroup OBJECT-GROUP
        OBJECTS {
            tnMcsPortInfoAttributeTotal
        }
        STATUS         current
        DESCRIPTION    "."
        ::= { tnOpticalPortInfoGroups 275 }

    tnMcsPortInfoGroup OBJECT-GROUP
        OBJECTS {
            tnMcsPortInfoCurrentAddDisposition,
            tnMcsPortInfoCurrentDropDisposition,
            tnMcsPortInfoTestingActive,
            tnMcsPortInfoAddInputPower
        }
        STATUS         current
        DESCRIPTION    "."
        ::= { tnOpticalPortInfoGroups 276 }

    tnMcsPortChannelInfoScalarsGroup OBJECT-GROUP
        OBJECTS {
            tnMcsPortChannelInfoAttributeTotal
        }
        STATUS         current
        DESCRIPTION    "."
        ::= { tnOpticalPortInfoGroups 277 }

    tnMcsPortChannelInfoGroup OBJECT-GROUP
        OBJECTS {
            tnMcsPortChannelInfoCurrentRoutingAdd,
            tnMcsPortChannelInfoCurrentRoutingDrop
        }
        STATUS         current
        DESCRIPTION    "."
        ::= { tnOpticalPortInfoGroups 278 }

    tnAarPortInfoScalarsGroup OBJECT-GROUP
        OBJECTS {
            tnAarPortInfoAttributeTotal
        }
        STATUS         current
        DESCRIPTION    "."
        ::= { tnOpticalPortInfoGroups 279 }

    tnAarPortInfoGroup OBJECT-GROUP
        OBJECTS {
            tnAarPortInfoTotalPowerIn,
            tnAarPortInfoLosThreshold,
            tnAarPortInfoLosThresholdTolerance,
            tnAarPortInfoLosMode,
            tnAarPortInfoTotalPowerOut,
            tnAarPortInfoSignalPowerOut,
            tnAarPortInfoOAPumpBiasCurrent,
            tnAarPortInfoOAPumpTemperature,
            tnAarPortInfoTestingActive,
            tnAarPortInfoOAPump1BiasCurrent,
            tnAarPortInfoOAPump2BiasCurrent,
            tnAarPortInfoOAPump1Temperature,
            tnAarPortInfoOAPump2Temperature
        }
        STATUS         current
        DESCRIPTION    "."
        ::= { tnOpticalPortInfoGroups 280 }

    tnWr20tfmPortChannelInfoScalarsGroup OBJECT-GROUP
        OBJECTS {
            tnWr20tfmPortChannelInfoAttributeTotal
        }
        STATUS         current
        DESCRIPTION    "."
        ::= { tnOpticalPortInfoGroups 281 }

    tnWr20tfmPortChannelInfoGroup OBJECT-GROUP
        OBJECTS {
            tnWr20tfmPortChannelInfoDropDisposition,
            tnWr20tfmPortChannelInfoAddDisposition
        }
        STATUS         current
        DESCRIPTION    "."
        ::= { tnOpticalPortInfoGroups 282 }

    tnMpoPortInfoScalarsGroup OBJECT-GROUP
        OBJECTS {
            tnMpoPortInfoAttributeTotal
        }
        STATUS         current
        DESCRIPTION    "."
        ::= { tnOpticalPortInfoGroups 283 }

    tnMpoPortInfoGroup OBJECT-GROUP
        OBJECTS {
            tnMpoPortInfoSignalDirection
        }
        STATUS         current
        DESCRIPTION    "."
        ::= { tnOpticalPortInfoGroups 284 }

    tnMpoPortMultiPositionScalarsGroup OBJECT-GROUP
        OBJECTS {
            tnMpoPortMultiPositionInfoAttributeTotal
        }
        STATUS         current
        DESCRIPTION    "."
        ::= { tnOpticalPortInfoGroups 285 }

    tnMpoPortMultiPositionInfoGroup OBJECT-GROUP
        OBJECTS {
            tnMpoPortMultiPositionInfoUnderlyingPortUsage,
            tnMpoPortMultiPositionInfoUnderlyingPortIfIndex,
            tnMpoPortMultiPositionInfoUnderlyingPortDirection
        }
        STATUS         current
        DESCRIPTION    "."
        ::= { tnOpticalPortInfoGroups 286 }

    tnIo4an100gPortInfoScalarsGroup OBJECT-GROUP
        OBJECTS {
            tnIo4an100gPortInfoAttributeTotal
        }
        STATUS         current
        DESCRIPTION    "."
        ::= { tnOpticalPortInfoGroups 287 }

    tnIo4an100gPortInfoGroup OBJECT-GROUP
        OBJECTS {
            tnIo4an100gPortInfoFunction
        }
        STATUS         current
        DESCRIPTION    "."
        ::= { tnOpticalPortInfoGroups 288 }

    tnIo30an10gPortInfoScalarsGroup OBJECT-GROUP
        OBJECTS {
            tnIo30an10gPortInfoAttributeTotal
        }
        STATUS         current
        DESCRIPTION    "."
        ::= { tnOpticalPortInfoGroups 289 }

    tnIo30an10gPortInfoGroup OBJECT-GROUP
        OBJECTS {
            tnIo30an10gPortInfoFunction
        }
        STATUS         current
        DESCRIPTION    "."
        ::= { tnOpticalPortInfoGroups 290 }

    tnIo30an300PortInfoScalarsGroup OBJECT-GROUP
        OBJECTS {
            tnIo30an300PortInfoAttributeTotal
        }
        STATUS         current
        DESCRIPTION    "."
        ::= { tnOpticalPortInfoGroups 291 }

    tnIo30an300PortInfoGroup OBJECT-GROUP
        OBJECTS {
            tnIo30an300PortInfoFunction
        }
        STATUS         current
        DESCRIPTION    "."
        ::= { tnOpticalPortInfoGroups 292 }

    tnIo4an400PortInfoScalarsGroup OBJECT-GROUP
        OBJECTS {
            tnIo4an400PortInfoAttributeTotal
        }
        STATUS         current
        DESCRIPTION    "."
        ::= { tnOpticalPortInfoGroups 293 }

    tnIo4an400PortInfoGroup OBJECT-GROUP
        OBJECTS {
            tnIo4an400PortInfoFunction
        }
        STATUS         current
        DESCRIPTION    "."
        ::= { tnOpticalPortInfoGroups 294 }

    tn12p120PortInfoScalarsGroup OBJECT-GROUP
        OBJECTS {
            tn12p120PortInfoAttributeTotal
        }
        STATUS         current
        DESCRIPTION    "."
        ::= { tnOpticalPortInfoGroups 295 }

    tn12p120PortInfoGroup OBJECT-GROUP
        OBJECTS {
            tn12p120PortInfoFunction
        }
        STATUS         current
        DESCRIPTION    "."
        ::= { tnOpticalPortInfoGroups 296 }

    tn20p200PortInfoScalarsGroup OBJECT-GROUP
        OBJECTS {
            tn20p200PortInfoAttributeTotal
        }
        STATUS         current
        DESCRIPTION    "."
        ::= { tnOpticalPortInfoGroups 297 }

    tn20p200PortInfoGroup OBJECT-GROUP
        OBJECTS {
            tn20p200PortInfoFunction
        }
        STATUS         current
        DESCRIPTION    "."
        ::= { tnOpticalPortInfoGroups 298 }

    tn1ud200PortInfoScalarsGroup OBJECT-GROUP
        OBJECTS {
            tn1ud200PortInfoAttributeTotal
        }
        STATUS         current
        DESCRIPTION    "."
        ::= { tnOpticalPortInfoGroups 299 }

    tn1ud200PortInfoGroup OBJECT-GROUP
        OBJECTS {
            tn1ud200PortInfoFunction
        }
        STATUS         current
        DESCRIPTION    "."
        ::= { tnOpticalPortInfoGroups 300 }

    tnOt130snq10PortInfoScalarsGroup OBJECT-GROUP
        OBJECTS {
            tnOt130snq10PortInfoAttributeTotal
        }
        STATUS         current
        DESCRIPTION    "."
        ::= { tnOpticalPortInfoGroups 301 }

    tnOt130snq10PortInfoGroup OBJECT-GROUP
        OBJECTS {
            tnOt130snq10PortInfoFunction
        }
        STATUS         current
        DESCRIPTION    "."
        ::= { tnOpticalPortInfoGroups 302 }

    tnIroadmvPortInfoScalarsGroup OBJECT-GROUP
        OBJECTS {
            tnIroadmvPortInfoAttributeTotal
        }
        STATUS         current
        DESCRIPTION    "."
        ::= { tnOpticalPortInfoGroups 303 }

    tnIroadmvPortInfoGroup OBJECT-GROUP
        OBJECTS {
            tnIroadmvPortInfoFunction
        }
        STATUS         current
        DESCRIPTION    "."
        ::= { tnOpticalPortInfoGroups 304 }

    tnIroadmfPortInfoScalarsGroup OBJECT-GROUP
        OBJECTS {
            tnIroadmfPortInfoAttributeTotal
        }
        STATUS         current
        DESCRIPTION    "."
        ::= { tnOpticalPortInfoGroups 305 }

    tnIroadmfPortInfoGroup OBJECT-GROUP
        OBJECTS {
            tnIroadmfPortInfoFunction
        }
        STATUS         current
        DESCRIPTION    "."
        ::= { tnOpticalPortInfoGroups 306 }

    tnIroadmPortInfoScalarsGroup OBJECT-GROUP
        OBJECTS {
            tnIroadmPortInfoAttributeTotal
        }
        STATUS         current
        DESCRIPTION    "."
        ::= { tnOpticalPortInfoGroups 307 }

    tnIroadmPortInfoGroup OBJECT-GROUP
        OBJECTS {
            tnIroadmPortInfoIngressOaPowerIn,
            tnIroadmPortInfoIngressOaPowerOut,
            tnIroadmPortInfoEgressOaPowerIn,
            tnIroadmPortInfoEgressOaPowerOut,
            tnIroadmPortInfoIngressOaSignalPowerOut,
            tnIroadmPortInfoEgressOaSignalPowerOut,
            tnIroadmPortInfoIngressOaInputToOutputGain,
            tnIroadmPortInfoEgressOaInputToOutputGain,
            tnIroadmPortInfoEgressOaMaxFlatGain,
            tnIroadmPortInfoIngressOaMaxFlatGain,
            tnIroadmPortInfoActualTilt,
            tnIroadmPortInfoDCMInPower,
            tnIroadmPortInfoDCMOutPower,
            tnIroadmPortInfoPowerSpanRepairMargin,
            tnIroadmPortInfoEnable,
            tnIroadmPortInfoGainTilt,
            tnIroadmPortInfoActOutAtten,
            tnIroadmPortInfoOSCVoaAtten,
            tnIroadmPortInfoOSCTxPowerIn,
            tnIroadmPortInfoOSCTxPowerOut,
            tnIroadmPortInfoOSCRxPowerIn,
            tnIroadmPortInfoOSCSfpTxPowerOut,
            tnIroadmPortInfoOSCSfpRxPowerIn,
            tnIroadmPortInfoEgressOAPowerGain,
            tnIroadmPortInfoActOutAttenL,
            tnIroadmPortInfoIngressOaPowerInL,
            tnIroadmPortInfoIngressOaPowerOutL,
            tnIroadmPortInfoEgressOaPowerInL,
            tnIroadmPortInfoEgressOaPowerOutL,
            tnIroadmPortInfoIngressOaSignalPowerOutL,
            tnIroadmPortInfoEgressOaSignalPowerOutL,
            tnIroadmPortInfoIngressOaInputToOutputGainL,
            tnIroadmPortInfoEgressOaInputToOutputGainL,
            tnIroadmPortInfoActualTiltL,
            tnIroadmPortInfoGainTiltL,
            tnIroadmPortInfoEgressOAPowerGainL,
            tnIroadmPortInfoIngressOaMaxFlatGainL,
            tnIroadmPortInfoEgressOaMaxFlatGainL,
            tnIroadmPortInfoSpanLoss,
            tnIroadmPortInfoAseAmpOn,
            tnIroadmPortInfoAseAmpOnL,
            tnIroadmPortInfoAseTotalPowerOut,
            tnIroadmPortInfoAseTotalPowerOutL,
            tnIroadmPortInfoAseTargetTotalPowerOut,
            tnIroadmPortInfoAseTargetTotalPowerOutL
        }
        STATUS         current
        DESCRIPTION    "."
        ::= { tnOpticalPortInfoGroups 308 }

    tnIroadmPortChannelInfoScalarsGroup OBJECT-GROUP
        OBJECTS {
            tnIroadmPortChannelInfoAttributeTotal
        }
        STATUS         current
        DESCRIPTION    "."
        ::= { tnOpticalPortInfoGroups 309 }

    tnIroadmPortChannelInfoGroup OBJECT-GROUP
        OBJECTS {
            tnIroadmPortChannelInfoAddDisposition
        }
        STATUS         current
        DESCRIPTION    "."
        ::= { tnOpticalPortInfoGroups 310 }

    tnWssRefLdInfoScalarsGroup OBJECT-GROUP
        OBJECTS {
            tnWssRefLdInfoAttributeTotal
        }
        STATUS         current
        DESCRIPTION    "."
        ::= { tnOpticalPortInfoGroups 311 }

    tnWssRefLdInfoGroup OBJECT-GROUP
        OBJECTS {
            tnWssRefLdInfoIfIndex,
            tnWssRefLdInfoApplicability
        }
        STATUS         current
        DESCRIPTION    "."
        ::= { tnOpticalPortInfoGroups 312 }

    tnMonOcmPortInfoScalarsGroup OBJECT-GROUP
        OBJECTS {
            tnMonOcmPortInfoAttributeTotal
        }
        STATUS         current
        DESCRIPTION    "."
        ::= { tnOpticalPortInfoGroups 313 }

    tnMonOcmPortInfoGroup OBJECT-GROUP
        OBJECTS {
            tnMonOcmPortInfoFunction
        }
        STATUS         current
        DESCRIPTION    "."
        ::= { tnOpticalPortInfoGroups 314 }

    tnUl2uc400PortInfoScalarsGroup OBJECT-GROUP
        OBJECTS {
            tnUl2uc400PortInfoAttributeTotal
        }
        STATUS         current
        DESCRIPTION    "."
        ::= { tnOpticalPortInfoGroups 315 }

    tnUl2uc400PortInfoGroup OBJECT-GROUP
        OBJECTS {
            tnUl2uc400PortInfoFunction
        }
        STATUS         current
        DESCRIPTION    "."
        ::= { tnOpticalPortInfoGroups 316 }

    tnUl4uc400PortInfoScalarsGroup OBJECT-GROUP
        OBJECTS {
            tnUl4uc400PortInfoAttributeTotal
        }
        STATUS         current
        DESCRIPTION    "."
        ::= { tnOpticalPortInfoGroups 317 }

    tnUl4uc400PortInfoGroup OBJECT-GROUP
        OBJECTS {
            tnUl4uc400PortInfoFunction
        }
        STATUS         current
        DESCRIPTION    "."
        ::= { tnOpticalPortInfoGroups 318 }

    tnUl20uc200PortInfoScalarsGroup OBJECT-GROUP
        OBJECTS {
            tnUl20uc200PortInfoAttributeTotal
        }
        STATUS         current
        DESCRIPTION    "."
        ::= { tnOpticalPortInfoGroups 319 }

    tnUl20uc200PortInfoGroup OBJECT-GROUP
        OBJECTS {
            tnUl20uc200PortInfoFunction
        }
        STATUS         current
        DESCRIPTION    "."
        ::= { tnOpticalPortInfoGroups 320 }

    tnD5x500PortInfoScalarsGroup OBJECT-GROUP
        OBJECTS {
            tnD5x500PortInfoAttributeTotal
        }
        STATUS         current
        DESCRIPTION    "."
        ::= { tnOpticalPortInfoGroups 321 }

    tnD5x500PortInfoGroup OBJECT-GROUP
        OBJECTS {
            tnD5x500PortInfoFunction
        }
        STATUS         current
        DESCRIPTION    "."
        ::= { tnOpticalPortInfoGroups 322 }

    tnOtS11M100PortInfoScalarsGroup OBJECT-GROUP
        OBJECTS {
            tnOtS11M100PortInfoAttributeTotal
        }
        STATUS         current
        DESCRIPTION    "."
        ::= { tnOpticalPortInfoGroups 323 }

    tnOtS11M100PortInfoGroup OBJECT-GROUP
        OBJECTS {
            tnOtS11M100PortInfoFunction
        }
        STATUS         current
        DESCRIPTION    "."
        ::= { tnOpticalPortInfoGroups 324 }

    tnMonOtdrPortInfoScalarsGroup OBJECT-GROUP
        OBJECTS {
            tnMonOtdrPortInfoAttributeTotal
        }
        STATUS         current
        DESCRIPTION    "."
        ::= { tnOpticalPortInfoGroups 325 }

    tnMonOtdrPortInfoGroup OBJECT-GROUP
        OBJECTS {
            tnMonOtdrPortInfoFunction
        }
        STATUS         current
        DESCRIPTION    "."
        ::= { tnOpticalPortInfoGroups 326 }

    tnPSS96PowerFilterPortInfoScalarsGroup OBJECT-GROUP
        OBJECTS {
            tnPSS96PowerFilterPortInfoAttributeTotal
        }
        STATUS         current
        DESCRIPTION    "."
        ::= { tnOpticalPortInfoGroups 327 }

    tnPSS96PowerFilterPortInfoGroup OBJECT-GROUP
        OBJECTS {
            tnPSS96PowerFilterPortInfoFunction
        }
        STATUS         current
        DESCRIPTION    "."
        ::= { tnOpticalPortInfoGroups 328 }

    tn12ce120PortInfoScalarsGroup OBJECT-GROUP
        OBJECTS {
            tn12ce120PortInfoAttributeTotal
        }
        STATUS         current
        DESCRIPTION    "."
        ::= { tnOpticalPortInfoGroups 329 }

    tn12ce120PortInfoGroup OBJECT-GROUP
        OBJECTS {
            tn12ce120PortInfoFunction
        }
        STATUS         current
        DESCRIPTION    "."
        ::= { tnOpticalPortInfoGroups 330 }

    tn1ce100PortInfoScalarsGroup OBJECT-GROUP
        OBJECTS {
            tn1ce100PortInfoAttributeTotal
        }
        STATUS         current
        DESCRIPTION    "."
        ::= { tnOpticalPortInfoGroups 331 }

    tn1ce100PortInfoGroup OBJECT-GROUP
        OBJECTS {
            tn1ce100PortInfoFunction
        }
        STATUS         current
        DESCRIPTION    "."
        ::= { tnOpticalPortInfoGroups 332 }

    tnLcI1000PortInfoScalarsGroup OBJECT-GROUP
        OBJECTS {
            tnLcI1000PortInfoAttributeTotal
        }
        STATUS         current
        DESCRIPTION    "."
        ::= { tnOpticalPortInfoGroups 333 }

    tnLcI1000PortInfoGroup OBJECT-GROUP
        OBJECTS {
            tnLcI1000PortInfoFunction
        }
        STATUS         current
        DESCRIPTION    "."
        ::= { tnOpticalPortInfoGroups 334 }

    tnAwbegrPortInfoScalarsGroup OBJECT-GROUP
        OBJECTS {
            tnAwbegrPortInfoAttributeTotal
        }
        STATUS         current
        DESCRIPTION    "."
        ::= { tnOpticalPortInfoGroups 335 }

    tnAwbegrPortInfoGroup OBJECT-GROUP
        OBJECTS {
            tnAwbegrPortInfoFunction
        }
        STATUS         current
        DESCRIPTION    "."
        ::= { tnOpticalPortInfoGroups 336 }

    tnAwbingPortInfoScalarsGroup OBJECT-GROUP
        OBJECTS {
            tnAwbingPortInfoAttributeTotal
        }
        STATUS         current
        DESCRIPTION    "."
        ::= { tnOpticalPortInfoGroups 337 }

    tnAwbingPortInfoGroup OBJECT-GROUP
        OBJECTS {
            tnAwbingPortInfoFunction
        }
        STATUS         current
        DESCRIPTION    "."
        ::= { tnOpticalPortInfoGroups 338 }

    tnAwbilaPortInfoScalarsGroup OBJECT-GROUP
        OBJECTS {
            tnAwbilaPortInfoAttributeTotal
        }
        STATUS         current
        DESCRIPTION    "."
        ::= { tnOpticalPortInfoGroups 339 }

    tnAwbilaPortInfoGroup OBJECT-GROUP
        OBJECTS {
            tnAwbilaPortInfoFunction
        }
        STATUS         current
        DESCRIPTION    "."
        ::= { tnOpticalPortInfoGroups 340 }

    tnRa5pPortInfoScalarsGroup OBJECT-GROUP
        OBJECTS {
            tnRa5pPortInfoAttributeTotal
        }
        STATUS         current
        DESCRIPTION    "."
        ::= { tnOpticalPortInfoGroups 341 }

    tnRa5pPortInfoGroup OBJECT-GROUP
        OBJECTS {
            tnRa5pPortInfoFunction
        }
        STATUS         current
        DESCRIPTION    "."
        ::= { tnOpticalPortInfoGroups 342 }

    tnIroadm9mPortInfoScalarsGroup OBJECT-GROUP
        OBJECTS {
            tnIroadm9mPortInfoAttributeTotal
        }
        STATUS         current
        DESCRIPTION    "."
        ::= { tnOpticalPortInfoGroups 343 }

    tnIroadm9mPortInfoGroup OBJECT-GROUP
        OBJECTS {
            tnIroadm9mPortInfoFunction
        }
        STATUS         current
        DESCRIPTION    "."
        ::= { tnOpticalPortInfoGroups 344 }

    tnS13x100PortInfoScalarsGroup OBJECT-GROUP
        OBJECTS {
            tnS13x100PortInfoAttributeTotal
        }
        STATUS         current
        DESCRIPTION    "."
        ::= { tnOpticalPortInfoGroups 345 }

    tnS13x100PortInfoGroup OBJECT-GROUP
        OBJECTS {
            tnS13x100PortInfoFunction
        }
        STATUS         current
        DESCRIPTION    "."
        ::= { tnOpticalPortInfoGroups 346 }

    tn12ce121PortInfoScalarsGroup OBJECT-GROUP
        OBJECTS {
            tn12ce121PortInfoAttributeTotal
        }
        STATUS         current
        DESCRIPTION    "."
        ::= { tnOpticalPortInfoGroups 347 }

    tn12ce121PortInfoGroup OBJECT-GROUP
        OBJECTS {
            tn12ce121PortInfoFunction
        }
        STATUS         current
        DESCRIPTION    "."
        ::= { tnOpticalPortInfoGroups 348 }

    tnPtpioctlPortInfoScalarsGroup OBJECT-GROUP
        OBJECTS {
            tnPtpioctlPortInfoAttributeTotal
        }
        STATUS         current
        DESCRIPTION    "."
        ::= { tnOpticalPortInfoGroups 349 }

    tnPtpioctlPortInfoGroup OBJECT-GROUP
        OBJECTS {
            tnPtpioctlPortInfoFunction
        }
        STATUS         current
        DESCRIPTION    "."
        ::= { tnOpticalPortInfoGroups 350 }

    tnAa2donwbPortInfoScalarsGroup OBJECT-GROUP
        OBJECTS {
            tnAa2donwbPortInfoAttributeTotal
        }
        STATUS         current
        DESCRIPTION    "."
        ::= { tnOpticalPortInfoGroups 351 }

    tnAa2donwbPortInfoGroup OBJECT-GROUP
        OBJECTS {
            tnAa2donwbPortInfoFunction
        }
        STATUS         current
        DESCRIPTION    "."
        ::= { tnOpticalPortInfoGroups 352 }

    tnOsctaprPortInfoScalarsGroup OBJECT-GROUP
        OBJECTS {
            tnOsctaprPortInfoAttributeTotal
        }
        STATUS         current
        DESCRIPTION    "."
        ::= { tnOpticalPortInfoGroups 353 }

    tnOsctaprPortInfoGroup OBJECT-GROUP
        OBJECTS {
            tnOsctaprPortInfoFunction
        }
        STATUS         current
        DESCRIPTION    "."
        ::= { tnOpticalPortInfoGroups 354 }

    tn11qpa4bPortInfoScalarsGroup OBJECT-GROUP
        OBJECTS {
            tn11qpa4bPortInfoAttributeTotal
        }
        STATUS         current
        DESCRIPTION    "."
        ::= { tnOpticalPortInfoGroups 355 }

    tn11qpa4bPortInfoGroup OBJECT-GROUP
        OBJECTS {
            tn11qpa4bPortInfoFunction
        }
        STATUS         current
        DESCRIPTION    "."
        ::= { tnOpticalPortInfoGroups 356 }

    tn1ux100PortInfoScalarsGroup OBJECT-GROUP
        OBJECTS {
            tn1ux100PortInfoAttributeTotal
        }
        STATUS         current
        DESCRIPTION    "."
        ::= { tnOpticalPortInfoGroups 357 }

    tn1ux100PortInfoGroup OBJECT-GROUP
        OBJECTS {
            tn1ux100PortInfoFunction
        }
        STATUS         current
        DESCRIPTION    "."
        ::= { tnOpticalPortInfoGroups 358 }

    tn20ax200PortInfoScalarsGroup OBJECT-GROUP
        OBJECTS {
            tn20ax200PortInfoAttributeTotal
        }
        STATUS         current
        DESCRIPTION    "."
        ::= { tnOpticalPortInfoGroups 359 }

    tn20ax200PortInfoGroup OBJECT-GROUP
        OBJECTS {
            tn20ax200PortInfoFunction
        }
        STATUS         current
        DESCRIPTION    "."
        ::= { tnOpticalPortInfoGroups 360 }

    tn20mx80PortInfoScalarsGroup OBJECT-GROUP
        OBJECTS {
            tn20mx80PortInfoAttributeTotal
        }
        STATUS         current
        DESCRIPTION    "."
        ::= { tnOpticalPortInfoGroups 361 }

    tn20mx80PortInfoGroup OBJECT-GROUP
        OBJECTS {
            tn20mx80PortInfoFunction
        }
        STATUS         current
        DESCRIPTION    "."
        ::= { tnOpticalPortInfoGroups 362 }

    tnAar2x8aPortInfoScalarsGroup OBJECT-GROUP
        OBJECTS {
            tnAar2x8aPortInfoAttributeTotal
        }
        STATUS         current
        DESCRIPTION    "."
        ::= { tnOpticalPortInfoGroups 363 }

    tnAar2x8aPortInfoGroup OBJECT-GROUP
        OBJECTS {
            tnAar2x8aPortInfoFunction
        }
        STATUS         current
        DESCRIPTION    "."
        ::= { tnOpticalPortInfoGroups 364 }

    tnS13x100ePortInfoScalarsGroup OBJECT-GROUP
        OBJECTS {
            tnS13x100ePortInfoAttributeTotal
        }
        STATUS         current
        DESCRIPTION    "."
        ::= { tnOpticalPortInfoGroups 365 }

    tnS13x100ePortInfoGroup OBJECT-GROUP
        OBJECTS {
            tnS13x100ePortInfoFunction
        }
        STATUS         current
        DESCRIPTION    "."
        ::= { tnOpticalPortInfoGroups 366 }

    tnWtocmflPortInfoScalarsGroup OBJECT-GROUP
        OBJECTS {
            tnWtocmflPortInfoAttributeTotal
        }
        STATUS         current
        DESCRIPTION    "."
        ::= { tnOpticalPortInfoGroups 367 }

    tnWtocmflPortInfoGroup OBJECT-GROUP
        OBJECTS {
            tnWtocmflPortInfoFunction
        }
        STATUS         current
        DESCRIPTION    "."
        ::= { tnOpticalPortInfoGroups 368 }

    tnAar2x8alPortInfoScalarsGroup OBJECT-GROUP
        OBJECTS {
            tnAar2x8alPortInfoAttributeTotal
        }
        STATUS         current
        DESCRIPTION    "."
        ::= { tnOpticalPortInfoGroups 369 }

    tnAar2x8alPortInfoGroup OBJECT-GROUP
        OBJECTS {
            tnAar2x8alPortInfoFunction
        }
        STATUS         current
        DESCRIPTION    "."
        ::= { tnOpticalPortInfoGroups 370 }

    tnWr20tfmlPortInfoScalarsGroup OBJECT-GROUP
        OBJECTS {
            tnWr20tfmlPortInfoAttributeTotal
        }
        STATUS         current
        DESCRIPTION    "."
        ::= { tnOpticalPortInfoGroups 371 }

    tnWr20tfmlPortInfoGroup OBJECT-GROUP
        OBJECTS {
            tnWr20tfmlPortInfoFunction
        }
        STATUS         current
        DESCRIPTION    "."
        ::= { tnOpticalPortInfoGroups 372 }

    tnMcs8x16lPortInfoScalarsGroup OBJECT-GROUP
        OBJECTS {
            tnMcs8x16lPortInfoAttributeTotal
        }
        STATUS         current
        DESCRIPTION    "."
        ::= { tnOpticalPortInfoGroups 373 }

    tnMcs8x16lPortInfoGroup OBJECT-GROUP
        OBJECTS {
            tnMcs8x16lPortInfoFunction
        }
        STATUS         current
        DESCRIPTION    "."
        ::= { tnOpticalPortInfoGroups 374 }

    tnPSS8xPowerFilterPortInfoScalarsGroup OBJECT-GROUP
        OBJECTS {
            tnPSS8xPowerFilterPortInfoAttributeTotal
        }
        STATUS         current
        DESCRIPTION    "."
        ::= { tnOpticalPortInfoGroups 375 }

    tnPSS8xPowerFilterPortInfoGroup OBJECT-GROUP
        OBJECTS {
            tnPSS8xPowerFilterPortInfoFunction
        }
        STATUS         current
        DESCRIPTION    "."
        ::= { tnOpticalPortInfoGroups 376 }

    tnLcI2000PortInfoScalarsGroup OBJECT-GROUP
        OBJECTS {
            tnLcI2000PortInfoAttributeTotal
        }
        STATUS         current
        DESCRIPTION    "."
        ::= { tnOpticalPortInfoGroups 377 }

    tnLcI2000PortInfoGroup OBJECT-GROUP
        OBJECTS {
            tnLcI2000PortInfoFunction
        }
        STATUS         current
        DESCRIPTION    "."
        ::= { tnOpticalPortInfoGroups 378 }

    tn30se300PortInfoScalarsGroup OBJECT-GROUP
        OBJECTS {
            tn30se300PortInfoAttributeTotal
        }
        STATUS         current
        DESCRIPTION    "."
        ::= { tnOpticalPortInfoGroups 379 }

    tn30se300PortInfoGroup OBJECT-GROUP
        OBJECTS {
            tn30se300PortInfoFunction
        }
        STATUS         current
        DESCRIPTION    "."
        ::= { tnOpticalPortInfoGroups 380 }

    tn6se300PortInfoScalarsGroup OBJECT-GROUP
        OBJECTS {
            tn6se300PortInfoAttributeTotal
        }
        STATUS         current
        DESCRIPTION    "."
        ::= { tnOpticalPortInfoGroups 381 }

    tn6se300PortInfoGroup OBJECT-GROUP
        OBJECTS {
            tn6se300PortInfoFunction
        }
        STATUS         current
        DESCRIPTION    "."
        ::= { tnOpticalPortInfoGroups 382 }

    tnOtdrwbPortInfoScalarsGroup OBJECT-GROUP
        OBJECTS {
            tnOtdrwbPortInfoAttributeTotal
        }
        STATUS         current
        DESCRIPTION    "."
        ::= { tnOpticalPortInfoGroups 383 }

    tnOtdrwbPortInfoGroup OBJECT-GROUP
        OBJECTS {
            tnOtdrwbPortInfoFunction
        }
        STATUS         current
        DESCRIPTION    "."
        ::= { tnOpticalPortInfoGroups 384 }

    tn8dc30tPortInfoScalarsGroup OBJECT-GROUP
        OBJECTS {
            tn8dc30tPortInfoAttributeTotal
        }
        STATUS         current
        DESCRIPTION    "."
        ::= { tnOpticalPortInfoGroups 385 }

    tn8dc30tPortInfoGroup OBJECT-GROUP
        OBJECTS {
            tn8dc30tPortInfoFunction
        }
        STATUS         current
        DESCRIPTION    "."
        ::= { tnOpticalPortInfoGroups 386 }

    tn16dc65tPortInfoScalarsGroup OBJECT-GROUP
        OBJECTS {
            tn16dc65tPortInfoAttributeTotal
        }
        STATUS         current
        DESCRIPTION    "."
        ::= { tnOpticalPortInfoGroups 387 }

    tn16dc65tPortInfoGroup OBJECT-GROUP
        OBJECTS {
            tn16dc65tPortInfoFunction
        }
        STATUS         current
        DESCRIPTION    "."
        ::= { tnOpticalPortInfoGroups 388 }

    tnD5x500lPortInfoScalarsGroup OBJECT-GROUP
        OBJECTS {
            tnD5x500lPortInfoAttributeTotal
        }
        STATUS         current
        DESCRIPTION    "."
        ::= { tnOpticalPortInfoGroups 389 }

    tnD5x500lPortInfoGroup OBJECT-GROUP
        OBJECTS {
            tnD5x500lPortInfoFunction
        }
        STATUS         current
        DESCRIPTION    "."
        ::= { tnOpticalPortInfoGroups 390 }

    tnLcI2000lPortInfoScalarsGroup OBJECT-GROUP
        OBJECTS {
            tnLcI2000lPortInfoAttributeTotal
        }
        STATUS         current
        DESCRIPTION    "."
        ::= { tnOpticalPortInfoGroups 391 }

    tnLcI2000lPortInfoGroup OBJECT-GROUP
        OBJECTS {
            tnLcI2000lPortInfoFunction
        }
        STATUS         current
        DESCRIPTION    "."
        ::= { tnOpticalPortInfoGroups 392 }

    tnIroadm9rPortInfoScalarsGroup OBJECT-GROUP
        OBJECTS {
            tnIroadm9rPortInfoAttributeTotal
        }
        STATUS         current
        DESCRIPTION    "."
        ::= { tnOpticalPortInfoGroups 393 }

    tnIroadm9rPortInfoGroup OBJECT-GROUP
        OBJECTS {
            tnIroadm9rPortInfoFunction
        }
        STATUS         current
        DESCRIPTION    "."
        ::= { tnOpticalPortInfoGroups 394 }

    tnRa2p96PortInfoScalarsGroup OBJECT-GROUP
        OBJECTS {
            tnRa2p96PortInfoAttributeTotal
        }
        STATUS         current
        DESCRIPTION    "."
        ::= { tnOpticalPortInfoGroups 395 }

    tnRa2p96PortInfoGroup OBJECT-GROUP
        OBJECTS {
            tnRa2p96PortInfoFunction
        }
        STATUS         current
        DESCRIPTION    "."
        ::= { tnOpticalPortInfoGroups 396 }

    tnOtdrmPortInfoScalarsGroup OBJECT-GROUP
        OBJECTS {
            tnOtdrmPortInfoAttributeTotal
        }
        STATUS         current
        DESCRIPTION    "."
        ::= { tnOpticalPortInfoGroups 397 }

    tnOtdrmPortInfoGroup OBJECT-GROUP
        OBJECTS {
            tnOtdrmPortInfoFunction
        }
        STATUS         current
        DESCRIPTION    "."
        ::= { tnOpticalPortInfoGroups 398 }

    tnEthToTDMPortAssocInfoScalarsGroup OBJECT-GROUP
        OBJECTS {
            tnEthToTDMPortAssocInfoAttributeTotal
        }
        STATUS         current
        DESCRIPTION    "."
        ::= { tnOpticalPortInfoGroups 399 }

    tnEthToTDMPortAssocInfoGroup OBJECT-GROUP
        OBJECTS {
            tnTDMModuleType,
            tnTDMModuleRate
        }
        STATUS         current
        DESCRIPTION    "."
        ::= { tnOpticalPortInfoGroups 400 }

    tn20an80PortInfoScalarsGroup OBJECT-GROUP
        OBJECTS {
            tn20an80PortInfoAttributeTotal
        }
        STATUS         current
        DESCRIPTION    "."
        ::= { tnOpticalPortInfoGroups 401 }

    tn20an80PortInfoGroup OBJECT-GROUP
        OBJECTS {
            tn20an80PortInfoFunction
        }
        STATUS         current
        DESCRIPTION    "."
        ::= { tnOpticalPortInfoGroups 402 }

    tn10an400PortInfoScalarsGroup OBJECT-GROUP
        OBJECTS {
            tn10an400PortInfoAttributeTotal
        }
        STATUS         current
        DESCRIPTION    "."
        ::= { tnOpticalPortInfoGroups 403 }

    tn10an400PortInfoGroup OBJECT-GROUP
        OBJECTS {
            tn10an400PortInfoFunction
        }
        STATUS         current
        DESCRIPTION    "."
        ::= { tnOpticalPortInfoGroups 404 }

    tn8p20PortInfoScalarsGroup OBJECT-GROUP
        OBJECTS {
            tn8p20PortInfoAttributeTotal
        }
        STATUS         current
        DESCRIPTION    "."
        ::= { tnOpticalPortInfoGroups 405 }

    tn8p20PortInfoGroup OBJECT-GROUP
        OBJECTS {
            tn8p20PortInfoFunction
        }
        STATUS         current
        DESCRIPTION    "."
        ::= { tnOpticalPortInfoGroups 406 }

    tnOpsflexPortInfoScalarsGroup OBJECT-GROUP
        OBJECTS {
            tnOpsflexPortInfoAttributeTotal
        }
        STATUS         current
        DESCRIPTION    "."
        ::= { tnOpticalPortInfoGroups 407 }

    tnOpsflexPortInfoGroup OBJECT-GROUP
        OBJECTS {
            tnOpsflexPortInfoFunction
        }
        STATUS         current
        DESCRIPTION    "."
        ::= { tnOpticalPortInfoGroups 408 }

    tnD5x500qPortInfoScalarsGroup OBJECT-GROUP
        OBJECTS {
            tnD5x500qPortInfoAttributeTotal
        }
        STATUS         current
        DESCRIPTION    "."
        ::= { tnOpticalPortInfoGroups 409 }

    tnD5x500qPortInfoGroup OBJECT-GROUP
        OBJECTS {
            tnD5x500qPortInfoFunction
        }
        STATUS         current
        DESCRIPTION    "."
        ::= { tnOpticalPortInfoGroups 410 }

    tn18p40PortInfoScalarsGroup OBJECT-GROUP
        OBJECTS {
            tn18p40PortInfoAttributeTotal
        }
        STATUS         current
        DESCRIPTION    "."
        ::= { tnOpticalPortInfoGroups 411 }

    tn18p40PortInfoGroup OBJECT-GROUP
        OBJECTS {
            tn18p40PortInfoFunction
        }
        STATUS         current
        DESCRIPTION    "."
        ::= { tnOpticalPortInfoGroups 412 }

    tnDa2c4PortInfoScalarsGroup OBJECT-GROUP
        OBJECTS {
            tnDa2c4PortInfoAttributeTotal
        }
        STATUS         current
        DESCRIPTION    "."
        ::= { tnOpticalPortInfoGroups 413 }

    tnDa2c4PortInfoGroup OBJECT-GROUP
        OBJECTS {
            tnDa2c4PortInfoFunction
        }
        STATUS         current
        DESCRIPTION    "."
        ::= { tnOpticalPortInfoGroups 414 }

    tn130sla1PortInfoScalarsGroup OBJECT-GROUP
        OBJECTS {
            tn130sla1PortInfoAttributeTotal
        }
        STATUS         current
        DESCRIPTION    "."
        ::= { tnOpticalPortInfoGroups 415 }

    tn130sla1PortInfoGroup OBJECT-GROUP
        OBJECTS {
            tn130sla1PortInfoFunction
        }
        STATUS         current
        DESCRIPTION    "."
        ::= { tnOpticalPortInfoGroups 416 }

    tn130slx10PortInfoScalarsGroup OBJECT-GROUP
        OBJECTS {
            tn130slx10PortInfoAttributeTotal
        }
        STATUS         current
        DESCRIPTION    "."
        ::= { tnOpticalPortInfoGroups 417 }

    tn130slx10PortInfoGroup OBJECT-GROUP
        OBJECTS {
            tn130slx10PortInfoFunction
        }
        STATUS         current
        DESCRIPTION    "."
        ::= { tnOpticalPortInfoGroups 418 }

    tnPSS12xPowerFilterPortInfoScalarsGroup OBJECT-GROUP
        OBJECTS {
            tnPSS12xPowerFilterPortInfoAttributeTotal
        }
        STATUS         current
        DESCRIPTION    "."
        ::= { tnOpticalPortInfoGroups 419 }

    tnPSS12xPowerFilterPortInfoGroup OBJECT-GROUP
        OBJECTS {
            tnPSS12xPowerFilterPortInfoFunction
        }
        STATUS         current
        DESCRIPTION    "."
        ::= { tnOpticalPortInfoGroups 420 }

    tnIroadm20PortInfoScalarsGroup OBJECT-GROUP
        OBJECTS {
            tnIroadm20PortInfoAttributeTotal
        }
        STATUS         current
        DESCRIPTION    "."
        ::= { tnOpticalPortInfoGroups 421 }

    tnIroadm20PortInfoGroup OBJECT-GROUP
        OBJECTS {
            tnIroadm20PortInfoFunction
        }
        STATUS         current
        DESCRIPTION    "."
        ::= { tnOpticalPortInfoGroups 422 }

    tnS2ad200PortInfoScalarsGroup OBJECT-GROUP
        OBJECTS {
            tnS2ad200PortInfoAttributeTotal
        }
        STATUS         current
        DESCRIPTION    "."
        ::= { tnOpticalPortInfoGroups 423 }

    tnS2ad200PortInfoGroup OBJECT-GROUP
        OBJECTS {
            tnS2ad200PortInfoFunction
        }
        STATUS         current
        DESCRIPTION    "."
        ::= { tnOpticalPortInfoGroups 424 }

    tnMsh4fsbPortInfoScalarsGroup OBJECT-GROUP
        OBJECTS {
            tnMsh4fsbPortInfoAttributeTotal
        }
        STATUS         current
        DESCRIPTION    "."
        ::= { tnOpticalPortInfoGroups 425 }

    tnMsh4fsbPortInfoGroup OBJECT-GROUP
        OBJECTS {
            tnMsh4fsbPortInfoFunction
        }
        STATUS         current
        DESCRIPTION    "."
        ::= { tnOpticalPortInfoGroups 426 }

    tn2ux200PortInfoScalarsGroup OBJECT-GROUP
        OBJECTS {
            tn2ux200PortInfoAttributeTotal
        }
        STATUS         current
        DESCRIPTION    "."
        ::= { tnOpticalPortInfoGroups 427 }

    tn2ux200PortInfoGroup OBJECT-GROUP
        OBJECTS {
            tn2ux200PortInfoFunction
        }
        STATUS         current
        DESCRIPTION    "."
        ::= { tnOpticalPortInfoGroups 428 }

    tn4mx200PortInfoScalarsGroup OBJECT-GROUP
        OBJECTS {
            tn4mx200PortInfoAttributeTotal
        }
        STATUS         current
        DESCRIPTION    "."
        ::= { tnOpticalPortInfoGroups 429 }

    tn4mx200PortInfoGroup OBJECT-GROUP
        OBJECTS {
            tn4mx200PortInfoFunction
        }
        STATUS         current
        DESCRIPTION    "."
        ::= { tnOpticalPortInfoGroups 430 }

    tnOpsb5PortInfoScalarsGroup OBJECT-GROUP
        OBJECTS {
            tnOpsb5PortInfoAttributeTotal
        }
        STATUS         current
        DESCRIPTION    "."
        ::= { tnOpticalPortInfoGroups 431 }

    tnOpsb5PortInfoGroup OBJECT-GROUP
        OBJECTS {
            tnOpsb5PortInfoFunction
        }
        STATUS         current
        DESCRIPTION    "."
        ::= { tnOpticalPortInfoGroups 432 }

    tnAswglPortInfoScalarsGroup OBJECT-GROUP
        OBJECTS {
            tnAswglPortInfoAttributeTotal
        }
        STATUS         current
        DESCRIPTION    "."
        ::= { tnOpticalPortInfoGroups 433 }

    tnAswglPortInfoGroup OBJECT-GROUP
        OBJECTS {
            tnAswglPortInfoFunction
        }
        STATUS         current
        DESCRIPTION    "."
        ::= { tnOpticalPortInfoGroups 434 }

    tnIpreampPortInfoScalarsGroup OBJECT-GROUP
        OBJECTS {
            tnIpreampPortInfoAttributeTotal
        }
        STATUS         current
        DESCRIPTION    "."
        ::= { tnOpticalPortInfoGroups 435 }

    tnIpreampPortInfoGroup OBJECT-GROUP
        OBJECTS {
            tnIpreampPortInfoFunction
        }
        STATUS         current
        DESCRIPTION    "."
        ::= { tnOpticalPortInfoGroups 436 }

--    obsolete
--    tn40cx800PortInfoScalarsGroup OBJECT-GROUP ::= { tnOpticalPortInfoGroups 437 }
--    tn40cx800PortInfoGroup        OBJECT-GROUP ::= { tnOpticalPortInfoGroups 438 }

    tnIrdm32PortInfoScalarsGroup OBJECT-GROUP
        OBJECTS {
            tnIrdm32PortInfoAttributeTotal
        }
        STATUS         current
        DESCRIPTION    "."
        ::= { tnOpticalPortInfoGroups 439 }

    tnIrdm32PortInfoGroup OBJECT-GROUP
        OBJECTS {
            tnIrdm32PortInfoFunction
        }
        STATUS         current
        DESCRIPTION    "."
        ::= { tnOpticalPortInfoGroups 440 }

    tnRa4pPortInfoScalarsGroup OBJECT-GROUP
        OBJECTS {
            tnRa4pPortInfoAttributeTotal
        }
        STATUS         current
        DESCRIPTION    "."
        ::= { tnOpticalPortInfoGroups 441 }

    tnRa4pPortInfoGroup OBJECT-GROUP
        OBJECTS {
            tnRa4pPortInfoFunction
        }
        STATUS         current
        DESCRIPTION    "."
        ::= { tnOpticalPortInfoGroups 442 }

    tnEilaPortInfoScalarsGroup OBJECT-GROUP
        OBJECTS {
            tnEilaPortInfoAttributeTotal
        }
        STATUS         current
        DESCRIPTION    "."
        ::= { tnOpticalPortInfoGroups 443 }

    tnEilaPortInfoGroup OBJECT-GROUP
        OBJECTS {
            tnEilaPortInfoFunction
        }
        STATUS         current
        DESCRIPTION    "."
        ::= { tnOpticalPortInfoGroups 444 }

--    obsolete
--    tn8cx800PortInfoScalarsGroup OBJECT-GROUP ::= { tnOpticalPortInfoGroups 445 }
--    tn8cx800PortInfoGroup        OBJECT-GROUP ::= { tnOpticalPortInfoGroups 446 }
--    tn6px800PortInfoScalarsGroup OBJECT-GROUP ::= { tnOpticalPortInfoGroups 447 }
--    tn6px800PortInfoGroup        OBJECT-GROUP ::= { tnOpticalPortInfoGroups 448 }

    tnMcs16x15PortInfoScalarsGroup OBJECT-GROUP
        OBJECTS {
            tnMcs16x15PortInfoAttributeTotal
        }
        STATUS         current
        DESCRIPTION    "."
        ::= { tnOpticalPortInfoGroups 449 }

    tnMcs16x15PortInfoGroup OBJECT-GROUP
        OBJECTS {
            tnMcs16x15PortInfoFunction,
            tnMcs16x15PortInfoAddInsertionLossToSig1,
            tnMcs16x15PortInfoAddInsertionLossToSig2,
            tnMcs16x15PortInfoAddInsertionLossToSig3,
            tnMcs16x15PortInfoAddInsertionLossToSig4,
            tnMcs16x15PortInfoAddInsertionLossToSig5,
            tnMcs16x15PortInfoAddInsertionLossToSig6,
            tnMcs16x15PortInfoAddInsertionLossToSig7,
            tnMcs16x15PortInfoAddInsertionLossToSig8,
            tnMcs16x15PortInfoAddInsertionLossToSig9,
            tnMcs16x15PortInfoAddInsertionLossToSig10,
            tnMcs16x15PortInfoAddInsertionLossToSig11,
            tnMcs16x15PortInfoAddInsertionLossToSig12,
            tnMcs16x15PortInfoAddInsertionLossToSig13,
            tnMcs16x15PortInfoAddInsertionLossToSig14,
            tnMcs16x15PortInfoAddInsertionLossToSig15,
            tnMcs16x15PortInfoAddInsertionLossToSig16,
            tnMcs16x15PortInfoDropInsertionLossFromSig1,
            tnMcs16x15PortInfoDropInsertionLossFromSig2,
            tnMcs16x15PortInfoDropInsertionLossFromSig3,
            tnMcs16x15PortInfoDropInsertionLossFromSig4,
            tnMcs16x15PortInfoDropInsertionLossFromSig5,
            tnMcs16x15PortInfoDropInsertionLossFromSig6,
            tnMcs16x15PortInfoDropInsertionLossFromSig7,
            tnMcs16x15PortInfoDropInsertionLossFromSig8,
            tnMcs16x15PortInfoDropInsertionLossFromSig9,
            tnMcs16x15PortInfoDropInsertionLossFromSig10,
            tnMcs16x15PortInfoDropInsertionLossFromSig11,
            tnMcs16x15PortInfoDropInsertionLossFromSig12,
            tnMcs16x15PortInfoDropInsertionLossFromSig13,
            tnMcs16x15PortInfoDropInsertionLossFromSig14,
            tnMcs16x15PortInfoDropInsertionLossFromSig15,
            tnMcs16x15PortInfoDropInsertionLossFromSig16
        }
        STATUS         current
        DESCRIPTION    "."
        ::= { tnOpticalPortInfoGroups 450 }

    tn10an1tPortInfoScalarsGroup OBJECT-GROUP
        OBJECTS {
            tn10an1tPortInfoAttributeTotal
        }
        STATUS         current
        DESCRIPTION    "."
        ::= { tnOpticalPortInfoGroups 451 }

    tn10an1tPortInfoGroup OBJECT-GROUP
        OBJECTS {
            tn10an1tPortInfoFunction
        }
        STATUS         current
        DESCRIPTION    "."
        ::= { tnOpticalPortInfoGroups 452 }

    tn8uc1tPortInfoScalarsGroup OBJECT-GROUP
        OBJECTS {
            tn8uc1tPortInfoAttributeTotal
        }
        STATUS         current
        DESCRIPTION    "."
        ::= { tnOpticalPortInfoGroups 453 }

    tn8uc1tPortInfoGroup OBJECT-GROUP
        OBJECTS {
            tn8uc1tPortInfoFunction
        }
        STATUS         current
        DESCRIPTION    "."
        ::= { tnOpticalPortInfoGroups 454 }

    tnDfc12PortInfoScalarsGroup OBJECT-GROUP
        OBJECTS {
            tnDfc12PortInfoAttributeTotal
        }
        STATUS         current
        DESCRIPTION    "."
        ::= { tnOpticalPortInfoGroups 455 }

    tnDfc12PortInfoGroup OBJECT-GROUP
        OBJECTS {
            tnDfc12PortInfoFunction
        }
        STATUS         current
        DESCRIPTION    "."
        ::= { tnOpticalPortInfoGroups 456 }

    tnIrdm32lPortInfoScalarsGroup OBJECT-GROUP
        OBJECTS {
            tnIrdm32lPortInfoAttributeTotal
        }
        STATUS         current
        DESCRIPTION    "."
        ::= { tnOpticalPortInfoGroups 457 }

    tnIrdm32lPortInfoGroup OBJECT-GROUP
        OBJECTS {
            tnIrdm32lPortInfoFunction
        }
        STATUS         current
        DESCRIPTION    "."
        ::= { tnOpticalPortInfoGroups 458 }

    tnS4x400PortInfoScalarsGroup OBJECT-GROUP
        OBJECTS {
            tnS4x400PortInfoAttributeTotal
        }
        STATUS         current
        DESCRIPTION    "."
        ::= { tnOpticalPortInfoGroups 459 }

    tnS4x400PortInfoGroup OBJECT-GROUP
        OBJECTS {
            tnS4x400PortInfoFunction
        }
        STATUS         current
        DESCRIPTION    "."
        ::= { tnOpticalPortInfoGroups 460 }

    tnTPS24PS1PortInfoScalarsGroup OBJECT-GROUP
        OBJECTS {
            tnTPS24PS1PortInfoAttributeTotal
        }
        STATUS         current
        DESCRIPTION    "."
        ::= { tnOpticalPortInfoGroups 461 }

    tnTPS24PS1PortInfoGroup OBJECT-GROUP
        OBJECTS {
            tnTPS24PS1PortInfoFunction
        }
        STATUS         current
        DESCRIPTION    "."
        ::= { tnOpticalPortInfoGroups 462 }

    tnTPS24PS2PortInfoScalarsGroup OBJECT-GROUP
        OBJECTS {
            tnTPS24PS2PortInfoAttributeTotal
        }
        STATUS         current
        DESCRIPTION    "."
        ::= { tnOpticalPortInfoGroups 463 }

    tnTPS24PS2PortInfoGroup OBJECT-GROUP
        OBJECTS {
            tnTPS24PS2PortInfoFunction
        }
        STATUS         current
        DESCRIPTION    "."
        ::= { tnOpticalPortInfoGroups 464 }

    tnTPS12PSPortInfoScalarsGroup OBJECT-GROUP
        OBJECTS {
            tnTPS12PSPortInfoAttributeTotal
        }
        STATUS         current
        DESCRIPTION    "."
        ::= { tnOpticalPortInfoGroups 465 }

    tnTPS12PSPortInfoGroup OBJECT-GROUP
        OBJECTS {
            tnTPS12PSPortInfoFunction
        }
        STATUS         current
        DESCRIPTION    "."
        ::= { tnOpticalPortInfoGroups 466 }

    tnEsrePortInfoScalarsGroup OBJECT-GROUP
        OBJECTS {
            tnEsrePortInfoAttributeTotal
        }
        STATUS         current
        DESCRIPTION    "."
        ::= { tnOpticalPortInfoGroups 467 }

    tnEsrePortInfoGroup OBJECT-GROUP
        OBJECTS {
            tnEsrePortInfoFunction
        }
        STATUS         current
        DESCRIPTION    "."
        ::= { tnOpticalPortInfoGroups 468 }

    tnGenericOtPortInfoScalarsGroup OBJECT-GROUP
        OBJECTS {
            tnGenericOtPortInfoAttributeTotal
        }
        STATUS         current
        DESCRIPTION    "."
        ::= { tnOpticalPortInfoGroups 469 }

    tnGenericOtPortInfoGroup OBJECT-GROUP
        OBJECTS {
            tnGenericOtPortInfoFunction
        }
        STATUS         current
        DESCRIPTION    "."
        ::= { tnOpticalPortInfoGroups 470 }

    tn1ety100PortInfoScalarsGroup OBJECT-GROUP
        OBJECTS {
            tn1ety100PortInfoAttributeTotal
        }
        STATUS         current
        DESCRIPTION    "."
        ::= { tnOpticalPortInfoGroups 471 }

    tn1ety100PortInfoGroup OBJECT-GROUP
        OBJECTS {
            tn1ety100PortInfoFunction
        }
        STATUS         current
        DESCRIPTION    "."
        ::= { tnOpticalPortInfoGroups 472 }

--    obsolete
--    tnD1ad400qPortInfoScalarsGroup OBJECT-GROUP ::= { tnOpticalPortInfoGroups 473 }
--    tnD1ad400qPortInfoGroup        OBJECT-GROUP ::= { tnOpticalPortInfoGroups 474 }

    tnOmdclPortInfoScalarsGroup OBJECT-GROUP
        OBJECTS {
            tnOmdclPortInfoAttributeTotal
        }
        STATUS         current
        DESCRIPTION    "."
        ::= { tnOpticalPortInfoGroups 475 }

    tnOmdclPortInfoGroup OBJECT-GROUP
        OBJECTS {
            tnOmdclPortInfoFunction,
            tnOmdclPortInfoOSCSfpRxPowerIn,
            tnOmdclPortInfoOSCSfpTxPowerOut,
            tnOmdclPortInfoOSCTxPowerIn,
            tnOmdclPortInfoOSCTxPowerOut,
            tnOmdclPortInfoTotalInputPower,
            tnOmdclPortInfoTotalInputPowerL,
            tnOmdclPortInfoInsertionLossSigC1IntoLine1Out,
            tnOmdclPortInfoInsertionLossSigC2IntoLine2Out,
            tnOmdclPortInfoInsertionLossSigL1IntoLine1OutL,
            tnOmdclPortInfoInsertionLossSigL2IntoLine2OutL,
            tnOmdclPortInfoInsertionLosstoSigC1OutFromLine1In,
            tnOmdclPortInfoInsertionLosstoSigC2OutFromLine2In,
            tnOmdclPortInfoInsertionLosstoSigL1OutFromLine1InL,
            tnOmdclPortInfoInsertionLosstoSigL2OutFromLine2InL,
            tnOmdclPortInfoTotalOutputPower,
            tnOmdclPortInfoTotalOutputPowerL,
            tnOmdclPortInfoTotalOutputPowerCplusL,
            tnOmdclPortInfoSpanLoss
        }
        STATUS         current
        DESCRIPTION    "."
        ::= { tnOpticalPortInfoGroups 476 }

    tnMcs16x15lPortInfoScalarsGroup OBJECT-GROUP
        OBJECTS {
            tnMcs16x15lPortInfoAttributeTotal
        }
        STATUS         current
        DESCRIPTION    "."
        ::= { tnOpticalPortInfoGroups 477 }

    tnMcs16x15lPortInfoGroup OBJECT-GROUP
        OBJECTS {
            tnMcs16x15lPortInfoFunction
        }
        STATUS         current
        DESCRIPTION    "."
        ::= { tnOpticalPortInfoGroups 478 }

    tnEilalPortInfoScalarsGroup OBJECT-GROUP
        OBJECTS {
            tnEilalPortInfoAttributeTotal
        }
        STATUS         current
        DESCRIPTION    "."
        ::= { tnOpticalPortInfoGroups 479 }

    tnEilalPortInfoGroup OBJECT-GROUP
        OBJECTS {
            tnEilalPortInfoFunction
        }
        STATUS         current
        DESCRIPTION    "."
        ::= { tnOpticalPortInfoGroups 480 }

    tnRa5pbPortInfoScalarsGroup OBJECT-GROUP
        OBJECTS {
            tnRa5pbPortInfoAttributeTotal
        }
        STATUS         current
        DESCRIPTION    "."
        ::= { tnOpticalPortInfoGroups 481 }

    tnRa5pbPortInfoGroup OBJECT-GROUP
        OBJECTS {
            tnRa5pbPortInfoFunction
        }
        STATUS         current
        DESCRIPTION    "."
        ::= { tnOpticalPortInfoGroups 482 }

    tnMlfsbPortInfoScalarsGroup OBJECT-GROUP
        OBJECTS {
            tnMlfsbPortInfoAttributeTotal
        }
        STATUS         current
        DESCRIPTION    "."
        ::= { tnOpticalPortInfoGroups 483 }

    tnMlfsbPortInfoGroup OBJECT-GROUP
        OBJECTS {
            tnMlfsbPortInfoFunction
        }
        STATUS         current
        DESCRIPTION    "."
        ::= { tnOpticalPortInfoGroups 484 }

    tnPortLptInfoScalarsGroup OBJECT-GROUP
        OBJECTS {
            tnPortLptInfoAttributeTotal
        }
        STATUS         current
        DESCRIPTION    "."
        ::= { tnOpticalPortInfoGroups 485 }

    tnPortLptInfoGroup OBJECT-GROUP
        OBJECTS {
            tnPortLptInfoCons,
            tnPortLptInfoFlsDelayTime,
            tnPortLptInfoTxDisDelayTime,
            tnPortLptInfoExtensionTime
        }
        STATUS         current
        DESCRIPTION    "."
        ::= { tnOpticalPortInfoGroups 486 }

    tnPortInfoScalarsGroup OBJECT-GROUP
        OBJECTS {
            tnPortInfoAttributeTotal
        }
        STATUS         current
        DESCRIPTION    "."
        ::= { tnOpticalPortInfoGroups 487 }

    tnPortInfoGroup OBJECT-GROUP
        OBJECTS {
            tnPortInfoFunction
        }
        STATUS         current
        DESCRIPTION    "."
        ::= { tnOpticalPortInfoGroups 488 }

    tn18P400PortInfoScalarsGroup OBJECT-GROUP
        OBJECTS {
            tn18P400PortInfoAttributeTotal
        }
        STATUS         current
        DESCRIPTION    "."
        ::= { tnOpticalPortInfoGroups 489 }

    tn18P400PortInfoGroup OBJECT-GROUP
        OBJECTS {
            tn18P400PortInfoFunction
        }
        STATUS         current
        DESCRIPTION    "."
        ::= { tnOpticalPortInfoGroups 490 }

    tn4uc1tPortInfoScalarsGroup OBJECT-GROUP
        OBJECTS {
            tn4uc1tPortInfoAttributeTotal
        }
        STATUS         current
        DESCRIPTION    "."
        ::= { tnOpticalPortInfoGroups 491 }

    tn4uc1tPortInfoGroup OBJECT-GROUP
        OBJECTS {
            tn4uc1tPortInfoFunction
        }
        STATUS         current
        DESCRIPTION    "."
        ::= { tnOpticalPortInfoGroups 492 }

    tnAsgPortInfoScalarsGroup OBJECT-GROUP
        OBJECTS {
            tnAsgPortInfoAttributeTotal
        }
        STATUS         current
        DESCRIPTION    "."
        ::= { tnOpticalPortInfoGroups 493 }

    tnAsgPortInfoGroup OBJECT-GROUP
        OBJECTS {
            tnAsgPortInfoFunction
        }
        STATUS         current
        DESCRIPTION    "."
        ::= { tnOpticalPortInfoGroups 494 }

    tn12p120sPortInfoScalarsGroup OBJECT-GROUP
        OBJECTS {
            tn12p120sPortInfoAttributeTotal
        }
        STATUS         current
        DESCRIPTION    "."
        ::= { tnOpticalPortInfoGroups 495 }

    tn12p120sPortInfoGroup OBJECT-GROUP
        OBJECTS {
            tn12p120sPortInfoFunction
        }
        STATUS         current
        DESCRIPTION    "."
        ::= { tnOpticalPortInfoGroups 496 }

    tn16p200PortInfoScalarsGroup OBJECT-GROUP
        OBJECTS {
            tn16p200PortInfoAttributeTotal
        }
        STATUS         current
        DESCRIPTION    "."
        ::= { tnOpticalPortInfoGroups 497 }

    tn16p200PortInfoGroup OBJECT-GROUP
        OBJECTS {
            tn16p200PortInfoFunction
        }
        STATUS         current
        DESCRIPTION    "."
        ::= { tnOpticalPortInfoGroups 498 }

    tnIr9PortInfoScalarsGroup OBJECT-GROUP
        OBJECTS {
            tnIr9PortInfoAttributeTotal
        }
        STATUS         current
        DESCRIPTION    "."
        ::= { tnOpticalPortInfoGroups 499 }

    tnIr9PortInfoGroup OBJECT-GROUP
        OBJECTS {
            tnIr9PortInfoFunction
        }
        STATUS         current
        DESCRIPTION    "."
        ::= { tnOpticalPortInfoGroups 500 }

    tnMxn824PortInfoScalarsGroup OBJECT-GROUP
        OBJECTS {
            tnMxn824PortInfoAttributeTotal
        }
        STATUS         current
        DESCRIPTION    "."
        ::= { tnOpticalPortInfoGroups 501 }

    tnMxn824PortInfoGroup OBJECT-GROUP
        OBJECTS {
            tnMxn824PortInfoFunction
        }
        STATUS         current
        DESCRIPTION    "."
        ::= { tnOpticalPortInfoGroups 502 }

    tnAsc4PortInfoScalarsGroup OBJECT-GROUP
        OBJECTS {
            tnAsc4PortInfoAttributeTotal
        }
        STATUS         current
        DESCRIPTION    "."
        ::= { tnOpticalPortInfoGroups 503 }

    tnAsc4PortInfoGroup OBJECT-GROUP
        OBJECTS {
            tnAsc4PortInfoFunction
        }
        STATUS         current
        DESCRIPTION    "."
        ::= { tnOpticalPortInfoGroups 504 }

    tn5mx500PortInfoScalarsGroup OBJECT-GROUP
        OBJECTS {
            tn5mx500PortInfoAttributeTotal
        }
        STATUS         current
        DESCRIPTION    "."
        ::= { tnOpticalPortInfoGroups 505 }

    tn5mx500PortInfoGroup OBJECT-GROUP
        OBJECTS {
            tn5mx500PortInfoFunction
        }
        STATUS         current
        DESCRIPTION    "."
        ::= { tnOpticalPortInfoGroups 506 }

    tn2ux500PortInfoScalarsGroup OBJECT-GROUP
        OBJECTS {
            tn2ux500PortInfoAttributeTotal
        }
        STATUS         current
        DESCRIPTION    "."
        ::= { tnOpticalPortInfoGroups 507 }

    tn2ux500PortInfoGroup OBJECT-GROUP
        OBJECTS {
            tn2ux500PortInfoFunction
        }
        STATUS         current
        DESCRIPTION    "."
        ::= { tnOpticalPortInfoGroups 508 }

    tnMxnPortChannelInfoScalarsGroup OBJECT-GROUP
        OBJECTS {
            tnMxnPortChannelInfoAttributeTotal
        }
        STATUS         current
        DESCRIPTION    "."
        ::= { tnOpticalPortInfoGroups 509 }

    tnMxnPortChannelInfoGroup OBJECT-GROUP
        OBJECTS {
            tnMxnPortChannelInfoCurrentRoutingAdd,
            tnMxnPortChannelInfoCurrentRoutingDrop
        }
        STATUS         current
        DESCRIPTION    "."
        ::= { tnOpticalPortInfoGroups 510 }

    tnMxnPortInfoScalarsGroup OBJECT-GROUP
        OBJECTS {
            tnMxnPortInfoAttributeTotal
        }
        STATUS         current
        DESCRIPTION    "."
        ::= { tnOpticalPortInfoGroups 511 }

    tnMxnPortInfoGroup OBJECT-GROUP
        OBJECTS {
            tnMxnPortInfoAddInsertionLossToSig1,
            tnMxnPortInfoAddInsertionLossToSig2,
            tnMxnPortInfoAddInsertionLossToSig3,
            tnMxnPortInfoAddInsertionLossToSig4,
            tnMxnPortInfoAddInsertionLossToSig5,
            tnMxnPortInfoAddInsertionLossToSig6,
            tnMxnPortInfoAddInsertionLossToSig7,
            tnMxnPortInfoAddInsertionLossToSig8,
            tnMxnPortInfoInputPower,
            tnMxnPortInfoOutputPower,
            tnMxnPortInfoDropInsertionLossFromSig1,
            tnMxnPortInfoDropInsertionLossFromSig2,
            tnMxnPortInfoDropInsertionLossFromSig3,
            tnMxnPortInfoDropInsertionLossFromSig4,
            tnMxnPortInfoDropInsertionLossFromSig5,
            tnMxnPortInfoDropInsertionLossFromSig6,
            tnMxnPortInfoDropInsertionLossFromSig7,
            tnMxnPortInfoDropInsertionLossFromSig8,
            tnMxnPortInfoAddTargetPower,
            tnMxnPortInfoPlannedFrequencyLowLimitOut,
            tnMxnPortInfoPlannedFrequencyHighLimitOut,
            tnMxnPortInfoPlannedFrequencyLowLimitIn,
            tnMxnPortInfoPlannedFrequencyHighLimitIn,
            tnMxnPortInfoAddExpectedPower,
            tnMxnPortInfoExpectedPowerDev
        }
        STATUS         current
        DESCRIPTION    "."
        ::= { tnOpticalPortInfoGroups 512 }

    tnAscPortInfoScalarsGroup OBJECT-GROUP
        OBJECTS {
            tnAscPortInfoAttributeTotal
        }
        STATUS         current
        DESCRIPTION    "."
        ::= { tnOpticalPortInfoGroups 513 }

    tnAscPortInfoGroup OBJECT-GROUP
        OBJECTS {
            tnAscPortInfoTotalInputPower,
            tnAscPortInfoLosMode,
            tnAscPortInfoChanInputPower,
            tnAscPortInfoTotalOutputPower,
            tnAscPortInfoPowerGain,
            tnAscPortInfoSignalPowerOut,
            tnAscPortInfoOAMPumpTemperature,
            tnAscPortInfoOAMPumpBiases,
            tnAscPortInfoEnable,
            tnAscPortInfoPlannedFrequencyIn,
            tnAscPortInfoPlannedFrequencyOut,
            tnAscPortInfoPlannedFrequencyLowLimitOut,
            tnAscPortInfoPlannedFrequencyHighLimitOut,
            tnAscPortInfoPlannedFrequencyLowLimitIn,
            tnAscPortInfoPlannedFrequencyHighLimitIn,
            tnAscPortInfoChanTargetPower,
            tnAscPortInfoExpectedPowerDev,
            tnAscPortInfoVoaCurrent,
            tnAscPortInputToOutputGain
        }
        STATUS         current
        DESCRIPTION    "."
        ::= { tnOpticalPortInfoGroups 514 }

    tnOpsumPortInfoScalarsGroup OBJECT-GROUP
        OBJECTS {
            tnOpsumPortInfoAttributeTotal
        }
        STATUS         current
        DESCRIPTION    "."
        ::= { tnOpticalPortInfoGroups 515 }

    tnOpsumPortInfoGroup OBJECT-GROUP
        OBJECTS {
            tnOpsumPortInfoFunction
        }
        STATUS         current
        DESCRIPTION    "."
        ::= { tnOpticalPortInfoGroups 516 }

    tnMxn1624PortInfoScalarsGroup OBJECT-GROUP
        OBJECTS {
            tnMxn1624PortInfoAttributeTotal
        }
        STATUS         current
        DESCRIPTION    "."
        ::= { tnOpticalPortInfoGroups 517 }

    tnMxn1624PortInfoGroup OBJECT-GROUP
        OBJECTS {
            tnMxn1624PortInfoFunction
        }
        STATUS         current
        DESCRIPTION    "."
        ::= { tnOpticalPortInfoGroups 518 }

    tnIr4PortInfoScalarsGroup OBJECT-GROUP
        OBJECTS {
            tnIr4PortInfoAttributeTotal
        }
        STATUS         current
        DESCRIPTION    "."
        ::= { tnOpticalPortInfoGroups 519 }

    tnIr4PortInfoGroup OBJECT-GROUP
        OBJECTS {
            tnIr4PortInfoFunction
        }
        STATUS         current
        DESCRIPTION    "."
        ::= { tnOpticalPortInfoGroups 520 }

    tnAsc2PortInfoScalarsGroup OBJECT-GROUP
        OBJECTS {
            tnAsc2PortInfoAttributeTotal
        }
        STATUS         current
        DESCRIPTION    "."
        ::= { tnOpticalPortInfoGroups 521 }

    tnAsc2PortInfoGroup OBJECT-GROUP
        OBJECTS {
            tnAsc2PortInfoFunction
        }
        STATUS         current
        DESCRIPTION    "."
        ::= { tnOpticalPortInfoGroups 522 }

    tnSfd48PortInfoScalarsGroup OBJECT-GROUP
        OBJECTS {
            tnSfd48PortInfoAttributeTotal
        }
        STATUS         current
        DESCRIPTION    "."
        ::= { tnOpticalPortInfoGroups 523 }

    tnSfd48PortInfoGroup OBJECT-GROUP
        OBJECTS {
            tnSfd48PortInfoFunction
        }
        STATUS         current
        DESCRIPTION    "."
        ::= { tnOpticalPortInfoGroups 524 }

    tnSfd64PortInfoScalarsGroup OBJECT-GROUP
        OBJECTS {
            tnSfd64PortInfoAttributeTotal
        }
        STATUS         current
        DESCRIPTION    "."
        ::= { tnOpticalPortInfoGroups 525 }

    tnSfd64PortInfoGroup OBJECT-GROUP
        OBJECTS {
            tnSfd64PortInfoFunction
        }
        STATUS         current
        DESCRIPTION    "."
        ::= { tnOpticalPortInfoGroups 526 }

    tnIr32AWPortInfoScalarsGroup OBJECT-GROUP
        OBJECTS {
            tnIr32AWPortInfoAttributeTotal
        }
        STATUS         current
        DESCRIPTION    "."
        ::= { tnOpticalPortInfoGroups 527 }

    tnIr32AWPortInfoGroup OBJECT-GROUP
        OBJECTS {
            tnIr32AWPortInfoFunction
        }
        STATUS         current
        DESCRIPTION    "."
        ::= { tnOpticalPortInfoGroups 528 }

    tnEilaAWPortInfoScalarsGroup OBJECT-GROUP
        OBJECTS {
            tnEilaAWPortInfoAttributeTotal
        }
        STATUS         current
        DESCRIPTION    "."
        ::= { tnOpticalPortInfoGroups 529 }

    tnEilaAWPortInfoGroup OBJECT-GROUP
        OBJECTS {
            tnEilaAWPortInfoFunction
        }
        STATUS         current
        DESCRIPTION    "."
        ::= { tnOpticalPortInfoGroups 530 }

    tn18ce300PortInfoScalarsGroup OBJECT-GROUP
        OBJECTS {
            tn18ce300PortInfoAttributeTotal
        }
        STATUS         current
        DESCRIPTION    "."
        ::= { tnOpticalPortInfoGroups 531 }

    tn18ce300PortInfoGroup OBJECT-GROUP
        OBJECTS {
            tn18ce300PortInfoFunction
        }
        STATUS         current
        DESCRIPTION    "."
        ::= { tnOpticalPortInfoGroups 532 }

    tnOpsumlPortInfoScalarsGroup OBJECT-GROUP
        OBJECTS {
            tnOpsumlPortInfoAttributeTotal
        }
        STATUS         current
        DESCRIPTION    "."
        ::= { tnOpticalPortInfoGroups 533 }

    tnOpsumlPortInfoGroup OBJECT-GROUP
        OBJECTS {
            tnOpsumlPortInfoFunction
        }
        STATUS         current
        DESCRIPTION    "."
        ::= { tnOpticalPortInfoGroups 534 }

-------------------------------------------------------------------------------
-- Conformance Port Line Card Config Group Definitions
--------------------------------------------------------------------------------
--    obsolete
--    tnBbaHgPortLcConfigScalarsGroup OBJECT-GROUP ::= { tnOpticalPortLcConfigGroups 1 }
--    tnBbaHgPortLcConfigGroup        OBJECT-GROUP ::= { tnOpticalPortLcConfigGroups 2 }
--    tnBbaLgPortLcConfigScalarsGroup OBJECT-GROUP ::= { tnOpticalPortLcConfigGroups 3 }
--    tnBbaLgPortLcConfigGroup        OBJECT-GROUP ::= { tnOpticalPortLcConfigGroups 4 }

--------------------------------------------------------------------------------
-- Compliance Statements (mandatory)
--------------------------------------------------------------------------------
    tnOpticalPortCompliance MODULE-COMPLIANCE
        STATUS         current
        DESCRIPTION    "."
        MODULE
        MANDATORY-GROUPS {
--            obsolete
--            tnOpticalPortScalarsGroup,
--            tnOC48SwsPortScalarsGroup,
--            tnSimpleOpticsPortScalarsGroup,
--            tnOC48SwsUserNwPortScalarsGroup,
--            tnOC48SwsUserNwPortGroup,
--            tnBandFilterPortScalarsGroup,
--            tnBandFilterPortGroup,
--            tnOscPortScalarsGroup,
--            tnOscPortGroup,
--            tnChannelFilterPortScalarsGroup,
--            tnChannelFilterPortGroup,
--            tnBbaLinePortScalarsGroup,
--            tnBbaLinePortGroup,
--            tnPpsPortScalarsGroup,
--            tnPpsPortGroup,
--            tnOC192SwsUserNwPortScalarsGroup,
--            tnOC192SwsUserNwPortGroup,
--            tn2x1GEoSWSPortScalarsGroup,
--            tn2x1GEoSWSPortGroup,
--            tnSonetPortScalarsGroup,
--            tnSonetPortGroup,
            tnOpticalPortGroup,
--            obsolete
--            tnRoadmPortScalarsGroup,
--            tnRoadmPortGroup,
--            tnWaveKeyPortScalarsGroup,
            tnWaveKeyPortGroup,
--            obsolete
--            tn10GELANPortScalarsGroup,
--            tn10GELANPortGroup,
            tnOpticalFiberGroup,
--            obsolete
--            tnChannelAddDropPortScalarsGroup,
--            tnChannelAddDropPortGroup,
--            tnQuadOC48MuxPortScalarsGroup,
--            tnQuadOC48MuxPortGroup,
--            tnBbaLowGainPortScalarsGroup,
--            tnBbaLowGainPortGroup,
            tnLoopbackPortGroup,
--            obsolete
--            tnDcmPortScalarsGroup,
--            tnDcmPortGroup,
            tnInsertionLossPortGroup,
--            obsolete
--            tnQuadOC3or12MuxPortScalarsGroup,
--            tnQuadOC3or12MuxPortGroup,
--            tnDecaGigEMuxPortScalarsGroup,
--            tnDecaGigEMuxPortGroup,
            tnProtectionGroupPortGroup,
            tnDTVPortGroup,
            tnPortInventoryGroup,
            tnPortOtdrScanGroup,
            tnFlexgridOtsInfoGroup,
            tnOpticalPortConnectorGroup,
--            obsolete
--            tnPortOtdrScanMGroup,
            tnOtsConfigGroup,
            tnPotentialQMarginGroup,
            tnAutoTurnUpGroup,
            tnMaxPortGroup,
            tnAutoTurnUpOmsGroup
        }
        ::= { tnOpticalPortCompliances 1 }

--------------------------------------------------------------------------------
-- Compliance Port Config Statements (mandatory)
--------------------------------------------------------------------------------
    tnOpticalPortConfigCompliance MODULE-COMPLIANCE
        STATUS         current
        DESCRIPTION    "."
        MODULE
        MANDATORY-GROUPS {
            tnSdhPortConfigScalarsGroup,
            tnSdhPortConfigGroup,
--            obsolete
--            tnOC48STM16PortConfigScalarsGroup,
--            tnOC48STM16PortConfigGroup,
--            tnOC192STM64PortConfigScalarsGroup,
--            tnOC192STM64PortConfigGroup,
--            tnQuadOC48STM16MuxPortConfigScalarsGroup,
--            tnQuadOC48STM16MuxPortConfigGroup,
--            tnQuadOC3or12STM1or4MuxPortConfigScalarsGroup,
--            tnQuadOC3or12STM1or4MuxPortConfigGroup,
--            tnBandFilterPortConfigScalarsGroup,
--            tnBandFilterPortConfigGroup,
            tnOscPortConfigScalarsGroup,
            tnOscPortConfigGroup,
--            obsolete
--            tnChFilterPortConfigScalarsGroup,
--            tnChFilterPortConfigGroup,
--            tnChAddDropPortConfigScalarsGroup,
--            tnChAddDropPortConfigGroup,
--            tnBbaHgPortConfigScalarsGroup,
--            tnBbaHgPortConfigGroup,
--            tnBbaLgPortConfigScalarsGroup,
--            tnBbaLgPortConfigGroup,
--            tnPpsPortConfigScalarsGroup,
--            tnPpsPortConfigGroup,
--            tnDualGigEMuxPortConfigScalarsGroup,
--            tnDualGigEMuxPortConfigGroup,
--            tnRoadmPortConfigScalarsGroup,
--            tnRoadmPortConfigGroup,
--            tn10GigELANPortConfigScalarsGroup,
--            tn10GigELANPortConfigGroup,
            tnDcmPortConfigScalarsGroup,
            tnDcmPortConfigGroup,
--            obsolete
--            tnDecaGigEMuxPortConfigScalarsGroup,
--            tnDecaGigEMuxPortConfigGroup,
            tnSonetPortConfigScalarsGroup,
            tnSonetPortConfigGroup,
--            obsolete
--            tnExternalDcuPortConfigScalarsGroup,
--            tnExternalDcuPortConfigGroup,
            tnDigitalWrapperPortConfigScalarsGroup,
            tnDigitalWrapperPortConfigGroup,
            tnNetworkPortConfigScalarsGroup,
            tnNetworkPortConfigGroup,
--            obsolete
--            tnMsaHgPortConfigScalarsGroup,
--            tnMsaHgPortConfigGroup,
--            tnCmd42PortConfigScalarsGroup,
--            tnCmd42PortConfigGroup,
--            tnWssX9PortConfigScalarsGroup,
--            tnWssX9PortConfigGroup,
            tnSfpPortConfigScalarsGroup,
            tnSfpPortConfigGroup,
--            obsolete
--            tn1xMR2dot5GPortConfigScalarsGroup,
--            tn1xMR2dot5GPortConfigGroup,
            tnOpsaPortConfigScalarsGroup,
            tnOpsaPortConfigGroup,
            tn11stmm10PortConfigScalarsGroup,
            tn11stmm10PortConfigGroup,
            tn11star1PortConfigScalarsGroup,
            tn11star1PortConfigGroup,
            tnAhphgPortConfigScalarsGroup,
            tnAhphgPortConfigGroup,
            tnAlphgPortConfigScalarsGroup,
            tnAlphgPortConfigGroup,
            tnCwr8PortConfigScalarsGroup,
            tnCwr8PortConfigGroup,
            tn11stge12PortConfigScalarsGroup,
            tn11stge12PortConfigGroup,
            tn11dpge12PortConfigScalarsGroup,
            tn11dpge12PortConfigGroup,
            tnSfd44PortConfigScalarsGroup,
            tnSfd44PortConfigGroup,
            tnDwdmCmnPortConfigGroup,
            tnDwdmCmnLinePortConfigGroup,
            tnDwdmCmnClientPortConfigGroup,
            tnRsmonIngrPortConfigGroup,
            tnMsmonPortConfigGroup,
            tnOscSfpPortConfigGroup,
            tnDwdmGpPhyPortConfigGroup,
--            obsolete
--            tnGccPortConfigGroup,
            tnSvacPortConfigGroup,
            tnSfdPortConfigGroup,
            tnSfcPortConfigGroup,
            tnVtsPortConfigGroup,
            tnOmdPortConfigGroup,
            tn4dpa4PortConfigScalarsGroup,
            tn4dpa4PortConfigGroup,
            tnCwr8c88PortConfigScalarsGroup,
            tnCwr8c88PortConfigGroup,
            tnSfd44bPortConfigScalarsGroup,
            tnSfd44bPortConfigGroup,
            tnItlbPortConfigScalarsGroup,
            tnItlbPortConfigGroup,
            tnAhplgPortConfigScalarsGroup,
            tnAhplgPortConfigGroup,
            tnDwdmCmnOtu1Odu1LinePortConfigGroup,
            tnDwdmCmnOtu1Odu1ClientPortConfigGroup,
            tn43stx4PortConfigScalarsGroup,
            tn43stx4PortConfigGroup,
            tnDwdmCmnOtu3Odu3LinePortConfigGroup,
            tnAlpfgkPortConfigScalarsGroup,
            tnAlpfgkPortConfigGroup,
            tn4dpa2PortConfigScalarsGroup,
            tn4dpa2PortConfigGroup,
            tn43sta1pPortConfigScalarsGroup,
            tn43sta1pPortConfigGroup,
            tn43stx4pPortConfigScalarsGroup,
            tn43stx4pPortConfigGroup,
            tnA2325aPortConfigScalarsGroup,
            tnA2325aPortConfigGroup,
            tnSfd40PortConfigScalarsGroup,
            tnSfd40PortConfigGroup,
            tnSfd40bPortConfigScalarsGroup,
            tnSfd40bPortConfigGroup,
            tn11qpa4PortConfigScalarsGroup,
            tn11qpa4PortConfigGroup,
            tn112scx10PortConfigScalarsGroup,
            tn112scx10PortConfigGroup,
            tn112sca1PortConfigScalarsGroup,
            tn112sca1PortConfigGroup,
            tnDwdmCmnOtu4Odu4LinePortConfigGroup,
            tnDwdmCmnOtu4Odu4ClientPortConfigGroup,
            tnRsmonEgrPortConfigGroup,
            tnDwdmCbrArPortConfigGroup,
            tnAlpfgtPortConfigScalarsGroup,
            tnAlpfgtPortConfigGroup,
            tnOsctPortConfigScalarsGroup,
            tnOsctPortConfigGroup,
            tnWtocmPortConfigScalarsGroup,
            tnWtocmPortConfigGroup,
            tnWr2c88PortConfigScalarsGroup,
            tnWr2c88PortConfigGroup,
            tnAm2017bPortConfigScalarsGroup,
            tnAm2017bPortConfigGroup,
            tnAm2325bPortConfigScalarsGroup,
            tnAm2325bPortConfigGroup,
            tn1dpp21PortConfigScalarsGroup,
            tn1dpp21PortConfigGroup,
            tnE1T1PortConfigGroup,
            tnMvacPortConfigScalarsGroup,
            tnMvacPortConfigGroup,
            tn43scx4PortConfigScalarsGroup,
            tn43scx4PortConfigGroup,
            tnRa2pPortConfigScalarsGroup,
            tnRa2pPortConfigGroup,
            tnAm2318aPortConfigScalarsGroup,
            tnAm2318aPortConfigGroup,
            tnAm2125aPortConfigScalarsGroup,
            tnAm2125aPortConfigGroup,
            tnItluPortConfigScalarsGroup,
            tnItluPortConfigGroup,
            tnWr8c88aPortConfigScalarsGroup,
            tnWr8c88aPortConfigGroup,
            tn11dpe12ePortConfigScalarsGroup,
            tn11dpe12ePortConfigGroup,
            tn112sx10lPortConfigScalarsGroup,
            tn112sx10lPortConfigGroup,
            tn112sa1lPortConfigScalarsGroup,
            tn112sa1lPortConfigGroup,
            tn11dpm12PortConfigScalarsGroup,
            tn11dpm12PortConfigGroup,
--            obsolete
--            tnWr8c88aAttenPortConfigGroup,
            tnRamanPortConfigGroup,
            tnMesh4PortConfigScalarsGroup,
            tnMesh4PortConfigGroup,
--            obsolete
--            tnTcmPortConfigScalarsGroup,
--            tnTcmPortConfigGroup,
            tn43sca1PortConfigScalarsGroup,
            tn43sca1PortConfigGroup,
            tn43scx4lPortConfigScalarsGroup,
            tn43scx4lPortConfigGroup,
            tnAm2125bPortConfigScalarsGroup,
            tnAm2125bPortConfigGroup,
            tn112snx10PortConfigScalarsGroup,
            tn112snx10PortConfigGroup,
            tn112sna1PortConfigScalarsGroup,
            tn112sna1PortConfigGroup,
--            obsolete
--            tn11qta4PortConfigScalarsGroup,
--            tn11qta4PortConfigGroup,
            tn1dpp24mPortConfigScalarsGroup,
            tn1dpp24mPortConfigGroup,
            tnDwdmCmnOtu3Odu3ClientPortConfigGroup,
            tnul43scupPortConfigScalarsGroup,
            tnul43scupPortConfigGroup,
            tnul11qcupPortConfigScalarsGroup,
            tnul11qcupPortConfigGroup,
            tn11qpen4PortConfigScalarsGroup,
            tn11qpen4PortConfigGroup,
            tn43scx4ePortConfigScalarsGroup,
            tn43scx4ePortConfigGroup,
            tn43scge1PortConfigScalarsGroup,
            tn43scge1PortConfigGroup,
            tn11qpe24PortConfigScalarsGroup,
            tn11qpe24PortConfigGroup,
            tn11star1aPortConfigScalarsGroup,
            tn11star1aPortConfigGroup,
            tnMvac8bPortConfigScalarsGroup,
            tnMvac8bPortConfigGroup,
            tnWssAttenPortConfigScalarsGroup,
            tnWssAttenPortConfigGroup,
            tnWr8c88afPortConfigScalarsGroup,
            tnWr8c88afPortConfigGroup,
            tncl10an10gPortConfigScalarsGroup,
            tncl10an10gPortConfigGroup,
            tncl24anmPortConfigScalarsGroup,
            tncl24anmPortConfigGroup,
            tnOpsbPortConfigScalarsGroup,
            tnOpsbPortConfigGroup,
            tnOpsPortConfigScalarsGroup,
            tnOpsPortConfigGroup,
            tn11dpe12aPortConfigScalarsGroup,
            tn11dpe12aPortConfigGroup,
            tnul130scupPortConfigScalarsGroup,
            tnul130scupPortConfigGroup,
            tn130scx10PortConfigScalarsGroup,
            tn130scx10PortConfigGroup,
            tnA2p2125PortConfigScalarsGroup,
            tnA2p2125PortConfigGroup,
            tn4qpa8PortConfigScalarsGroup,
            tn4qpa8PortConfigGroup,
            tnOt112pdm11PortConfigScalarsGroup,
            tnOt112pdm11PortConfigGroup,
            tnWtocmaPortConfigScalarsGroup,
            tnWtocmaPortConfigGroup,
            tnPtpctlPortConfigScalarsGroup,
            tnPtpctlPortConfigGroup,
            tnPtpioPortConfigScalarsGroup,
            tnPtpioPortConfigGroup,
            tnIo24et1gbPortConfigScalarsGroup,
            tnIo24et1gbPortConfigGroup,
            tnDwdmIoPortConfigScalarsGroup,
            tnDwdmIoPortConfigGroup,
            tnIo4an10gPortConfigScalarsGroup,
            tnIo4an10gPortConfigGroup,
            tnIo8et1gbPortConfigScalarsGroup,
            tnIo8et1gbPortConfigGroup,
            tnIo10et10gPortConfigScalarsGroup,
            tnIo10et10gPortConfigGroup,
            tnUl11qcupcPortConfigScalarsGroup,
            tnUl11qcupcPortConfigGroup,
            tnOt520scx4PortConfigScalarsGroup,
            tnOt520scx4PortConfigGroup,
            tnWssAprPortConfigScalarsGroup,
            tnWssAprPortConfigGroup,
            tnPowerFilterPortConfigScalarsGroup,
            tnPowerFilterPortConfigGroup,
            tn11ope8PortConfigScalarsGroup,
            tn11ope8PortConfigGroup,
            tn11qce12xPortConfigScalarsGroup,
            tn11qce12xPortConfigGroup,
            tnAm2625aPortConfigScalarsGroup,
            tnAm2625aPortConfigGroup,
            tnAm2032aPortConfigScalarsGroup,
            tnAm2032aPortConfigGroup,
            tnOt260scx2PortConfigScalarsGroup,
            tnOt260scx2PortConfigGroup,
            tnOt130snx10PortConfigScalarsGroup,
            tnOt130snx10PortConfigGroup,
            tnIo24anmbPortConfigScalarsGroup,
            tnIo24anmbPortConfigGroup,
            tnOt11dpm8PortConfigScalarsGroup,
            tnOt11dpm8PortConfigGroup,
            tnOt11dpm4mPortConfigScalarsGroup,
            tnOt11dpm4mPortConfigGroup,
            tnUl130scupbPortConfigScalarsGroup,
            tnUl130scupbPortConfigGroup,
            tnOt112sdx11PortConfigScalarsGroup,
            tnOt112sdx11PortConfigGroup,
            tnAa2donwPortConfigScalarsGroup,
            tnAa2donwPortConfigGroup,
            tnOt130sca1PortConfigScalarsGroup,
            tnOt130sca1PortConfigGroup,
            tnIo10an10gbPortConfigScalarsGroup,
            tnIo10an10gbPortConfigGroup,
            tnIo10et10gbPortConfigScalarsGroup,
            tnIo10et10gbPortConfigGroup,
            tnPsc1x6PortConfigScalarsGroup,
            tnPsc1x6PortConfigGroup,
            tnWr20tfPortConfigScalarsGroup,
            tnWr20tfPortConfigGroup,
            tnWtocmfPortConfigScalarsGroup,
            tnWtocmfPortConfigGroup,
            tnAswgPortConfigScalarsGroup,
            tnAswgPortConfigGroup,
            tnA4pswgPortConfigScalarsGroup,
            tnA4pswgPortConfigGroup,
            tnOtdrPortConfigScalarsGroup,
            tnOtdrPortConfigGroup,
            tnWr20tfmPortConfigScalarsGroup,
            tnWr20tfmPortConfigGroup,
            tnAar8aPortConfigScalarsGroup,
            tnAar8aPortConfigGroup,
            tnMcs8x16PortConfigScalarsGroup,
            tnMcs8x16PortConfigGroup,
            tnMsh8fsmPortConfigScalarsGroup,
            tnMsh8fsmPortConfigGroup,
            tnMcsPortConfigScalarsGroup,
            tnMcsPortConfigGroup,
            tnAarPortConfigScalarsGroup,
            tnAarPortConfigGroup,
            tnWr20tfmPortChannelConfigScalarsGroup,
            tnWr20tfmPortChannelConfigGroup,
            tnMpoPortConfigScalarsGroup,
            tnMpoPortChannelConfigGroup,
            tnIo4an100gPortConfigScalarsGroup,
            tnIo4an100gPortConfigGroup,
            tnIo30an10gPortConfigScalarsGroup,
            tnIo30an10gPortConfigGroup,
            tnIo30an300PortConfigScalarsGroup,
            tnIo30an300PortConfigGroup,
            tnIo4an400PortConfigScalarsGroup,
            tnIo4an400PortConfigGroup,
            tn12p120PortConfigScalarsGroup,
            tn12p120PortConfigGroup,
            tn20p200PortConfigScalarsGroup,
            tn20p200PortConfigGroup,
            tn1ud200PortConfigScalarsGroup,
            tn1ud200PortConfigGroup,
            tnOt130snq10PortConfigScalarsGroup,
            tnOt130snq10PortConfigGroup,
            tnIroadmvPortConfigScalarsGroup,
            tnIroadmvPortConfigGroup,
            tnIroadmfPortConfigScalarsGroup,
            tnIroadmfPortConfigGroup,
            tnIroadmPortConfigScalarsGroup,
            tnIroadmPortConfigGroup,
            tnMonOcmPortConfigScalarsGroup,
            tnMonOcmPortConfigGroup,
            tnUl2uc400PortConfigScalarsGroup,
            tnUl2uc400PortConfigGroup,
            tnUl4uc400PortConfigScalarsGroup,
            tnUl4uc400PortConfigGroup,
            tnUl20uc200PortConfigScalarsGroup,
            tnUl20uc200PortConfigGroup,
            tnD5x500PortConfigScalarsGroup,
            tnD5x500PortConfigGroup,
            tnOtS11M100PortConfigScalarsGroup,
            tnOtS11M100PortConfigGroup,
            tnMonOtdrPortConfigScalarsGroup,
            tnMonOtdrPortConfigGroup,
            tnPSS96PowerFilterPortConfigScalarsGroup,
            tnPSS96PowerFilterPortConfigGroup,
            tn12ce120PortConfigScalarsGroup,
            tn12ce120PortConfigGroup,
            tn1ce100PortConfigScalarsGroup,
            tn1ce100PortConfigGroup,
            tnLcI1000PortConfigScalarsGroup,
            tnLcI1000PortConfigGroup,
            tnAwbegrPortConfigScalarsGroup,
            tnAwbegrPortConfigGroup,
            tnAwbingPortConfigScalarsGroup,
            tnAwbingPortConfigGroup,
            tnAwbilaPortConfigScalarsGroup,
            tnAwbilaPortConfigGroup,
            tnRa5pPortConfigScalarsGroup,
            tnRa5pPortConfigGroup,
            tnIroadm9mPortConfigScalarsGroup,
            tnIroadm9mPortConfigGroup,
            tnS13x100PortConfigScalarsGroup,
            tnS13x100PortConfigGroup,
            tn12ce121PortConfigScalarsGroup,
            tn12ce121PortConfigGroup,
            tnPtpioctlPortConfigScalarsGroup,
            tnPtpioctlPortConfigGroup,
            tnAa2donwbPortConfigScalarsGroup,
            tnAa2donwbPortConfigGroup,
            tnOsctaprPortConfigScalarsGroup,
            tnOsctaprPortConfigGroup,
            tn11qpa4bPortConfigScalarsGroup,
            tn11qpa4bPortConfigGroup,
            tn1ux100PortConfigScalarsGroup,
            tn1ux100PortConfigGroup,
            tn20ax200PortConfigScalarsGroup,
            tn20ax200PortConfigGroup,
            tn20mx80PortConfigScalarsGroup,
            tn20mx80PortConfigGroup,
            tnAar2x8aPortConfigScalarsGroup,
            tnAar2x8aPortConfigGroup,
            tnS13x100ePortConfigScalarsGroup,
            tnS13x100ePortConfigGroup,
            tnWtocmflPortConfigScalarsGroup,
            tnWtocmflPortConfigGroup,
            tnAar2x8alPortConfigScalarsGroup,
            tnAar2x8alPortConfigGroup,
            tnWr20tfmlPortConfigScalarsGroup,
            tnWr20tfmlPortConfigGroup,
            tnMcs8x16lPortConfigScalarsGroup,
            tnMcs8x16lPortConfigGroup,
            tnPSS8xPowerFilterPortConfigScalarsGroup,
            tnPSS8xPowerFilterPortConfigGroup,
            tnLcI2000PortConfigScalarsGroup,
            tnLcI2000PortConfigGroup,
            tn30se300PortConfigScalarsGroup,
            tn30se300PortConfigGroup,
            tn6se300PortConfigScalarsGroup,
            tn6se300PortConfigGroup,
            tnOtdrwbPortConfigScalarsGroup,
            tnOtdrwbPortConfigGroup,
            tn8dc30tPortConfigScalarsGroup,
            tn8dc30tPortConfigGroup,
            tn16dc65tPortConfigScalarsGroup,
            tn16dc65tPortConfigGroup,
            tnD5x500lPortConfigScalarsGroup,
            tnD5x500lPortConfigGroup,
            tnLcI2000lPortConfigScalarsGroup,
            tnLcI2000lPortConfigGroup,
            tnIroadm9rPortConfigScalarsGroup,
            tnIroadm9rPortConfigGroup,
            tnRa2p96PortConfigScalarsGroup,
            tnRa2p96PortConfigGroup,
            tnOtdrmPortConfigScalarsGroup,
            tnOtdrmPortConfigGroup,
            tn103scecPortConfigScalarsGroup,
            tnOcsPacketPortConfigGroup,
            tn20an80PortConfigScalarsGroup,
            tn20an80PortConfigGroup,
            tn10an400PortConfigScalarsGroup,
            tn10an400PortConfigGroup,
            tn8p20PortConfigScalarsGroup,
            tn8p20PortConfigGroup,
            tnOpsflexPortConfigScalarsGroup,
            tnOpsflexPortConfigGroup,
            tnD5x500qPortConfigScalarsGroup,
            tnD5x500qPortConfigGroup,
            tn18p40PortConfigScalarsGroup,
            tn18p40PortConfigGroup,
            tnDa2c4PortConfigScalarsGroup,
            tnDa2c4PortConfigGroup,
            tn130sla1PortConfigScalarsGroup,
            tn130sla1PortConfigGroup,
            tn130slx10PortConfigScalarsGroup,
            tn130slx10PortConfigGroup,
            tnPSS12xPowerFilterPortConfigScalarsGroup,
            tnPSS12xPowerFilterPortConfigGroup,
            tnIroadm20PortConfigScalarsGroup,
            tnIroadm20PortConfigGroup,
            tnS2ad200PortConfigScalarsGroup,
            tnS2ad200PortConfigGroup,
            tnMsh4fsbPortConfigScalarsGroup,
            tnMsh4fsbPortConfigGroup,
            tn2ux200PortConfigScalarsGroup,
            tn2ux200PortConfigGroup,
            tn4mx200PortConfigScalarsGroup,
            tn4mx200PortConfigGroup,
            tnOpsb5PortConfigScalarsGroup,
            tnOpsb5PortConfigGroup,
            tnAswglPortConfigScalarsGroup,
            tnAswglPortConfigGroup,
            tnIpreampPortConfigScalarsGroup,
            tnIpreampPortConfigGroup,
--            obsolete
--            tn40cx800PortConfigScalarsGroup,
--            tn40cx800PortConfigGroup,
            tnIrdm32PortConfigScalarsGroup,
            tnIrdm32PortConfigGroup,
            tnRa4pPortConfigScalarsGroup,
            tnRa4pPortConfigGroup,
            tnEilaPortConfigScalarsGroup,
            tnEilaPortConfigGroup,
--            obsolete
--            tn8cx800PortConfigScalarsGroup,
--            tn8cx800PortConfigGroup,
--            tn6px800PortConfigScalarsGroup,
--            tn6px800PortConfigGroup,
            tnMcs16x15PortConfigScalarsGroup,
            tnMcs16x15PortConfigGroup,
            tn10an1tPortConfigScalarsGroup,
            tn10an1tPortConfigGroup,
            tn8uc1tPortConfigScalarsGroup,
            tn8uc1tPortConfigGroup,
            tnDfc12PortConfigScalarsGroup,
            tnDfc12PortConfigGroup,
            tnIrdm32lPortConfigScalarsGroup,
            tnIrdm32lPortConfigGroup,
            tnS4x400PortConfigScalarsGroup,
            tnS4x400PortConfigGroup,
            tnTPS24PS1PortConfigScalarsGroup,
            tnTPS24PS1PortConfigGroup,
            tnTPS24PS2PortConfigScalarsGroup,
            tnTPS24PS2PortConfigGroup,
            tnTPS12PSPortConfigScalarsGroup,
            tnTPS12PSPortConfigGroup,
            tnEsrePortConfigScalarsGroup,
            tnEsrePortConfigGroup,
            tnGenericOtPortConfigScalarsGroup,
            tnGenericOtPortConfigGroup,
            tn1ety100PortConfigScalarsGroup,
            tn1ety100PortConfigGroup,
--            obsolete
--            tnD1ad400qPortConfigScalarsGroup,
--            tnD1ad400qPortConfigGroup,
            tnOmdclPortConfigScalarsGroup,
            tnOmdclPortConfigGroup,
            tnMcs16x15lPortConfigScalarsGroup,
            tnMcs16x15lPortConfigGroup,
            tnEilalPortConfigScalarsGroup,
            tnEilalPortConfigGroup,
            tnRa5pbPortConfigScalarsGroup,
            tnRa5pbPortConfigGroup,
            tnMlfsbPortConfigScalarsGroup,
            tnMlfsbPortConfigGroup,
            tnPortLptConfigScalarsGroup,
            tnPortLptConfigGroup,
            tnPortConfigScalarsGroup,
            tnPortConfigGroup,
            tn18P400PortConfigScalarsGroup,
            tn18P400PortConfigGroup,
            tn4uc1tPortConfigScalarsGroup,
            tn4uc1tPortConfigGroup,
            tnAsgPortConfigScalarsGroup,
            tnAsgPortConfigGroup,
            tn12p120sPortConfigScalarsGroup,
            tn12p120sPortConfigGroup,
            tn16p200PortConfigScalarsGroup,
            tn16p200PortConfigGroup,
            tnIr9PortConfigScalarsGroup,
            tnIr9PortConfigGroup,
            tnMxn824PortConfigScalarsGroup,
            tnMxn824PortConfigGroup,
            tnAsc4PortConfigScalarsGroup,
            tnAsc4PortConfigGroup,
            tn5mx500PortConfigScalarsGroup,
            tn5mx500PortConfigGroup,
            tn2ux500PortConfigScalarsGroup,
            tn2ux500PortConfigGroup,
            tnMxnPortConfigScalarsGroup,
            tnMxnPortConfigGroup,
            tnAscPortConfigScalarsGroup,
            tnAscPortConfigGroup,
            tnOpsumPortConfigScalarsGroup,
            tnOpsumPortConfigGroup,
            tnMxn1624PortConfigScalarsGroup,
            tnMxn1624PortConfigGroup,
            tnIr4PortConfigScalarsGroup,
            tnIr4PortConfigGroup,
            tnAsc2PortConfigScalarsGroup,
            tnAsc2PortConfigGroup,
            tnFwPortModuleScalarsGroup,
            tnFwPortModuleGroup,
            tnSfd48PortConfigScalarsGroup,
            tnSfd48PortConfigGroup,
            tnSfd64PortConfigScalarsGroup,
            tnSfd64PortConfigGroup,
            tnIr32AWPortConfigScalarsGroup,
            tnIr32AWPortConfigGroup,
            tnEilaAWPortConfigScalarsGroup,
            tnEilaAWPortConfigGroup,
            tn18ce300PortConfigScalarsGroup,
            tn18ce300PortConfigGroup,
            tnGnssModuleScalarsGroup,
            tnGnssModuleGroup,
            tnOpsumlPortConfigScalarsGroup,
            tnOpsumlPortConfigGroup
        }
        ::= { tnOpticalPortConfigCompliances 1 }

--------------------------------------------------------------------------------
-- Compliance Port Info Statements (mandatory)
--------------------------------------------------------------------------------
    tnOpticalPortInfoCompliance MODULE-COMPLIANCE
        STATUS         current
        DESCRIPTION    "."
        MODULE
        MANDATORY-GROUPS {
            tnSdhPortInfoScalarsGroup,
            tnSdhPortInfoGroup,
--            obsolete
--            tnOC48STM16PortInfoScalarsGroup,
--            tnOC48STM16PortInfoGroup,
--            tnOC192STM64PortInfoScalarsGroup,
--            tnOC192STM64PortInfoGroup,
--            tnQuadOC48STM16MuxPortInfoScalarsGroup,
--            tnQuadOC48STM16MuxPortInfoGroup,
--            tnQuadOC3or12STM1or4MuxPortInfoScalarsGroup,
--            tnQuadOC3or12STM1or4MuxPortInfoGroup,
--            tnBandFilterPortInfoScalarsGroup,
--            tnBandFilterPortInfoGroup,
            tnOscPortInfoScalarsGroup,
            tnOscPortInfoGroup,
--            obsolete
--            tnChFilterPortInfoScalarsGroup,
--            tnChFilterPortInfoGroup,
--            tnChAddDropPortInfoScalarsGroup,
--            tnChAddDropPortInfoGroup,
--            tnBbaHgPortInfoScalarsGroup,
--            tnBbaHgPortInfoGroup,
--            tnBbaLgPortInfoScalarsGroup,
--            tnBbaLgPortInfoGroup,
--            tnPpsPortInfoScalarsGroup,
--            tnPpsPortInfoGroup,
--            tnDualGigEMuxPortInfoScalarsGroup,
--            tnDualGigEMuxPortInfoGroup,
--            tnRoadmPortInfoScalarsGroup,
--            tnRoadmPortInfoGroup,
--            tn10GigELANPortInfoScalarsGroup,
--            tn10GigELANPortInfoGroup,
            tnDcmPortInfoScalarsGroup,
            tnDcmPortInfoGroup,
--            obsolete
--            tnDecaGigEMuxPortInfoScalarsGroup,
--            tnDecaGigEMuxPortInfoGroup,
            tnSonetPortInfoScalarsGroup,
            tnSonetPortInfoGroup,
--            obsolete
--            tnExternalDcuPortInfoScalarsGroup,
--            tnExternalDcuPortInfoGroup,
            tnDigitalWrapperPortInfoScalarsGroup,
            tnDigitalWrapperPortInfoGroup,
--            obsolete
--            tnMsaHgPortInfoScalarsGroup,
--            tnMsaHgPortInfoGroup,
--            tnWssX9PortInfoScalarsGroup,
--            tnWssX9PortInfoGroup,
            tnSfpPortInfoScalarsGroup,
            tnSfpPortInfoGroup,
--            obsolete
--            tn1xMR2dot5GPortInfoScalarsGroup,
--            tn1xMR2dot5GPortInfoGroup,
            tnNetworkPortInfoScalarsGroup,
            tnNetworkPortInfoGroup,
            tnOpsaPortInfoScalarsGroup,
            tnOpsaPortInfoGroup,
            tn11stmm10PortInfoScalarsGroup,
            tn11stmm10PortInfoGroup,
            tn11star1PortInfoScalarsGroup,
            tn11star1PortInfoGroup,
            tnAhphgPortInfoScalarsGroup,
            tnAhphgPortInfoGroup,
            tnAlphgPortInfoScalarsGroup,
            tnAlphgPortInfoGroup,
            tnCwr8PortInfoScalarsGroup,
            tnCwr8PortInfoGroup,
            tn11stge12PortInfoScalarsGroup,
            tn11stge12PortInfoGroup,
            tn11dpge12PortInfoScalarsGroup,
            tn11dpge12PortInfoGroup,
--            obsolete
--            tnDwdmGpPhyPortInfoGroup,
            tnDwdmCmnLinePortInfoGroup,
            tnDwdmCmnClientPortInfoGroup,
            tnRsmonIngrPortInfoGroup,
            tnOtPortInfoGroup,
            tnWaveKeyPortInfoGroup,
            tnOmdPortInfoGroup,
            tn4dpa4PortInfoScalarsGroup,
            tn4dpa4PortInfoGroup,
            tnCwr8c88PortInfoScalarsGroup,
            tnCwr8c88PortInfoGroup,
            tnAhplgPortInfoScalarsGroup,
            tnAhplgPortInfoGroup,
            tnTimeSlotLinePortInfoGroup,
            tnDwdmCmnOtu1Odu1LinePortInfoGroup,
            tnDwdmCmnOtu1Odu1ClientPortInfoGroup,
            tn43stx4PortInfoScalarsGroup,
            tn43stx4PortInfoGroup,
            tnDwdmCmnOtu3Odu3LinePortInfoGroup,
            tnAlpfgkPortInfoScalarsGroup,
            tnAlpfgkPortInfoGroup,
            tn4dpa2PortInfoScalarsGroup,
            tn4dpa2PortInfoGroup,
            tn43sta1pPortInfoScalarsGroup,
            tn43sta1pPortInfoGroup,
            tn43stx4pPortInfoScalarsGroup,
            tn43stx4pPortInfoGroup,
            tnRsmonEgrPortInfoGroup,
            tnA2325aPortInfoScalarsGroup,
            tnA2325aPortInfoGroup,
            tn11qpa4PortInfoScalarsGroup,
            tn11qpa4PortInfoGroup,
            tn112scx10PortInfoScalarsGroup,
            tn112scx10PortInfoGroup,
            tn112sca1PortInfoScalarsGroup,
            tn112sca1PortInfoGroup,
            tnDwdmCmnOtu4Odu4LinePortInfoGroup,
            tnDwdmCmnOtu4Odu4ClientPortInfoGroup,
            tnAlpfgtPortInfoScalarsGroup,
            tnAlpfgtPortInfoGroup,
            tnOsctPortInfoScalarsGroup,
            tnOsctPortInfoGroup,
            tnWtocmPortInfoScalarsGroup,
            tnWtocmPortInfoGroup,
            tnWr2c88PortInfoScalarsGroup,
            tnWr2c88PortInfoGroup,
            tnAm2017bPortInfoScalarsGroup,
            tnAm2017bPortInfoGroup,
            tnAm2325bPortInfoScalarsGroup,
            tnAm2325bPortInfoGroup,
            tn1dpp21PortInfoScalarsGroup,
            tn1dpp21PortInfoGroup,
--            obsolete
--            tnE1T1PortInfoGroup,
            tnMvacPortInfoScalarsGroup,
            tnMvacPortInfoGroup,
            tn43scx4PortInfoScalarsGroup,
            tn43scx4PortInfoGroup,
            tnRa2pPortInfoScalarsGroup,
            tnRa2pPortInfoGroup,
            tnAm2318aPortInfoScalarsGroup,
            tnAm2318aPortInfoGroup,
            tnAm2125aPortInfoScalarsGroup,
            tnAm2125aPortInfoGroup,
            tnWr8c88aPortInfoScalarsGroup,
            tnWr8c88aPortInfoGroup,
            tn11dpe12ePortInfoScalarsGroup,
            tn11dpe12ePortInfoGroup,
            tn112sx10lPortInfoScalarsGroup,
            tn112sx10lPortInfoGroup,
            tn112sa1lPortInfoScalarsGroup,
            tn112sa1lPortInfoGroup,
            tn11dpm12PortInfoScalarsGroup,
            tn11dpm12PortInfoGroup,
            tnRamanPortInfoGroup,
            tnMesh4PortInfoScalarsGroup,
            tnMesh4PortInfoGroup,
--            obsolete
--            tnTcmPortInfoScalarsGroup,
--            tnTcmPortInfoGroup,
            tn43sca1PortInfoScalarsGroup,
            tn43sca1PortInfoGroup,
            tn43scx4lPortInfoScalarsGroup,
            tn43scx4lPortInfoGroup,
            tnAm2125bPortInfoScalarsGroup,
            tnAm2125bPortInfoGroup,
            tn112snx10PortInfoScalarsGroup,
            tn112snx10PortInfoGroup,
            tn112sna1PortInfoScalarsGroup,
            tn112sna1PortInfoGroup,
--            obsolete
--            tn11qta4PortInfoScalarsGroup,
--            tn11qta4PortInfoGroup,
            tn1dpp24mPortInfoScalarsGroup,
            tn1dpp24mPortInfoGroup,
            tnDwdmCmnOtu3Odu3ClientPortInfoGroup,
            tnul43scupPortInfoScalarsGroup,
            tnul43scupPortInfoGroup,
            tnul11qcupPortInfoScalarsGroup,
            tnul11qcupPortInfoGroup,
            tn11qpen4PortInfoScalarsGroup,
            tn11qpen4PortInfoGroup,
            tn43scx4ePortInfoScalarsGroup,
            tn43scx4ePortInfoGroup,
            tnWssAttenPortInfoScalarsGroup,
            tnWssAttenPortInfoGroup,
            tn43scge1PortInfoScalarsGroup,
            tn43scge1PortInfoGroup,
            tn11qpe24PortInfoScalarsGroup,
            tn11qpe24PortInfoGroup,
            tn11star1aPortInfoScalarsGroup,
            tn11star1aPortInfoGroup,
            tnMvac8bPortInfoScalarsGroup,
            tnMvac8bPortInfoGroup,
            tnWr8c88afPortInfoScalarsGroup,
            tnWr8c88afPortInfoGroup,
            tncl10an10gPortInfoScalarsGroup,
            tncl10an10gPortInfoGroup,
            tncl24anmPortInfoScalarsGroup,
            tncl24anmPortInfoGroup,
            tnOpsbPortInfoScalarsGroup,
            tnOpsbPortInfoGroup,
            tnOpsPortInfoScalarsGroup,
            tnOpsPortInfoGroup,
            tn11dpe12aPortInfoScalarsGroup,
            tn11dpe12aPortInfoGroup,
            tnul130scupPortInfoScalarsGroup,
            tnul130scupPortInfoGroup,
            tn130scx10PortInfoScalarsGroup,
            tn130scx10PortInfoGroup,
            tnA2p2125PortInfoScalarsGroup,
            tnA2p2125PortInfoGroup,
            tn4qpa8PortInfoScalarsGroup,
            tn4qpa8PortInfoGroup,
            tnOt112pdm11PortInfoScalarsGroup,
            tnOt112pdm11PortInfoGroup,
            tnWtocmaPortInfoScalarsGroup,
            tnWtocmaPortInfoGroup,
            tnPtpctlPortInfoScalarsGroup,
            tnPtpctlPortInfoGroup,
            tnPtpioPortInfoScalarsGroup,
            tnPtpioPortInfoGroup,
            tnIo24et1gbPortInfoScalarsGroup,
            tnIo24et1gbPortInfoGroup,
            tnIo4an10gPortInfoScalarsGroup,
            tnIo4an10gPortInfoGroup,
            tnIo8et1gbPortInfoScalarsGroup,
            tnIo8et1gbPortInfoGroup,
            tnIo10et10gPortInfoScalarsGroup,
            tnIo10et10gPortInfoGroup,
            tnUl11qcupcPortInfoScalarsGroup,
            tnUl11qcupcPortInfoGroup,
            tnOt520scx4PortInfoScalarsGroup,
            tnOt520scx4PortInfoGroup,
            tnSkewInfoGroup,
            tnPowerFilterPortInfoScalarsGroup,
            tnPowerFilterPortInfoGroup,
            tn11ope8PortInfoScalarsGroup,
            tn11ope8PortInfoGroup,
            tn11qce12xPortInfoScalarsGroup,
            tn11qce12xPortInfoGroup,
            tnAm2625aPortInfoScalarsGroup,
            tnAm2625aPortInfoGroup,
            tnAm2032aPortInfoScalarsGroup,
            tnAm2032aPortInfoGroup,
            tnOt260scx2PortInfoScalarsGroup,
            tnOt260scx2PortInfoGroup,
            tnOt130snx10PortInfoScalarsGroup,
            tnOt130snx10PortInfoGroup,
            tnIo24anmbPortInfoScalarsGroup,
            tnIo24anmbPortInfoGroup,
            tnOt11dpm8PortInfoScalarsGroup,
            tnOt11dpm8PortInfoGroup,
            tnOt11dpm4mPortInfoScalarsGroup,
            tnOt11dpm4mPortInfoGroup,
            tnUl130scupbPortInfoScalarsGroup,
            tnUl130scupbPortInfoGroup,
            tnOt112sdx11PortInfoScalarsGroup,
            tnOt112sdx11PortInfoGroup,
            tnAa2donwPortInfoScalarsGroup,
            tnAa2donwPortInfoGroup,
            tnOt130sca1PortInfoScalarsGroup,
            tnOt130sca1PortInfoGroup,
            tnIo10an10gbPortInfoScalarsGroup,
            tnIo10an10gbPortInfoGroup,
            tnIo10et10gbPortInfoScalarsGroup,
            tnIo10et10gbPortInfoGroup,
            tnWr20tfPortInfoScalarsGroup,
            tnWr20tfPortInfoGroup,
            tnWssPortInfoScalarsGroup,
            tnWssPortInfoGroup,
            tnWtocmfPortInfoScalarsGroup,
            tnWtocmfPortInfoGroup,
            tnAswgPortInfoScalarsGroup,
            tnAswgPortInfoGroup,
            tnA4pswgPortInfoScalarsGroup,
            tnA4pswgPortInfoGroup,
            tnOtdrPortInfoScalarsGroup,
            tnOtdrPortInfoGroup,
            tnWr20tfmPortInfoScalarsGroup,
            tnWr20tfmPortInfoGroup,
            tnAar8aPortInfoScalarsGroup,
            tnAar8aPortInfoGroup,
            tnMcs8x16PortInfoScalarsGroup,
            tnMcs8x16PortInfoGroup,
            tnMsh8fsmPortInfoScalarsGroup,
            tnMsh8fsmPortInfoGroup,
            tnMcsPortInfoScalarsGroup,
            tnMcsPortInfoGroup,
            tnMcsPortChannelInfoScalarsGroup,
            tnMcsPortChannelInfoGroup,
            tnAarPortInfoScalarsGroup,
            tnAarPortInfoGroup,
            tnWr20tfmPortChannelInfoScalarsGroup,
            tnWr20tfmPortChannelInfoGroup,
            tnMpoPortInfoScalarsGroup,
            tnMpoPortInfoGroup,
            tnMpoPortMultiPositionScalarsGroup,
            tnMpoPortMultiPositionInfoGroup,
            tnIo4an100gPortInfoScalarsGroup,
            tnIo4an100gPortInfoGroup,
            tnIo30an10gPortInfoScalarsGroup,
            tnIo30an10gPortInfoGroup,
            tnIo30an300PortInfoScalarsGroup,
            tnIo30an300PortInfoGroup,
            tnIo4an400PortInfoScalarsGroup,
            tnIo4an400PortInfoGroup,
            tn12p120PortInfoScalarsGroup,
            tn12p120PortInfoGroup,
            tn20p200PortInfoScalarsGroup,
            tn20p200PortInfoGroup,
            tn1ud200PortInfoScalarsGroup,
            tn1ud200PortInfoGroup,
            tnOt130snq10PortInfoScalarsGroup,
            tnOt130snq10PortInfoGroup,
            tnIroadmvPortInfoScalarsGroup,
            tnIroadmvPortInfoGroup,
            tnIroadmfPortInfoScalarsGroup,
            tnIroadmfPortInfoGroup,
            tnIroadmPortInfoScalarsGroup,
            tnIroadmPortInfoGroup,
            tnIroadmPortChannelInfoScalarsGroup,
            tnIroadmPortChannelInfoGroup,
            tnWssRefLdInfoScalarsGroup,
            tnWssRefLdInfoGroup,
            tnMonOcmPortInfoScalarsGroup,
            tnMonOcmPortInfoGroup,
            tnUl2uc400PortInfoScalarsGroup,
            tnUl2uc400PortInfoGroup,
            tnUl4uc400PortInfoScalarsGroup,
            tnUl4uc400PortInfoGroup,
            tnUl20uc200PortInfoScalarsGroup,
            tnUl20uc200PortInfoGroup,
            tnD5x500PortInfoScalarsGroup,
            tnD5x500PortInfoGroup,
            tnOtS11M100PortInfoScalarsGroup,
            tnOtS11M100PortInfoGroup,
            tnMonOtdrPortInfoScalarsGroup,
            tnMonOtdrPortInfoGroup,
            tnPSS96PowerFilterPortInfoScalarsGroup,
            tnPSS96PowerFilterPortInfoGroup,
            tn12ce120PortInfoScalarsGroup,
            tn12ce120PortInfoGroup,
            tn1ce100PortInfoScalarsGroup,
            tn1ce100PortInfoGroup,
            tnLcI1000PortInfoScalarsGroup,
            tnLcI1000PortInfoGroup,
            tnAwbegrPortInfoScalarsGroup,
            tnAwbegrPortInfoGroup,
            tnAwbingPortInfoScalarsGroup,
            tnAwbingPortInfoGroup,
            tnAwbilaPortInfoScalarsGroup,
            tnAwbilaPortInfoGroup,
            tnRa5pPortInfoScalarsGroup,
            tnRa5pPortInfoGroup,
            tnIroadm9mPortInfoScalarsGroup,
            tnIroadm9mPortInfoGroup,
            tnS13x100PortInfoScalarsGroup,
            tnS13x100PortInfoGroup,
            tn12ce121PortInfoScalarsGroup,
            tn12ce121PortInfoGroup,
            tnPtpioctlPortInfoScalarsGroup,
            tnPtpioctlPortInfoGroup,
            tnAa2donwbPortInfoScalarsGroup,
            tnAa2donwbPortInfoGroup,
            tnOsctaprPortInfoScalarsGroup,
            tnOsctaprPortInfoGroup,
            tn11qpa4bPortInfoScalarsGroup,
            tn11qpa4bPortInfoGroup,
            tn1ux100PortInfoScalarsGroup,
            tn1ux100PortInfoGroup,
            tn20ax200PortInfoScalarsGroup,
            tn20ax200PortInfoGroup,
            tn20mx80PortInfoScalarsGroup,
            tn20mx80PortInfoGroup,
            tnAar2x8aPortInfoScalarsGroup,
            tnAar2x8aPortInfoGroup,
            tnS13x100ePortInfoScalarsGroup,
            tnS13x100ePortInfoGroup,
            tnWtocmflPortInfoScalarsGroup,
            tnWtocmflPortInfoGroup,
            tnAar2x8alPortInfoScalarsGroup,
            tnAar2x8alPortInfoGroup,
            tnWr20tfmlPortInfoScalarsGroup,
            tnWr20tfmlPortInfoGroup,
            tnMcs8x16lPortInfoScalarsGroup,
            tnMcs8x16lPortInfoGroup,
            tnPSS8xPowerFilterPortInfoScalarsGroup,
            tnPSS8xPowerFilterPortInfoGroup,
            tnLcI2000PortInfoScalarsGroup,
            tnLcI2000PortInfoGroup,
            tn30se300PortInfoScalarsGroup,
            tn30se300PortInfoGroup,
            tn6se300PortInfoScalarsGroup,
            tn6se300PortInfoGroup,
            tnOtdrwbPortInfoScalarsGroup,
            tnOtdrwbPortInfoGroup,
            tn8dc30tPortInfoScalarsGroup,
            tn8dc30tPortInfoGroup,
            tn16dc65tPortInfoScalarsGroup,
            tn16dc65tPortInfoGroup,
            tnD5x500lPortInfoScalarsGroup,
            tnD5x500lPortInfoGroup,
            tnLcI2000lPortInfoScalarsGroup,
            tnLcI2000lPortInfoGroup,
            tnIroadm9rPortInfoScalarsGroup,
            tnIroadm9rPortInfoGroup,
            tnRa2p96PortInfoScalarsGroup,
            tnRa2p96PortInfoGroup,
            tnOtdrmPortInfoScalarsGroup,
            tnOtdrmPortInfoGroup,
            tnEthToTDMPortAssocInfoScalarsGroup,
            tnEthToTDMPortAssocInfoGroup,
            tn20an80PortInfoScalarsGroup,
            tn20an80PortInfoGroup,
            tn10an400PortInfoScalarsGroup,
            tn10an400PortInfoGroup,
            tn8p20PortInfoScalarsGroup,
            tn8p20PortInfoGroup,
            tnOpsflexPortInfoScalarsGroup,
            tnOpsflexPortInfoGroup,
            tnD5x500qPortInfoScalarsGroup,
            tnD5x500qPortInfoGroup,
            tn18p40PortInfoScalarsGroup,
            tn18p40PortInfoGroup,
            tnDa2c4PortInfoScalarsGroup,
            tnDa2c4PortInfoGroup,
            tn130sla1PortInfoScalarsGroup,
            tn130sla1PortInfoGroup,
            tn130slx10PortInfoScalarsGroup,
            tn130slx10PortInfoGroup,
            tnPSS12xPowerFilterPortInfoScalarsGroup,
            tnPSS12xPowerFilterPortInfoGroup,
            tnIroadm20PortInfoScalarsGroup,
            tnIroadm20PortInfoGroup,
            tnS2ad200PortInfoScalarsGroup,
            tnS2ad200PortInfoGroup,
            tnMsh4fsbPortInfoScalarsGroup,
            tnMsh4fsbPortInfoGroup,
            tn2ux200PortInfoScalarsGroup,
            tn2ux200PortInfoGroup,
            tn4mx200PortInfoScalarsGroup,
            tn4mx200PortInfoGroup,
            tnOpsb5PortInfoScalarsGroup,
            tnOpsb5PortInfoGroup,
            tnAswglPortInfoScalarsGroup,
            tnAswglPortInfoGroup,
            tnIpreampPortInfoScalarsGroup,
            tnIpreampPortInfoGroup,
--            obsolete
--            tn40cx800PortInfoScalarsGroup,
--            tn40cx800PortInfoGroup,
            tnIrdm32PortInfoScalarsGroup,
            tnIrdm32PortInfoGroup,
            tnRa4pPortInfoScalarsGroup,
            tnRa4pPortInfoGroup,
            tnEilaPortInfoScalarsGroup,
            tnEilaPortInfoGroup,
--            obsolete
--            tn8cx800PortInfoScalarsGroup,
--            tn8cx800PortInfoGroup,
--            tn6px800PortInfoScalarsGroup,
--            tn6px800PortInfoGroup,
            tnMcs16x15PortInfoScalarsGroup,
            tnMcs16x15PortInfoGroup,
            tn10an1tPortInfoScalarsGroup,
            tn10an1tPortInfoGroup,
            tn8uc1tPortInfoScalarsGroup,
            tn8uc1tPortInfoGroup,
            tnDfc12PortInfoScalarsGroup,
            tnDfc12PortInfoGroup,
            tnIrdm32lPortInfoScalarsGroup,
            tnIrdm32lPortInfoGroup,
            tnS4x400PortInfoScalarsGroup,
            tnS4x400PortInfoGroup,
            tnTPS24PS1PortInfoScalarsGroup,
            tnTPS24PS1PortInfoGroup,
            tnTPS24PS2PortInfoScalarsGroup,
            tnTPS24PS2PortInfoGroup,
            tnTPS12PSPortInfoScalarsGroup,
            tnTPS12PSPortInfoGroup,
            tnEsrePortInfoScalarsGroup,
            tnEsrePortInfoGroup,
            tnGenericOtPortInfoScalarsGroup,
            tnGenericOtPortInfoGroup,
            tn1ety100PortInfoScalarsGroup,
            tn1ety100PortInfoGroup,
--            obsolete
--            tnD1ad400qPortInfoScalarsGroup,
--            tnD1ad400qPortInfoGroup,
            tnOmdclPortInfoScalarsGroup,
            tnOmdclPortInfoGroup,
            tnMcs16x15lPortInfoScalarsGroup,
            tnMcs16x15lPortInfoGroup,
            tnEilalPortInfoScalarsGroup,
            tnEilalPortInfoGroup,
            tnRa5pbPortInfoScalarsGroup,
            tnRa5pbPortInfoGroup,
            tnMlfsbPortInfoScalarsGroup,
            tnMlfsbPortInfoGroup,
            tnPortLptInfoScalarsGroup,
            tnPortLptInfoGroup,
            tnPortInfoScalarsGroup,
            tnPortInfoGroup,
            tn18P400PortInfoScalarsGroup,
            tn18P400PortInfoGroup,
            tn4uc1tPortInfoScalarsGroup,
            tn4uc1tPortInfoGroup,
            tnAsgPortInfoScalarsGroup,
            tnAsgPortInfoGroup,
            tn12p120sPortInfoScalarsGroup,
            tn12p120sPortInfoGroup,
            tn16p200PortInfoScalarsGroup,
            tn16p200PortInfoGroup,
            tnIr9PortInfoScalarsGroup,
            tnIr9PortInfoGroup,
            tnMxn824PortInfoScalarsGroup,
            tnMxn824PortInfoGroup,
            tnAsc4PortInfoScalarsGroup,
            tnAsc4PortInfoGroup,
            tn5mx500PortInfoScalarsGroup,
            tn5mx500PortInfoGroup,
            tn2ux500PortInfoScalarsGroup,
            tn2ux500PortInfoGroup,
            tnMxnPortChannelInfoScalarsGroup,
            tnMxnPortChannelInfoGroup,
            tnMxnPortInfoScalarsGroup,
            tnMxnPortInfoGroup,
            tnAscPortInfoScalarsGroup,
            tnAscPortInfoGroup,
            tnOpsumPortInfoScalarsGroup,
            tnOpsumPortInfoGroup,
            tnMxn1624PortInfoScalarsGroup,
            tnMxn1624PortInfoGroup,
            tnIr4PortInfoScalarsGroup,
            tnIr4PortInfoGroup,
            tnAsc2PortInfoScalarsGroup,
            tnAsc2PortInfoGroup,
            tnSfd48PortInfoScalarsGroup,
            tnSfd48PortInfoGroup,
            tnSfd64PortInfoScalarsGroup,
            tnSfd64PortInfoGroup,
            tnIr32AWPortInfoScalarsGroup,
            tnIr32AWPortInfoGroup,
            tnEilaAWPortInfoScalarsGroup,
            tnEilaAWPortInfoGroup,
            tn18ce300PortInfoScalarsGroup,
            tn18ce300PortInfoGroup,
            tnOpsumlPortInfoScalarsGroup,
            tnOpsumlPortInfoGroup
        }
        ::= { tnOpticalPortInfoCompliances 1 }

--------------------------------------------------------------------------------
-- Compliance Port Line Card Config Statements (mandatory)
--------------------------------------------------------------------------------
--    obsolete
--    tnOpticalPortLcConfigCompliance MODULE-COMPLIANCE ::= { tnOpticalPortLcConfigCompliances 1 }

END -- DEFINITION OF TROPIC-OPTICALPORT-MIB
