-- "CONFIDENTIAL. All rights reserved. Alcatel. This computer program is protected under Copyright.
-- Recipient is to retain the program in confidence, and is not permitted to copy, use, distribute, modify or
-- translate the program without authorization. Passing on and copying,use and communication of its
-- contents is not permitted without written authorization."

    OPTICSIM-ETHPM-MIB DEFINITIONS ::= BEGIN

        IMPORTS
            ifIndex
                FROM IF-MIB
            OpticsIMPmRetrievingTime, OpticsIMPmLastDiscontinuityTimeStamp,
                        OpticsIMPmStartTime, OpticsIMPmElapsedTime,
                        OpticsIMPmGranularityPeriod, OpticsIMPmIndex,
            OpticsIMPmPeriodTime, OpticsIMPmSuspectIntervalFlag
                FROM OPTICSIM-COMMON-TC
            opticsimEthMib, opticsimEthMC
                FROM OPTICSIM-ETHREG-MIB
            opticsIMETSInFlowIndex, opticsIMETSOutFlowIndex,
                        OpticsIMETSTrafficDescrType
                FROM OpticsIMETS-MIB
            Counter64, Integer32, Gauge32, OBJECT-TYPE, MODULE-IDENTITY,
                Unsigned32  FROM SNMPv2-SMI
            TruthValue, RowStatus
                FROM SNMPv2-TC
            OpticsIMPmThresholdDataInstance FROM OPTICSIM-COMMON-TC
            opticsIMaclIndex,opticsIMaclMacAceIndex FROM OPTICSIM-ETHNE-MIB
            TsdimManagerType
                FROM TSDIM-SNMP-TC;


        opticsIMEthPmMib MODULE-IDENTITY

            LAST-UPDATED "1401060000Z"
                 ORGANIZATION
                                "Alcatel OND"
                 CONTACT-INFO
                                "Alcatel OND"

            DESCRIPTION
              "OPDnm15848: Linhai Qiu
               -Added ethAclCDRxTable,ethAclHDRxTable,ethAclCDRxThresholdIndexNext,
               ethAclCDRxThresholdTable
               -Added ethAclCDRxTableObjectsGroup,ethAclHDRxTableObjectsGroup,
                ethAclCDRxThresholdTableObjectsGroup group tables"

            REVISION "1206080000Z"
            DESCRIPTION
               "OPTnm04645: D.Spreafico.
                Added : - ethAggrPerQueueMaintCompressedTCO to ethAggrPerQueueMaintTable
                        - ethAggrMaintCompressedTxTTO  to ethAggrMaintTxTable
               "

            REVISION "1007200000Z"
            DESCRIPTION
              "TSDnm96143: P.Villa.
               Added enhEtsInFlowCDElapsedTime enhEtsOutFlowCDElapsedTime,
                          enhEtsInFlowHDElapsedTime enhEtsOutFlowHDElapsedTime  "


            REVISION "1005200000Z"
            DESCRIPTION
              "TSDnm92784: P.Villa.
               Addition of Counter64 attributes inside both EnhEthAggrCDThresholdEntry
               and EnhEtsFlowCDThresholdEntry"

            REVISION "1002050000Z"
            DESCRIPTION
          "D.Spreafico (TSDnm91853):
           - Added enhEthAggrPerQueueCDTable and enhEthAggrPerQueueHDTable
               - added thresholds on enhEthAggrCDThresholdTable related to the following counters:
                     RxEINBRate, RxEINBRatio, RxEIFERatio, RxTDFRatio, TxEONBRate, TxEONBRatio, TxTDFRatio"

            REVISION "1002050000Z"
            DESCRIPTION
          "S.Torassa (TSDnm77175):
           the etsOutFlowMaintReset MAX-ACCESS as been changed to read-write"

            REVISION "0912170000Z"
            DESCRIPTION
                "Added attribute etsInFlowMaintReset to etsInFlowMaintTable
         Added attribute etsOutFlowMaintReset to etsOutFlowMaintTable
         Added attribute enhEthAggrCDRxThresholdDataInstance  to enhEthAggrCDRxTable,
                 Added attribute enhEthAggrCDTxThresholdDataInstance  to enhEthAggrCDTxTable
                 Added attribute enhEtsInFlowCDThresholdDataInstance  to enhEtsInFlowCDTable
                 Added attribute enhEtsOutFlowCDThresholdDataInstance to enhEtsOutFlowCDTable
                 Added enhEthAggrCDThresholdIndexNext and enhEthAggrCDThresholdTable
                 Added enhEtsFlowCDThresholdIndexNext and enhEtsFlowCDThresholdTable
         Added new objects for enhanced PM tables:
            - enhEthAggrCDRxTable, enhEthAggrHDRxTable:  EINBRate, EINBRatio, EIFERatio, TDFRatio

            - enhEthAggrCDTxTable, enhEthAggrHDTxTable:  EONBRate, EONBRatio, TDFRatio
                "

            REVISION "0904230000Z"
                DESCRIPTION
                    "Added new objects for enhanced PM tables:
                     - enhEthAggrHDRxTable, enhEthAggrHDTxTable,
                       enhEthAggrCDRxTable, enhEthAggrCDTxTable

                     Added new objects for resetting PM counters per flow:
                     - etsInFlowCDResetCounter
                     - etsOutFlowCDResetCounter
                     "

            REVISION "0902190000Z"
            DESCRIPTION
                    "Added new objects for enhanced PM counters:
                     - enhEthAggrHDRxTable, enhEthAggrHDTxTable,
                       enhEthAggrCDRxTable, enhEthAggrCDTxTable
                     - enhEtsInFlowHDTable, enhEtsInFlowCDTable
                       enhEtsOutFlowHDTable,enhEtsOutFlowCDTable

                     Added new object PM Counters: ethAggrMaintRxReset and ethAggrMaintTxReset
                     "

            REVISION "0807280000Z"
                DESCRIPTION
                    " Linhai Qiu
                    (1) Added new object for enhEthAggrCDRxTable:
                               enhEthAggrCDRxTDF,
                    (2) Added new object for enhEthAggrHDRxTable:
                               enhEthAggrHDRxTDF,
                    (2) Added new table  enhEthAggrMaintTxTable and  enhEthAggrMaintRxTable
                     "

            REVISION "0707190000Z"
                DESCRIPTION
                    "Added new  objects for resetting PM counters:
                                       ethAggrCDRxResetCounter,
                       ethAggrCDTxResetCounter
                     Added new  tables for collecting aggregate, per queue PM
                     counters:
                                       ethAggrPerQueueCDTable,
                       ethAggrPerQueueHDTable,
                              ethAggrPerQueueMaintTable,
               . "

            REVISION "0602160000Z"
                DESCRIPTION
                    "Added new  object PM counters:
                     1) ethAggrCDRxTRCFUnicast,
                        ethAggrCDRxTRCFMulticast,
                        ethAggrCDRxTRCFBroadcast,
                        ethAggrCDRxTDF, ethAggrCDRxTRSEF to EthAggrCDRxEntry
                    2) ethAggrHDRxTRCFUnicast,
                        ethAggrHDRxTRCFMulticast,
                        ethAggrHDRxTRCFBroadcast,
                        ethAggrHDRxTDF, ethAggrHDRxTRSEF to EthAggrHDRxEntry
                    3) ethAggrCDTxTTFUnicast,
                       ethAggrCDTxTTFMulticast,
                       ethAggrCDTxTTFBroadcast,
                       ethAggrCDTxTDF to EthAggrCDTxEntry
                     4) ethAggrHDTxTTFUnicast,
                         ethAggrHDTxTTFMulticast,
                         ethAggrHDTxTTFBroadcast,
                        ethAggrHDTxTDF to EthAggrHDTxEntry
                    5) etsInFlowCDTRCFy,
                        etsInFlowCDTRCFr,
                        etsInFlowCDTRCOy,
                        etsInFlowCDTRCOr to EtsInFlowCDEntry
                     6) etsInFlowHDTRCFy,
                         etsInFlowHDTRCFr,
                        etsInFlowHDTRCOy,
                        etsInFlowHDTRCOr to EtsInFlowHDEntry
                    7) etsOutFlowCDTTFy,
                        etsOutFlowCDTTOy,
                         etsOutFlowCDTDFg,
                        etsOutFlowCDTDFy,
                        etsOutFlowCDTDOg,
                        etsOutFlowCDTDOy to EtsOutFlowCDEntry
                    8) etsOutFlowHDTTFy,
                        etsOutFlowHDTTOy,
                        etsOutFlowHDTDFg,
                        etsOutFlowHDTDFy,
                        etsOutFlowHDTDOg,
                        etsOutFlowHDTDOy to EtsOutFlowHDEntry
                    9) ethAggrMaintRxTRCFUnicast,
                       ethAggrMaintRxTRCFMulticast,
                       ethAggrMaintRxTRCFBroadcast to EthAggrMaintRxEntry
                    10) ethAggrMaintTxTTFUnicast,
                         ethAggrMaintTxTTFMulticast,
                         ethAggrMaintTxTTFBroadcast to EthAggrMaintTxEntry
                   "
           REVISION "0510270000Z"

           DESCRIPTION
                    "Added new  object
                     pmHistoryDataGranularityConfiguration "
           REVISION "0307250000Z"

            DESCRIPTION
                    "Compiler warning indication fixing
                (read-write clause in table with read-create as well is not permitted.
                It must be used read-create instead."
            REVISION "0302200000Z"
            DESCRIPTION
                "Changed CD tables: deleted granularityPeriod as index and changed startTime
                 from read-only to read-write. "
            ::= { opticsimEthMib 4 }



--
-- Node definitions
--

-- Received aggregates current datas table
        ethAggrCDRxTable OBJECT-TYPE
            SYNTAX SEQUENCE OF EthAggrCDRxEntry
            MAX-ACCESS not-accessible
            STATUS current
            DESCRIPTION
                "This table contains received aggregates Current Datas counters."
            ::= { opticsIMEthPmMib 1 }

        ethAggrCDRxEntry OBJECT-TYPE
            SYNTAX EthAggrCDRxEntry
            MAX-ACCESS not-accessible
            STATUS current
            DESCRIPTION
                "An entry of received aggregates Current Data counters table."
            INDEX { ifIndex }
            ::= { ethAggrCDRxTable 1 }

        EthAggrCDRxEntry ::=
            SEQUENCE {
                ethAggrCDRxTRCF
                    Counter64,
                ethAggrCDRxTRCO
                    Counter64,
                ethAggrCDRxLastDiscontinuityTimeStamp
                    OpticsIMPmLastDiscontinuityTimeStamp,
                ethAggrCDRxStartTime
                    OpticsIMPmStartTime,
                ethAggrCDRxStartByOS
                    TsdimManagerType,
                ethAggrCDRxRowStatus
                    RowStatus,
                ethAggrCDRxTRCFUnicast
                    Counter64,
                ethAggrCDRxTRCFMulticast
                    Counter64,
                ethAggrCDRxTRCFBroadcast
                    Counter64,
                ethAggrCDRxTDF
                    Counter64,
                ethAggrCDRxTRSEF
                    Counter64,
                ethAggrCDRxResetCounter
                    TruthValue
             }

        ethAggrCDRxTRCF OBJECT-TYPE
            SYNTAX Counter64
            MAX-ACCESS read-only
            STATUS current
            DESCRIPTION
                "The number of Ethernet frames received correctly by the Virtual Ethernet Interface."
            ::= { ethAggrCDRxEntry 2 }

        ethAggrCDRxTRCO OBJECT-TYPE
            SYNTAX Counter64
            MAX-ACCESS read-only
            STATUS current
            DESCRIPTION
                "The number of octets of Ethernet frames received correctly by the Virtual Ethernet Interface, including Ethernet headers characters"
            ::= { ethAggrCDRxEntry 3 }

        ethAggrCDRxLastDiscontinuityTimeStamp OBJECT-TYPE
            SYNTAX OpticsIMPmLastDiscontinuityTimeStamp
            MAX-ACCESS read-only
            STATUS current
            DESCRIPTION
                "See Textual Conventions."
            ::= { ethAggrCDRxEntry 6 }

        ethAggrCDRxStartTime OBJECT-TYPE
            SYNTAX OpticsIMPmStartTime
            MAX-ACCESS read-create
            STATUS current
            DESCRIPTION
                "See Textual Conventions.
                Even if it is defined as read-create, this objiect cannot be written by manager,
                but only read."
            ::= { ethAggrCDRxEntry 7 }

        ethAggrCDRxStartByOS OBJECT-TYPE
            SYNTAX TsdimManagerType
            MAX-ACCESS read-only
            STATUS current
            DESCRIPTION
                "See Textual Conventions"
            ::= { ethAggrCDRxEntry 8 }

        ethAggrCDRxRowStatus OBJECT-TYPE
            SYNTAX RowStatus
            MAX-ACCESS read-create
            STATUS current
            DESCRIPTION
                "See Textual Conventions"
            ::= { ethAggrCDRxEntry 9 }


        ethAggrCDRxTRCFUnicast OBJECT-TYPE
            SYNTAX Counter64
            MAX-ACCESS read-only
            STATUS current
            DESCRIPTION
              "The number of Ethernet Unicast frames received correctly by the Virtual Ethernet Interface."
            ::= { ethAggrCDRxEntry 10 }

        ethAggrCDRxTRCFMulticast OBJECT-TYPE
            SYNTAX Counter64
            MAX-ACCESS read-only
            STATUS current
            DESCRIPTION
             "The total number of good packets received that were directed to a multicast address.
               Note that this number does not include packets directed to the broadcast address. This behavior is the same
               performed by the counter etherStatsMulticastPkts in the IETF RMON-MIB published as RFC 2819"
            ::= { ethAggrCDRxEntry 11 }

        ethAggrCDRxTRCFBroadcast OBJECT-TYPE
            SYNTAX Counter64
            MAX-ACCESS read-only
            STATUS current
            DESCRIPTION
             "The total number of good packets received that were directed to the broadcast address.
                Note that this does not include multicast packets.
                This behavior is the same performed by the counter etherStatsBroadcastPkts in the IETF RMON-MIB published as RFC 2819"
            ::= { ethAggrCDRxEntry 12 }

        ethAggrCDRxTDF OBJECT-TYPE
            SYNTAX Counter64
            MAX-ACCESS read-only
            STATUS current
            DESCRIPTION
              "The number of Ethernet frames which where choosen to be discarded due to buffer congestion."
            ::= { ethAggrCDRxEntry 13 }

        ethAggrCDRxTRSEF OBJECT-TYPE
            SYNTAX Counter64
            MAX-ACCESS read-only
            STATUS current
            DESCRIPTION
             "This object is the sum of three contributions: dot3StatsAlignmentErrors, dot3StatsFCSErrors and dot3StatsFrameTooLongs."
            ::= { ethAggrCDRxEntry 14 }

        ethAggrCDRxResetCounter OBJECT-TYPE
            SYNTAX TruthValue
            MAX-ACCESS read-create
            STATUS current
            DESCRIPTION
             "This object allows to reset i.e. set to 0, all the curent counters
              for received frames."
            ::= { ethAggrCDRxEntry 15 }
-- Received aggregates history datas table
        ethAggrHDRxTable OBJECT-TYPE
            SYNTAX SEQUENCE OF EthAggrHDRxEntry
            MAX-ACCESS not-accessible
            STATUS current
            DESCRIPTION
                "This table contains received aggregates History Datas counters."
            ::= { opticsIMEthPmMib 2 }

        ethAggrHDRxEntry OBJECT-TYPE
            SYNTAX EthAggrHDRxEntry
            MAX-ACCESS not-accessible
            STATUS current
            DESCRIPTION
                "An entry of received aggregates History Data counters table."
            INDEX { ifIndex, ethAggrHDRxGranularityPeriod, ethAggrHDRxPeriodEndtime, ethAggrHDRxIndex }
            ::= { ethAggrHDRxTable 1 }

        EthAggrHDRxEntry ::=
            SEQUENCE {
                ethAggrHDRxGranularityPeriod
                    OpticsIMPmGranularityPeriod,
                ethAggrHDRxPeriodEndtime
                    OpticsIMPmPeriodTime,
                ethAggrHDRxIndex
                    OpticsIMPmIndex,
                ethAggrHDRxTRCF
                    Counter64,
                ethAggrHDRxTRCO
                    Counter64,
                ethAggrHDRxSuspectIntervalFlag
                    OpticsIMPmSuspectIntervalFlag,
                ethAggrHDRxLastDiscontinuityTimeStamp
                    OpticsIMPmLastDiscontinuityTimeStamp,
                ethAggrHDRxStartByOS
                    TsdimManagerType,
                ethAggrHDRxTRCFUnicast
                    Counter64,
                ethAggrHDRxTRCFMulticast
                    Counter64,
                ethAggrHDRxTRCFBroadcast
                    Counter64,
                ethAggrHDRxTDF
                    Counter64,
                ethAggrHDRxTRSEF
                    Counter64
             }

        ethAggrHDRxGranularityPeriod OBJECT-TYPE
            SYNTAX OpticsIMPmGranularityPeriod
            MAX-ACCESS not-accessible
            STATUS current
            DESCRIPTION
                "See Textual Conventions."
            ::= { ethAggrHDRxEntry 1 }

        ethAggrHDRxPeriodEndtime OBJECT-TYPE
            SYNTAX OpticsIMPmPeriodTime
            MAX-ACCESS not-accessible
            STATUS current
            DESCRIPTION
                "See Textual Conventions."
            ::= { ethAggrHDRxEntry 2 }

        ethAggrHDRxIndex OBJECT-TYPE
            SYNTAX OpticsIMPmIndex
            MAX-ACCESS not-accessible
            STATUS current
            DESCRIPTION
                "See Textual Conventions.
                "
            ::= { ethAggrHDRxEntry 3 }

        ethAggrHDRxTRCF OBJECT-TYPE
            SYNTAX Counter64
            MAX-ACCESS read-only
            STATUS current
            DESCRIPTION
                "The number of Ethernet frames received correctly by the Virtual Ethernet Interface."
            ::= { ethAggrHDRxEntry 4 }

        ethAggrHDRxTRCO OBJECT-TYPE
            SYNTAX Counter64
            MAX-ACCESS read-only
            STATUS current
            DESCRIPTION
                "The number of octets of Ethernet frames received correctly by the Virtual Ethernet Interface, including Ethernet headers characters"
            ::= { ethAggrHDRxEntry 5 }

        ethAggrHDRxSuspectIntervalFlag OBJECT-TYPE
            SYNTAX OpticsIMPmSuspectIntervalFlag
            MAX-ACCESS read-only
            STATUS current
            DESCRIPTION
                "See Textual Conventions."
            ::= { ethAggrHDRxEntry 6 }

        ethAggrHDRxLastDiscontinuityTimeStamp OBJECT-TYPE
            SYNTAX OpticsIMPmLastDiscontinuityTimeStamp
            MAX-ACCESS read-only
            STATUS current
            DESCRIPTION
                "See Textual Conventions."
            ::= { ethAggrHDRxEntry 7 }

        ethAggrHDRxStartByOS OBJECT-TYPE
            SYNTAX TsdimManagerType
            MAX-ACCESS read-only
            STATUS current
            DESCRIPTION
                "See Textual Conventions."
            ::= { ethAggrHDRxEntry 8 }

    ethAggrHDRxTRCFUnicast OBJECT-TYPE
            SYNTAX Counter64
            MAX-ACCESS read-only
            STATUS current
            DESCRIPTION
             "The collected number of Ethernet Unicast frames received correctly by the Virtual Ethernet Interface."
            ::= { ethAggrHDRxEntry 9 }

        ethAggrHDRxTRCFMulticast OBJECT-TYPE
            SYNTAX Counter64
            MAX-ACCESS read-only
            STATUS current
            DESCRIPTION
              "The collected number of Ethernet Multicast frames received correctly by the Virtual Ethernet Interface."
            ::= { ethAggrHDRxEntry 10 }

        ethAggrHDRxTRCFBroadcast OBJECT-TYPE
            SYNTAX Counter64
            MAX-ACCESS read-only
            STATUS current
            DESCRIPTION
              "The collected number of Ethernet Broadcast frames received correctly by the Virtual Ethernet Interface."
            ::= { ethAggrHDRxEntry 11 }

        ethAggrHDRxTDF OBJECT-TYPE
            SYNTAX Counter64
            MAX-ACCESS read-only
            STATUS current
            DESCRIPTION
              "The collected number of Ethernet frames which where choosen to be discarded due to buffer congestion."
            ::= { ethAggrHDRxEntry 12 }

            ethAggrHDRxTRSEF OBJECT-TYPE
            SYNTAX Counter64
            MAX-ACCESS read-only
            STATUS current
            DESCRIPTION
                 "This object is the collection of the sum of three contributions: dot3StatsAlignmentErrors, dot3StatsFCSErrors and dot3StatsFrameTooLongs."
            ::= { ethAggrHDRxEntry 13 }


-- Transmitted aggregates current datas table
        ethAggrCDTxTable OBJECT-TYPE
            SYNTAX SEQUENCE OF EthAggrCDTxEntry
            MAX-ACCESS not-accessible
            STATUS current
            DESCRIPTION
                "This table contains transmitted aggregates Current Datas counters."
            ::= { opticsIMEthPmMib 3 }

        ethAggrCDTxEntry OBJECT-TYPE
            SYNTAX EthAggrCDTxEntry
            MAX-ACCESS not-accessible
            STATUS current
            DESCRIPTION
                "An entry of transmitted aggregates Current Data counters table."
            INDEX { ifIndex }
            ::= { ethAggrCDTxTable 1 }

        EthAggrCDTxEntry ::=
            SEQUENCE {
                ethAggrCDTxTTF
                    Counter64,
                ethAggrCDTxTTO
                    Counter64,
                ethAggrCDTxLastDiscontinuityTimeStamp
                    OpticsIMPmLastDiscontinuityTimeStamp,
                ethAggrCDTxStartTime
                    OpticsIMPmStartTime,
                ethAggrCDTxStartByOS
                    TsdimManagerType,
                ethAggrCDTxRowStatus
                    RowStatus,
                ethAggrCDTxTTFUnicast
                    Counter64,
                ethAggrCDTxTTFMulticast
                    Counter64,
                ethAggrCDTxTTFBroadcast
                    Counter64,
                ethAggrCDTxTDF
                    Counter64,
                ethAggrCDTxResetCounter
                    TruthValue
             }

        ethAggrCDTxTTF OBJECT-TYPE
            SYNTAX Counter64
            MAX-ACCESS read-only
            STATUS current
            DESCRIPTION
                "The number of Ethernet frames transmitted out by the Virtual Ethernet Interface."
            ::= { ethAggrCDTxEntry 2 }

        ethAggrCDTxTTO OBJECT-TYPE
            SYNTAX Counter64
            MAX-ACCESS read-only
            STATUS current
            DESCRIPTION
                "The number of octets of Ethernet frames transmitted out by the Virtual Ethernet Interface, including Ethernet headers characters"
            ::= { ethAggrCDTxEntry 3 }

        ethAggrCDTxLastDiscontinuityTimeStamp OBJECT-TYPE
            SYNTAX OpticsIMPmLastDiscontinuityTimeStamp
            MAX-ACCESS read-only
            STATUS current
            DESCRIPTION
                "See Textual Conventions."
            ::= { ethAggrCDTxEntry 5 }

        ethAggrCDTxStartTime OBJECT-TYPE
            SYNTAX OpticsIMPmStartTime
            MAX-ACCESS read-create
            STATUS current
            DESCRIPTION
                "See Textual Conventions.
                Even if it is defined as read-write, this objiect cannot be written by manager, but
                only read."
            ::= { ethAggrCDTxEntry 6 }

        ethAggrCDTxStartByOS OBJECT-TYPE
            SYNTAX TsdimManagerType
            MAX-ACCESS read-only
            STATUS current
            DESCRIPTION
                "See Textual Conventions."
            ::= { ethAggrCDTxEntry 7 }

        ethAggrCDTxRowStatus OBJECT-TYPE
            SYNTAX RowStatus
            MAX-ACCESS read-create
            STATUS current
            DESCRIPTION
                "See Textual Conventions."
            ::= { ethAggrCDTxEntry 9 }


       ethAggrCDTxTTFUnicast OBJECT-TYPE
            SYNTAX Counter64
            MAX-ACCESS read-only
            STATUS current
            DESCRIPTION
            "The number of Ethernet Unicast frames transmitted out by the Virtual Ethernet Interface "
            ::= { ethAggrCDTxEntry 10 }

        ethAggrCDTxTTFMulticast OBJECT-TYPE
            SYNTAX Counter64
            MAX-ACCESS read-only
            STATUS current
            DESCRIPTION
             "The number of good packets transmitted by this address that were directed to a multicast address.
             Note that this number does not include packets directed to the broadcast address.
             This behavior is the same performed by the counter hostOutMulticastPkts in the IETF RMON-MIB published as RFC 2819 "
            ::= { ethAggrCDTxEntry 11 }

        ethAggrCDTxTTFBroadcast OBJECT-TYPE
            SYNTAX Counter64
            MAX-ACCESS read-only
            STATUS current
            DESCRIPTION
             "The number of good packets transmitted by this address that were directed to the broadcast address.
             This behavior is the same performed by the counter hostOutBroadcastPkts in the IETF RMON-MIB published as RFC 2819 "
            ::= { ethAggrCDTxEntry 12 }

        ethAggrCDTxTDF OBJECT-TYPE
            SYNTAX Counter64
            MAX-ACCESS read-only
            STATUS current
            DESCRIPTION
             "The number of Ethernet frames which where choosen to be discarded due to buffer congestion "
            ::= { ethAggrCDTxEntry 13 }

        ethAggrCDTxResetCounter OBJECT-TYPE
            SYNTAX TruthValue
            MAX-ACCESS read-create
            STATUS current
            DESCRIPTION
             "This object allows to reset i.e. set to 0, all the curent counters
              for transmitted frames."
            ::= { ethAggrCDTxEntry 14 }

-- Transmitted aggregates history datas table
        ethAggrHDTxTable OBJECT-TYPE
            SYNTAX SEQUENCE OF EthAggrHDTxEntry
            MAX-ACCESS not-accessible
            STATUS current
            DESCRIPTION
                "This table contains transmitted aggregates History Datas counters."
            ::= { opticsIMEthPmMib 4 }

        ethAggrHDTxEntry OBJECT-TYPE
            SYNTAX EthAggrHDTxEntry
            MAX-ACCESS not-accessible
            STATUS current
            DESCRIPTION
                "An entry of transmitted aggregates History Data counters table."
            INDEX { ifIndex, ethAggrHDTxGranularityPeriod, ethAggrHDTxPeriodEndtime, ethAggrHDTxIndex }
            ::= { ethAggrHDTxTable 1 }

        EthAggrHDTxEntry ::=
            SEQUENCE {
                ethAggrHDTxGranularityPeriod
                    OpticsIMPmGranularityPeriod,
                ethAggrHDTxPeriodEndtime
                    OpticsIMPmPeriodTime,
                ethAggrHDTxIndex
                    OpticsIMPmIndex,
                ethAggrHDTxTTF
                    Counter64,
                ethAggrHDTxTTO
                    Counter64,
                ethAggrHDTxSuspectIntervalFlag
                    OpticsIMPmSuspectIntervalFlag,
                ethAggrHDTxLastDiscontinuityTimeStamp
                    OpticsIMPmLastDiscontinuityTimeStamp,
                ethAggrHDTxStartByOS
                    TsdimManagerType,
                ethAggrHDTxTTFUnicast
                    Counter64,
                ethAggrHDTxTTFMulticast
                    Counter64,
                ethAggrHDTxTTFBroadcast
                    Counter64,
                ethAggrHDTxTDF
                    Counter64
             }

        ethAggrHDTxGranularityPeriod OBJECT-TYPE
            SYNTAX OpticsIMPmGranularityPeriod
            MAX-ACCESS not-accessible
            STATUS current
            DESCRIPTION
                "See Textual Conventions."
            ::= { ethAggrHDTxEntry 1 }

        ethAggrHDTxPeriodEndtime OBJECT-TYPE
            SYNTAX OpticsIMPmPeriodTime
            MAX-ACCESS not-accessible
            STATUS current
            DESCRIPTION
                "See Textual Conventions."
            ::= { ethAggrHDTxEntry 2 }

        ethAggrHDTxIndex OBJECT-TYPE
            SYNTAX OpticsIMPmIndex
            MAX-ACCESS not-accessible
            STATUS current
            DESCRIPTION
                "See Textual Conventions.
                "
            ::= { ethAggrHDTxEntry 3 }

        ethAggrHDTxTTF OBJECT-TYPE
            SYNTAX Counter64
            MAX-ACCESS read-only
            STATUS current
            DESCRIPTION
                "The number of Ethernet frames transmitted out by the Virtual Ethernet Interface."
            ::= { ethAggrHDTxEntry 4 }

        ethAggrHDTxTTO OBJECT-TYPE
            SYNTAX Counter64
            MAX-ACCESS read-only
            STATUS current
            DESCRIPTION
                "The number of octets of Ethernet frames transmitted out by the Virtual Ethernet Interface, including Ethernet headers characters"
            ::= { ethAggrHDTxEntry 5 }

        ethAggrHDTxSuspectIntervalFlag OBJECT-TYPE
            SYNTAX OpticsIMPmSuspectIntervalFlag
            MAX-ACCESS read-only
            STATUS current
            DESCRIPTION
                "See Textual Conventions."
            ::= { ethAggrHDTxEntry 6 }

        ethAggrHDTxLastDiscontinuityTimeStamp OBJECT-TYPE
            SYNTAX OpticsIMPmLastDiscontinuityTimeStamp
            MAX-ACCESS read-only
            STATUS current
            DESCRIPTION
                "See Textual Conventions."
            ::= { ethAggrHDTxEntry 7 }

        ethAggrHDTxStartByOS OBJECT-TYPE
            SYNTAX TsdimManagerType
            MAX-ACCESS read-only
            STATUS current
            DESCRIPTION
                "See Textual Conventions."
            ::= { ethAggrHDTxEntry 8 }


        ethAggrHDTxTTFUnicast OBJECT-TYPE
            SYNTAX Counter64
            MAX-ACCESS read-only
            STATUS current
            DESCRIPTION
            "The collected number of Ethernet Unicast frames transmitted out by the Virtual Ethernet Interface."
            ::= { ethAggrHDTxEntry 9 }

        ethAggrHDTxTTFMulticast OBJECT-TYPE
            SYNTAX Counter64
            MAX-ACCESS read-only
            STATUS current
            DESCRIPTION
             "The collected number of Ethernet Multicast frames transmitted out by the Virtual Ethernet Interface."
            ::= { ethAggrHDTxEntry 10 }

        ethAggrHDTxTTFBroadcast OBJECT-TYPE
            SYNTAX Counter64
            MAX-ACCESS read-only
            STATUS current
            DESCRIPTION
           "The collected number of Ethernet Broadcast frames transmitted out by the Virtual Ethernet Interface."
            ::= { ethAggrHDTxEntry 11 }

        ethAggrHDTxTDF OBJECT-TYPE
            SYNTAX Counter64
            MAX-ACCESS read-only
            STATUS current
            DESCRIPTION
           "The collected number of Ethernet frames which where choosen to be discarded due to buffer congestion."
            ::= { ethAggrHDTxEntry 12 }


-- Incoming flow current datas table
        etsInFlowCDTable OBJECT-TYPE
            SYNTAX SEQUENCE OF EtsInFlowCDEntry
            MAX-ACCESS not-accessible
            STATUS current
            DESCRIPTION
                "This table contains received flows Current Datas counters."
            ::= { opticsIMEthPmMib 5 }

        etsInFlowCDEntry OBJECT-TYPE
            SYNTAX EtsInFlowCDEntry
            MAX-ACCESS not-accessible
            STATUS current
            DESCRIPTION
                "An entry of received flows Current Data counters table."
            INDEX { opticsIMETSInFlowIndex }
            ::= { etsInFlowCDTable 1 }

        EtsInFlowCDEntry ::=
            SEQUENCE {
                etsInFlowCDTRCFg
                    Counter64,
                etsInFlowCDTRCOg
                    Counter64,
                etsInFlowCDLastDiscontinuityTimeStamp
                    OpticsIMPmLastDiscontinuityTimeStamp,
                etsInFlowCDStartTime
                    OpticsIMPmStartTime,
                etsInFlowCDStartByOS
                    TsdimManagerType,
                etsInFlowCDRowStatus
                    RowStatus,
                etsInFlowCDTRCFy
                    Counter64,
                etsInFlowCDTRCFr
                    Counter64,
                etsInFlowCDTRCOy
                    Counter64,
                etsInFlowCDTRCOr
                    Counter64,
                                etsInFlowCDResetCounter
                                        TruthValue
             }

        etsInFlowCDTRCFg OBJECT-TYPE
            SYNTAX Counter64
            MAX-ACCESS read-only
            STATUS current
            DESCRIPTION
                "The number of green Ethernet frames received correctly."
            ::= { etsInFlowCDEntry 2 }

        etsInFlowCDTRCOg OBJECT-TYPE
            SYNTAX Counter64
            MAX-ACCESS read-only
            STATUS current
            DESCRIPTION
                "The number of octets of  green Ethernet frames received correctly for this flow, including Ethernet headers characters"
            ::= { etsInFlowCDEntry 3 }

        etsInFlowCDLastDiscontinuityTimeStamp OBJECT-TYPE
            SYNTAX OpticsIMPmLastDiscontinuityTimeStamp
            MAX-ACCESS read-only
            STATUS current
            DESCRIPTION
                "See Textual Conventions."
            ::= { etsInFlowCDEntry 6 }

        etsInFlowCDStartTime OBJECT-TYPE
            SYNTAX OpticsIMPmStartTime
            MAX-ACCESS read-create
            STATUS current
            DESCRIPTION
                "See Textual Conventions.
                Even if it is defined as read-write, this objiect cannot be written by manager, but only readen."
            ::= { etsInFlowCDEntry 9 }

        etsInFlowCDStartByOS OBJECT-TYPE
            SYNTAX TsdimManagerType
            MAX-ACCESS read-only
            STATUS current
            DESCRIPTION
                "See Textual Conventions."
            ::= { etsInFlowCDEntry 10 }

        etsInFlowCDRowStatus OBJECT-TYPE
            SYNTAX RowStatus
            MAX-ACCESS read-create
            STATUS current
            DESCRIPTION
                "See Textual Conventions."
            ::= { etsInFlowCDEntry 11 }

        etsInFlowCDTRCFy OBJECT-TYPE
            SYNTAX Counter64
            MAX-ACCESS read-only
            STATUS current
            DESCRIPTION
             "The number of yellow Ethernet frames received correctly."
            ::= { etsInFlowCDEntry 12 }

         etsInFlowCDTRCFr OBJECT-TYPE
            SYNTAX Counter64
            MAX-ACCESS read-only
            STATUS current
            DESCRIPTION
             "The number of red Ethernet frames received correctly."
            ::= { etsInFlowCDEntry 13 }

        etsInFlowCDTRCOy OBJECT-TYPE
            SYNTAX Counter64
            MAX-ACCESS read-only
            STATUS current
            DESCRIPTION
             " The number of octets of yellow Ethernet frames received correctly for this flow, including Ethernet headers characters."
            ::= { etsInFlowCDEntry 14 }

        etsInFlowCDTRCOr OBJECT-TYPE
            SYNTAX Counter64
            MAX-ACCESS read-only
            STATUS current
            DESCRIPTION
              " The number of octets of red Ethernet frames received correctly for this flow, including Ethernet headers characters."
            ::= { etsInFlowCDEntry 15 }


         etsInFlowCDResetCounter OBJECT-TYPE
                        SYNTAX TruthValue
                        MAX-ACCESS read-write
                        STATUS current
                        DESCRIPTION
              " This object allows to reset i.e. set to 0, all the curent counters for received frames."
                        ::= { etsInFlowCDEntry 16 }



-- Incoming flow history datas table
        etsInFlowHDTable OBJECT-TYPE
            SYNTAX SEQUENCE OF EtsInFlowHDEntry
            MAX-ACCESS not-accessible
            STATUS current
            DESCRIPTION
                "This table contains  received flows History Datas counters."
            ::= { opticsIMEthPmMib 6 }

        etsInFlowHDEntry OBJECT-TYPE
            SYNTAX EtsInFlowHDEntry
            MAX-ACCESS not-accessible
            STATUS current
            DESCRIPTION
                "An entry of transmitted flows History Data counters table."
            INDEX { opticsIMETSInFlowIndex, etsInFlowHDGranularityPeriod, etsInFlowHDPeriodEndtime, etsInFlowHDIndex }
            ::= { etsInFlowHDTable 1 }

        EtsInFlowHDEntry ::=
            SEQUENCE {
                etsInFlowHDGranularityPeriod
                    OpticsIMPmGranularityPeriod,
                etsInFlowHDPeriodEndtime
                    OpticsIMPmPeriodTime,
                etsInFlowHDIndex
                    OpticsIMPmIndex,
                etsInFlowHDTRCFg
                    Counter64,
                etsInFlowHDTRCOg
                    Counter64,
                etsInFlowHDSuspectIntervalFlag
                    OpticsIMPmSuspectIntervalFlag,
                etsInFlowHDLastDiscontinuityTimeStamp
                    OpticsIMPmLastDiscontinuityTimeStamp,
                etsInFlowHDStartByOS
                    TsdimManagerType,
                etsInFlowHDTRCFy
                    Counter64,
                etsInFlowHDTRCFr
                    Counter64,
                etsInFlowHDTRCOy
                    Counter64,
                etsInFlowHDTRCOr
                    Counter64
             }

        etsInFlowHDGranularityPeriod OBJECT-TYPE
            SYNTAX OpticsIMPmGranularityPeriod
            MAX-ACCESS not-accessible
            STATUS current
            DESCRIPTION
                "See Textual Conventions."
            ::= { etsInFlowHDEntry 1 }

        etsInFlowHDPeriodEndtime OBJECT-TYPE
            SYNTAX OpticsIMPmPeriodTime
            MAX-ACCESS not-accessible
            STATUS current
            DESCRIPTION
                "See Textual Conventions."
            ::= { etsInFlowHDEntry 2 }

        etsInFlowHDIndex OBJECT-TYPE
            SYNTAX OpticsIMPmIndex
            MAX-ACCESS not-accessible
            STATUS current
            DESCRIPTION
                "See Textual Conventions.
                "
            ::= { etsInFlowHDEntry 3 }

        etsInFlowHDTRCFg OBJECT-TYPE
            SYNTAX Counter64
            MAX-ACCESS read-only
            STATUS current
            DESCRIPTION
                "The number of green Ethernet frames received correctly."
            ::= { etsInFlowHDEntry 4 }

        etsInFlowHDTRCOg OBJECT-TYPE
            SYNTAX Counter64
            MAX-ACCESS read-only
            STATUS current
            DESCRIPTION
                "The number of octets of  green Ethernet frames received correctly for this flow, including Ethernet headers characters"
            ::= { etsInFlowHDEntry 5 }

        etsInFlowHDSuspectIntervalFlag OBJECT-TYPE
            SYNTAX OpticsIMPmSuspectIntervalFlag
            MAX-ACCESS read-only
            STATUS current
            DESCRIPTION
                "See Textual Conventions."
            ::= { etsInFlowHDEntry 6 }

        etsInFlowHDLastDiscontinuityTimeStamp OBJECT-TYPE
            SYNTAX OpticsIMPmLastDiscontinuityTimeStamp
            MAX-ACCESS read-only
            STATUS current
            DESCRIPTION
                "See Textual Conventions."
            ::= { etsInFlowHDEntry 7 }

        etsInFlowHDStartByOS OBJECT-TYPE
            SYNTAX TsdimManagerType
            MAX-ACCESS read-only
            STATUS current
            DESCRIPTION
                "See Textual Conventions."
            ::= { etsInFlowHDEntry 8 }

        etsInFlowHDTRCFy OBJECT-TYPE
            SYNTAX Counter64
            MAX-ACCESS read-only
            STATUS current
            DESCRIPTION
             "The collected number of yellow Ethernet frames received correctly."
            ::= { etsInFlowHDEntry 9 }

        etsInFlowHDTRCFr OBJECT-TYPE
            SYNTAX Counter64
            MAX-ACCESS read-only
            STATUS current
            DESCRIPTION
             "The collected number of red Ethernet frames received correctly."
            ::= { etsInFlowHDEntry 10 }

        etsInFlowHDTRCOy OBJECT-TYPE
            SYNTAX Counter64
            MAX-ACCESS read-only
            STATUS current
            DESCRIPTION
             "The collected number of octets of yellow Ethernet frames received correctly for this flow,including Ethernet headers characters"
            ::= { etsInFlowHDEntry 11 }

        etsInFlowHDTRCOr OBJECT-TYPE
            SYNTAX Counter64
            MAX-ACCESS read-only
            STATUS current
            DESCRIPTION
             "The collected number of octets of red Ethernet frames received correctly for this flow,including Ethernet headers characters"
            ::= { etsInFlowHDEntry 12 }


-- Outgoing flow current datas table
        etsOutFlowCDTable OBJECT-TYPE
            SYNTAX SEQUENCE OF EtsOutFlowCDEntry
            MAX-ACCESS not-accessible
            STATUS current
            DESCRIPTION
                "This table contains transmitted flows Current Datas counters."
            ::= { opticsIMEthPmMib 7 }

        etsOutFlowCDEntry OBJECT-TYPE
            SYNTAX EtsOutFlowCDEntry
            MAX-ACCESS not-accessible
            STATUS current
            DESCRIPTION
                "An entry of transmitted flows Current Data counters table."
            INDEX { opticsIMETSOutFlowIndex }
            ::= { etsOutFlowCDTable 1 }

        EtsOutFlowCDEntry ::=
            SEQUENCE {
                etsOutFlowCDTTFg
                    Counter64,
                etsOutFlowCDTTOg
                    Counter64,
                etsOutFlowCDLastDiscontinuityTimeStamp
                    OpticsIMPmLastDiscontinuityTimeStamp,
                etsOutFlowCDStartTime
                    OpticsIMPmStartTime,
                etsOutFlowCDStartByOS
                    TsdimManagerType,
                etsOutFlowCDRowStatus
                    RowStatus,
                etsOutFlowCDTTFy
                    Counter64,
                etsOutFlowCDTTOy
                    Counter64,
                etsOutFlowCDTDFg
                    Counter64,
                etsOutFlowCDTDFy
                    Counter64,
                etsOutFlowCDTDOg
                    Counter64,
                etsOutFlowCDTDOy
                    Counter64,
                etsOutFlowCDResetCounter
                        TruthValue
             }

        etsOutFlowCDTTFg OBJECT-TYPE
            SYNTAX Counter64
            MAX-ACCESS read-only
            STATUS current
            DESCRIPTION
                "Total number of green Ethernet frames transmitted out."
            ::= { etsOutFlowCDEntry 6 }

        etsOutFlowCDTTOg OBJECT-TYPE
            SYNTAX Counter64
            MAX-ACCESS read-only
            STATUS current
            DESCRIPTION
                "Total number of octets of green Ethernet frames transmitted out, including  Ethernet header characters."
            ::= { etsOutFlowCDEntry 7 }

        etsOutFlowCDLastDiscontinuityTimeStamp OBJECT-TYPE
            SYNTAX OpticsIMPmLastDiscontinuityTimeStamp
            MAX-ACCESS read-only
            STATUS current
            DESCRIPTION
                "See Textual Conventions."
            ::= { etsOutFlowCDEntry 9 }

        etsOutFlowCDStartTime OBJECT-TYPE
            SYNTAX OpticsIMPmStartTime
            MAX-ACCESS read-create
            STATUS current
            DESCRIPTION
                "See Textual Conventions.
                Even if it is defined as read-create, this object cannot be written by manager, but only read."
            ::= { etsOutFlowCDEntry 13 }

        etsOutFlowCDStartByOS OBJECT-TYPE
            SYNTAX TsdimManagerType
            MAX-ACCESS read-only
            STATUS current
            DESCRIPTION
                "See Textual Conventions."
            ::= { etsOutFlowCDEntry 14 }

        etsOutFlowCDRowStatus OBJECT-TYPE
            SYNTAX RowStatus
            MAX-ACCESS read-create
            STATUS current
            DESCRIPTION
                "See Textual Conventions."
            ::= { etsOutFlowCDEntry 15 }

        etsOutFlowCDTTFy OBJECT-TYPE
            SYNTAX Counter64
            MAX-ACCESS read-only
            STATUS current
            DESCRIPTION
             "Total number of yellow Ethernet frames transmitted out."
            ::= { etsOutFlowCDEntry 16 }

        etsOutFlowCDTTOy OBJECT-TYPE
            SYNTAX Counter64
            MAX-ACCESS read-only
            STATUS current
            DESCRIPTION
               "Total number of octets of yellow Ethernet frames transmitted out,including Ethernet header characters."
            ::= { etsOutFlowCDEntry 17 }

        etsOutFlowCDTDFg OBJECT-TYPE
            SYNTAX Counter64
            MAX-ACCESS read-only
            STATUS current
            DESCRIPTION
              "The number of green Ethernet frames which where choosen to be discarded due to buffer congestion."
            ::= { etsOutFlowCDEntry 18 }

        etsOutFlowCDTDFy OBJECT-TYPE
            SYNTAX Counter64
            MAX-ACCESS read-only
            STATUS current
            DESCRIPTION
              "The number of yellow Ethernet frames which where choosen to be discarded due to buffer congestion."
            ::= { etsOutFlowCDEntry 19 }

        etsOutFlowCDTDOg OBJECT-TYPE
            SYNTAX Counter64
            MAX-ACCESS read-only
            STATUS current
            DESCRIPTION
              "The number of green Ethernet octets which where choosen to be discarded due to buffer congestion."
            ::= { etsOutFlowCDEntry 20 }

        etsOutFlowCDTDOy OBJECT-TYPE
            SYNTAX Counter64
            MAX-ACCESS read-only
            STATUS current
            DESCRIPTION
             "The number of yellow Ethernet octets which where choosen to be discarded due to buffer congestion."
            ::= { etsOutFlowCDEntry 21 }

                etsOutFlowCDResetCounter OBJECT-TYPE
                        SYNTAX TruthValue
                        MAX-ACCESS read-write
                        STATUS current
                        DESCRIPTION
             "This object allows to reset i.e. set to 0, all the curent counters for transmitted frames."
                        ::= { etsOutFlowCDEntry 22 }



-- Outgoing flow history datas table
        etsOutFlowHDTable OBJECT-TYPE
            SYNTAX SEQUENCE OF EtsOutFlowHDEntry
            MAX-ACCESS not-accessible
            STATUS current
            DESCRIPTION
                "This table contains transmitted flows History Datas counters."
            ::= { opticsIMEthPmMib 8 }

        etsOutFlowHDEntry OBJECT-TYPE
            SYNTAX EtsOutFlowHDEntry
            MAX-ACCESS not-accessible
            STATUS current
            DESCRIPTION
                "An entry of transmitted  flow counters History Datatable."
            INDEX { opticsIMETSOutFlowIndex, etsOutFlowHDGranularityPeriod, etsOutFlowHDPeriodEndtime, etsOutFlowHDIndex }
            ::= { etsOutFlowHDTable 1 }

        EtsOutFlowHDEntry ::=
            SEQUENCE {
                etsOutFlowHDGranularityPeriod
                    OpticsIMPmGranularityPeriod,
                etsOutFlowHDPeriodEndtime
                    OpticsIMPmPeriodTime,
                etsOutFlowHDIndex
                    OpticsIMPmIndex,
                etsOutFlowHDTTFg
                    Counter64,
                etsOutFlowHDTTOg
                    Counter64,
                etsOutFlowHDSuspectIntervalFlag
                    OpticsIMPmSuspectIntervalFlag,
                etsOutFlowHDLastDiscontinuityTimeStamp
                    OpticsIMPmLastDiscontinuityTimeStamp,
                etsOutFlowHDStartByOS
                    TsdimManagerType,
                etsOutFlowHDTTFy
                    Counter64,
                etsOutFlowHDTTOy
                    Counter64,
                etsOutFlowHDTDFg
                    Counter64,
                etsOutFlowHDTDFy
                    Counter64,
                etsOutFlowHDTDOg
                    Counter64,
                etsOutFlowHDTDOy
                    Counter64
             }

        etsOutFlowHDGranularityPeriod OBJECT-TYPE
            SYNTAX OpticsIMPmGranularityPeriod
            MAX-ACCESS not-accessible
            STATUS current
            DESCRIPTION
                "See Textual Conventions."
            ::= { etsOutFlowHDEntry 1 }

        etsOutFlowHDPeriodEndtime OBJECT-TYPE
            SYNTAX OpticsIMPmPeriodTime
            MAX-ACCESS not-accessible
            STATUS current
            DESCRIPTION
                "See Textual Conventions."
            ::= { etsOutFlowHDEntry 2 }

        etsOutFlowHDIndex OBJECT-TYPE
            SYNTAX OpticsIMPmIndex
            MAX-ACCESS not-accessible
            STATUS current
            DESCRIPTION
                "See Textual Conventions.
                "
            ::= { etsOutFlowHDEntry 3 }

        etsOutFlowHDTTFg OBJECT-TYPE
            SYNTAX Counter64
            MAX-ACCESS read-only
            STATUS current
            DESCRIPTION
                "Total number of green Ethernet frames transmitted out"
            ::= { etsOutFlowHDEntry 4 }

        etsOutFlowHDTTOg OBJECT-TYPE
            SYNTAX Counter64
            MAX-ACCESS read-only
            STATUS current
            DESCRIPTION
                "total number of octets of green Ethernet frames transmitted out, including  Ethernet header characters."
            ::= { etsOutFlowHDEntry 5 }

        etsOutFlowHDSuspectIntervalFlag OBJECT-TYPE
            SYNTAX OpticsIMPmSuspectIntervalFlag
            MAX-ACCESS read-only
            STATUS current
            DESCRIPTION
                "See Textual Conventions."
            ::= { etsOutFlowHDEntry 8 }

        etsOutFlowHDLastDiscontinuityTimeStamp OBJECT-TYPE
            SYNTAX OpticsIMPmLastDiscontinuityTimeStamp
            MAX-ACCESS read-only
            STATUS current
            DESCRIPTION
                "See Textual Conventions."
            ::= { etsOutFlowHDEntry 9 }

        etsOutFlowHDStartByOS OBJECT-TYPE
            SYNTAX TsdimManagerType
            MAX-ACCESS read-only
            STATUS current
            DESCRIPTION
                "See Textual Conventions."
            ::= { etsOutFlowHDEntry 10 }

        etsOutFlowHDTTFy OBJECT-TYPE
            SYNTAX Counter64
            MAX-ACCESS read-only
            STATUS current
            DESCRIPTION
             "Total collected number of yellow Ethernet frames transmitted out"
            ::= { etsOutFlowHDEntry 11 }

        etsOutFlowHDTTOy OBJECT-TYPE
            SYNTAX Counter64
            MAX-ACCESS read-only
            STATUS current
            DESCRIPTION
             "Total collected number of octets of yellow Ethernet frames transmitted out,including Ethernet header characters."
            ::= { etsOutFlowHDEntry 12 }

        etsOutFlowHDTDFg OBJECT-TYPE
            SYNTAX Counter64
            MAX-ACCESS read-only
            STATUS current
            DESCRIPTION
              "The collected number of green Ethernet frames which where choosen to be discarded due to buffer congestion."
            ::= { etsOutFlowHDEntry 13 }

        etsOutFlowHDTDFy OBJECT-TYPE
            SYNTAX Counter64
            MAX-ACCESS read-only
            STATUS current
            DESCRIPTION
             "The collected number of yellow Ethernet frames which where choosen to be discarded due to buffer congestion."
            ::= { etsOutFlowHDEntry 14 }

                etsOutFlowHDTDOg OBJECT-TYPE
            SYNTAX Counter64
            MAX-ACCESS read-only
            STATUS current
            DESCRIPTION
             "The collected number of green Ethernet octets which where choosen to be discarded due to buffer congestion."
            ::= { etsOutFlowHDEntry 15 }

        etsOutFlowHDTDOy OBJECT-TYPE
            SYNTAX Counter64
            MAX-ACCESS read-only
            STATUS current
            DESCRIPTION
              "The number of yellow Ethernet octets which where choosen to be discarded due to buffer congestion."
            ::= { etsOutFlowHDEntry 16 }

-- Received aggregates counters table for maintenance pourpose.
        ethAggrMaintRxTable OBJECT-TYPE
            SYNTAX SEQUENCE OF EthAggrMaintRxEntry
            MAX-ACCESS not-accessible
            STATUS current
            DESCRIPTION
                "This table contains received aggregates maintenance counters."
            ::= { opticsIMEthPmMib 9 }

        ethAggrMaintRxEntry OBJECT-TYPE
            SYNTAX EthAggrMaintRxEntry
            MAX-ACCESS not-accessible
            STATUS current
            DESCRIPTION
                "An entry of received aggregates maintenance counters table."
            INDEX { ifIndex }
            ::= { ethAggrMaintRxTable 1 }

        EthAggrMaintRxEntry ::=
            SEQUENCE {
                ethAggrMaintRxTRCO
                    Counter64,
                ethAggrMaintRxTRCF
                    Counter64,
                ethAggrMaintRxTRSEF
                    Counter64,
                ethAggrMaintRxTDF
                    Counter64,
                ethAggrMaintRxLastDiscontinuityTimeStamp
                    OpticsIMPmLastDiscontinuityTimeStamp,
                ethAggrMaintRxRetrievingTime
                    OpticsIMPmRetrievingTime,
                ethAggrMaintRxTRCFUnicast
                    Counter64,
                ethAggrMaintRxTRCFMulticast
                    Counter64,
                ethAggrMaintRxTRCFBroadcast
                    Counter64,
                                ethAggrMaintRxReset
                    TruthValue
             }

        ethAggrMaintRxTRCO OBJECT-TYPE
            SYNTAX Counter64
            MAX-ACCESS read-only
            STATUS current
            DESCRIPTION
                "The number of octets of Ethernet frames received correctly by the Virtual Ethernet Interface, including Ethernet headers characters"
            ::= { ethAggrMaintRxEntry 1 }

        ethAggrMaintRxTRCF OBJECT-TYPE
            SYNTAX Counter64
            MAX-ACCESS read-only
            STATUS current
            DESCRIPTION
                "The number of Ethernet frames received correctly by the Virtual Ethernet Interface."
            ::= { ethAggrMaintRxEntry 2 }

        ethAggrMaintRxTRSEF OBJECT-TYPE
            SYNTAX Counter64
            MAX-ACCESS read-only
            STATUS current
            DESCRIPTION
                "This object is the sum of three contributions dot3StatsAlignmentErrors, dot3StatsFCSErrors and dot3StatsFrameTooLongs"
            ::= { ethAggrMaintRxEntry 3 }

        ethAggrMaintRxTDF OBJECT-TYPE
            SYNTAX Counter64
            MAX-ACCESS read-only
            STATUS current
            DESCRIPTION
                "Total number of Ethernet frames which where choosen to be discarded due to buffer congestion"
            ::= { ethAggrMaintRxEntry 4 }

        ethAggrMaintRxLastDiscontinuityTimeStamp OBJECT-TYPE
            SYNTAX OpticsIMPmLastDiscontinuityTimeStamp
            MAX-ACCESS read-only
            STATUS current
            DESCRIPTION
                "See Textual Conventions."
            ::= { ethAggrMaintRxEntry 5 }

        ethAggrMaintRxRetrievingTime OBJECT-TYPE
            SYNTAX OpticsIMPmRetrievingTime
            MAX-ACCESS read-only
            STATUS current
            DESCRIPTION
                "See Textual Conventions."
            ::= { ethAggrMaintRxEntry 6 }

        ethAggrMaintRxTRCFUnicast OBJECT-TYPE
            SYNTAX Counter64
            MAX-ACCESS read-only
            STATUS current
            DESCRIPTION
              "The number of Ethernet Unicast frames received correctly by the Virtual Ethernet Interface."
            ::= { ethAggrMaintRxEntry 7 }

         ethAggrMaintRxTRCFMulticast OBJECT-TYPE
            SYNTAX Counter64
            MAX-ACCESS read-only
            STATUS current
            DESCRIPTION
             "The total number of good packets received that were directed to a multicast address.
             Note that this number does not include packets directed to the broadcast address.
             This behavior is the same performed by the counter etherStatsMulticastPkts in the IETF RMON-MIB published as RFC 2819"
            ::= { ethAggrMaintRxEntry 8 }

        ethAggrMaintRxTRCFBroadcast OBJECT-TYPE
            SYNTAX Counter64
            MAX-ACCESS read-only
            STATUS current
            DESCRIPTION
             "The total number of good packets received that were directed to the broadcast address.
               Note that this does not include multicast packets.
               This behavior is the same performed by the counter etherStatsBroadcastPkts in the IETF RMON-MIB published as RFC 2819"
            ::= { ethAggrMaintRxEntry 9 }

            ethAggrMaintRxReset OBJECT-TYPE
            SYNTAX TruthValue
            MAX-ACCESS read-write
            STATUS current
            DESCRIPTION
        "This object allows to reset i.e. set to 0, all the counters for received frames."
            ::= { ethAggrMaintRxEntry 10 }


-- Transmitted aggregates counters table for maintenance pourpose.
        ethAggrMaintTxTable OBJECT-TYPE
            SYNTAX SEQUENCE OF EthAggrMaintTxEntry
            MAX-ACCESS not-accessible
            STATUS current
            DESCRIPTION
                "This table contains transmitted aggregates maintenance counters."
            ::= { opticsIMEthPmMib 11 }

        ethAggrMaintTxEntry OBJECT-TYPE
            SYNTAX EthAggrMaintTxEntry
            MAX-ACCESS not-accessible
            STATUS current
            DESCRIPTION
                "An entry of transmitted aggregate maintenance counters table."
            INDEX { ifIndex }
            ::= { ethAggrMaintTxTable 1 }

        EthAggrMaintTxEntry ::=
            SEQUENCE {
                ethAggrMaintTxTTO
                    Counter64,
                ethAggrMaintTxTTF
                    Counter64,
                ethAggrMaintTxTDF
                    Counter64,
                ethAggrMaintTxLastDiscontinuityTimeStamp
                    OpticsIMPmLastDiscontinuityTimeStamp,
                ethAggrMaintTxRetrievingTime
                    OpticsIMPmRetrievingTime,
                ethAggrMaintTxTTFUnicast
                    Counter64,
                ethAggrMaintTxTTFMulticast
                    Counter64,
                ethAggrMaintTxTTFBroadcast
                    Counter64,
                            ethAggrMaintTxReset
                    TruthValue,
                    ethAggrMaintCompressedTxTTO
                    Counter64
             }

        ethAggrMaintTxTTO OBJECT-TYPE
            SYNTAX Counter64
            MAX-ACCESS read-only
            STATUS current
            DESCRIPTION
                "The number of octets of Ethernet frames transmitted out by the Virtual Ethernet Interface, including Ethernet headers characters"
            ::= { ethAggrMaintTxEntry 1 }

        ethAggrMaintTxTTF OBJECT-TYPE
            SYNTAX Counter64
            MAX-ACCESS read-only
            STATUS current
            DESCRIPTION
                "The number of Ethernet frames transmitted out by the Virtual Ethernet Interface."
            ::= { ethAggrMaintTxEntry 2 }

        ethAggrMaintTxTDF OBJECT-TYPE
            SYNTAX Counter64
            MAX-ACCESS read-only
            STATUS current
            DESCRIPTION
                "Total number of Ethernet frames which where choosen to be discarded due to buffer congestion"
            ::= { ethAggrMaintTxEntry 3 }

        ethAggrMaintTxLastDiscontinuityTimeStamp OBJECT-TYPE
            SYNTAX OpticsIMPmLastDiscontinuityTimeStamp
            MAX-ACCESS read-only
            STATUS current
            DESCRIPTION
                "See Textual Conventions."
            ::= { ethAggrMaintTxEntry 4 }

        ethAggrMaintTxRetrievingTime OBJECT-TYPE
            SYNTAX OpticsIMPmRetrievingTime
            MAX-ACCESS read-only
            STATUS current
            DESCRIPTION
                "See Textual Conventions."
            ::= { ethAggrMaintTxEntry 5 }

        ethAggrMaintTxTTFUnicast OBJECT-TYPE
            SYNTAX Counter64
            MAX-ACCESS read-only
            STATUS current
            DESCRIPTION
            "The number of Ethernet Unicast frames transmitted out by the Virtual Ethernet Interface."
            ::= { ethAggrMaintTxEntry 6 }

        ethAggrMaintTxTTFMulticast OBJECT-TYPE
            SYNTAX Counter64
            MAX-ACCESS read-only
            STATUS current
            DESCRIPTION
             "The number of good packets transmitted by this address that were directed to a multicast address.
               Note that this number does not include packets directed to the broadcast address.
               This behavior is the same performed by the counter hostOutMulticastPkts in the IETF RMON-MIB published as RFC 2819."
            ::= { ethAggrMaintTxEntry 7 }

            ethAggrMaintTxTTFBroadcast OBJECT-TYPE
            SYNTAX Counter64
            MAX-ACCESS read-only
            STATUS current
            DESCRIPTION
               "The number of good packets transmitted by this address that were directed to the broadcast address.
                 This behavior is the same performed by the counter hostOutBroadcastPkts in the IETF RMON-MIB published as RFC 2819."
            ::= { ethAggrMaintTxEntry 8 }

        ethAggrMaintTxReset OBJECT-TYPE
            SYNTAX TruthValue
            MAX-ACCESS read-write
            STATUS current
            DESCRIPTION
                "This object allows to reset i.e. set to 0, all the
                  counters for transmitted frames."
            ::= { ethAggrMaintTxEntry 9 }

        ethAggrMaintCompressedTxTTO OBJECT-TYPE
            SYNTAX Counter64
            MAX-ACCESS read-only
            STATUS current
            DESCRIPTION
                    "The number of Ethernet octets at the egress of the compression module transmitted out by the Virtual Ethernet Interface"
            ::= { ethAggrMaintTxEntry 10 }


-- Incoming flow counters table for maintenance pourpose.
        etsInFlowMaintTable OBJECT-TYPE
            SYNTAX SEQUENCE OF EtsInFlowMaintEntry
            MAX-ACCESS not-accessible
            STATUS current
            DESCRIPTION
                "This table contains incoming flow maintenance counters. "
            ::= { opticsIMEthPmMib 17 }

        etsInFlowMaintEntry OBJECT-TYPE
            SYNTAX EtsInFlowMaintEntry
            MAX-ACCESS not-accessible
            STATUS current
            DESCRIPTION
                "An entry of incoming flow maintenance counters table."
            INDEX { opticsIMETSInFlowIndex }
            ::= { etsInFlowMaintTable 1 }

        EtsInFlowMaintEntry ::=
            SEQUENCE {
                etsInFlowMaintTRCOg
                    Counter64,
                etsInFlowMaintTRCFg
                    Counter64,
                etsInFlowMaintTRCOy
                    Counter64,
                etsInFlowMaintTRCFy
                    Counter64,
                etsInFlowMaintTRCOr
                    Counter64,
                etsInFlowMaintTRCFr
                    Counter64,
                etsInFlowMaintRetrievingTime
                    OpticsIMPmRetrievingTime,
                etsInFlowMaintLastDiscontinuityTimeStamp
                    OpticsIMPmLastDiscontinuityTimeStamp,
                etsInFlowMaintReset
                    TruthValue
             }

        etsInFlowMaintTRCOg OBJECT-TYPE
            SYNTAX Counter64
            MAX-ACCESS read-only
            STATUS current
            DESCRIPTION
                "The number of octets of  green Ethernet frames received correctly for this flow, including Ethernet headers characters"
            ::= { etsInFlowMaintEntry 3 }

        etsInFlowMaintTRCFg OBJECT-TYPE
            SYNTAX Counter64
            MAX-ACCESS read-only
            STATUS current
            DESCRIPTION
                "The number of green Ethernet frames received correctly."
            ::= { etsInFlowMaintEntry 4 }

        etsInFlowMaintTRCOy OBJECT-TYPE
            SYNTAX Counter64
            MAX-ACCESS read-only
            STATUS current
            DESCRIPTION
                "The number of octets of yellow Ethernet frames received correctly for this flow, including Ethernet headers characters"
            ::= { etsInFlowMaintEntry 8 }

        etsInFlowMaintTRCFy OBJECT-TYPE
            SYNTAX Counter64
            MAX-ACCESS read-only
            STATUS current
            DESCRIPTION
                "The number of yellow Ethernet frames received correctly."
            ::= { etsInFlowMaintEntry 9 }

        etsInFlowMaintTRCOr OBJECT-TYPE
            SYNTAX Counter64
            MAX-ACCESS read-only
            STATUS current
            DESCRIPTION
                "The number of octets of red Ethernet frames received correctly for this flow, including Ethernet headers characters"
            ::= { etsInFlowMaintEntry 13 }

        etsInFlowMaintTRCFr OBJECT-TYPE
            SYNTAX Counter64
            MAX-ACCESS read-only
            STATUS current
            DESCRIPTION
                "The number of red Ethernet frames received correctly."
            ::= { etsInFlowMaintEntry 14 }

        etsInFlowMaintRetrievingTime OBJECT-TYPE
            SYNTAX OpticsIMPmRetrievingTime
            MAX-ACCESS read-only
            STATUS current
            DESCRIPTION
                "See Textual Conventions."
            ::= { etsInFlowMaintEntry 15 }

        etsInFlowMaintLastDiscontinuityTimeStamp OBJECT-TYPE
            SYNTAX OpticsIMPmLastDiscontinuityTimeStamp
            MAX-ACCESS read-only
            STATUS current
            DESCRIPTION
                "See Textual Conventions."
            ::= { etsInFlowMaintEntry 16 }

        etsInFlowMaintReset OBJECT-TYPE
            SYNTAX TruthValue
            MAX-ACCESS read-write
            STATUS current
            DESCRIPTION
                "This object allows to reset, i.e. set to 0, all
                 the InFlow maintenance counters. Setting this
                 object to true(1) resets all the counters. After this
                 action its value goes back to false(2)."
            ::= { etsInFlowMaintEntry 17 }

-- Outgoing flow counters table for maintenance pourpose
        etsOutFlowMaintTable OBJECT-TYPE
            SYNTAX SEQUENCE OF EtsOutFlowMaintEntry
            MAX-ACCESS not-accessible
            STATUS current
            DESCRIPTION
                "This table contains outgoing flow maintenance counters. "
            ::= { opticsIMEthPmMib 18 }

        etsOutFlowMaintEntry OBJECT-TYPE
            SYNTAX EtsOutFlowMaintEntry
            MAX-ACCESS not-accessible
            STATUS current
            DESCRIPTION
                "An entry of outgoing flow maintenance counters table."
            INDEX { opticsIMETSOutFlowIndex }
            ::= { etsOutFlowMaintTable 1 }

        EtsOutFlowMaintEntry ::=
            SEQUENCE {
                etsOutFlowMaintTTOg
                    Counter64,
                etsOutFlowMaintTTFg
                    Counter64,
                etsOutFlowMaintTDFg
                    Counter64,
                etsOutFlowMaintTTOy
                    Counter64,
                etsOutFlowMaintTTFy
                    Counter64,
                etsOutFlowMaintTDFy
                    Counter64,
                etsOutFlowMaintRetrievingTime
                    OpticsIMPmRetrievingTime,
                etsOutFlowMaintLastDiscontinuityTimeStamp
                    OpticsIMPmLastDiscontinuityTimeStamp,
                etsOutFlowMaintReset
                    TruthValue
             }

        etsOutFlowMaintTTOg OBJECT-TYPE
            SYNTAX Counter64
            MAX-ACCESS read-only
            STATUS current
            DESCRIPTION
                "Total number of octets of green Ethernet frames transmitted out, including  Ethernet header characters."
            ::= { etsOutFlowMaintEntry 3 }

        etsOutFlowMaintTTFg OBJECT-TYPE
            SYNTAX Counter64
            MAX-ACCESS read-only
            STATUS current
            DESCRIPTION
                "Total number of green Ethernet frames transmitted out."
            ::= { etsOutFlowMaintEntry 4 }

        etsOutFlowMaintTDFg OBJECT-TYPE
            SYNTAX Counter64
            MAX-ACCESS read-only
            STATUS current
            DESCRIPTION
                "Total number of green Ethernet frames which were chosen to be discarded due to buffer congestion."
            ::= { etsOutFlowMaintEntry 5 }

        etsOutFlowMaintTTOy OBJECT-TYPE
            SYNTAX Counter64
            MAX-ACCESS read-only
            STATUS current
            DESCRIPTION
                "Total number of octets of yellow Ethernet frames transmitted out, including  Ethernet header characters."
            ::= { etsOutFlowMaintEntry 8 }

        etsOutFlowMaintTTFy OBJECT-TYPE
            SYNTAX Counter64
            MAX-ACCESS read-only
            STATUS current
            DESCRIPTION
                "Total number of yellow Ethernet frames transmitted out."
            ::= { etsOutFlowMaintEntry 9 }

        etsOutFlowMaintTDFy OBJECT-TYPE
            SYNTAX Counter64
            MAX-ACCESS read-only
            STATUS current
            DESCRIPTION
                "Total number of yellow Ethernet frames which were chosen to be discarded due to buffer congestion."
            ::= { etsOutFlowMaintEntry 10 }

        etsOutFlowMaintRetrievingTime OBJECT-TYPE
            SYNTAX OpticsIMPmRetrievingTime
            MAX-ACCESS read-only
            STATUS current
            DESCRIPTION
                "See Textual Conventions."
            ::= { etsOutFlowMaintEntry 13 }

        etsOutFlowMaintLastDiscontinuityTimeStamp OBJECT-TYPE
            SYNTAX OpticsIMPmLastDiscontinuityTimeStamp
            MAX-ACCESS read-only
            STATUS current
            DESCRIPTION
                "See Textual Conventions."
            ::= { etsOutFlowMaintEntry 14 }

        etsOutFlowMaintReset OBJECT-TYPE
            SYNTAX TruthValue
-- TSDnm77175
--            MAX-ACCESS read-only
            MAX-ACCESS read-write
-- TSDnm77175 end
            STATUS current
            DESCRIPTION
                "This object allows to reset, i.e. set to 0, all
                 the OutFlow maintenance counters. Setting this
                 object to true(1) resets all the counters. After this
                 action its value goes back to false(2)."
            ::= { etsOutFlowMaintEntry 15 }

-- per node history data granularity period configuration

        pmHistoryDataGranularityConfiguration OBJECT-TYPE
            SYNTAX Integer32
            MAX-ACCESS read-write
            STATUS current
            DESCRIPTION
                "This object allow to configure the granularity period
                                 for the history data.
                                 The allowed valued are:
                                  - 1: for 15m granularity
                                  - 2: for 1h granularity (default)"
            ::= { opticsIMEthPmMib 19 }


-- received per queue aggregates per queue current datas table
        ethAggrPerQueueCDTable OBJECT-TYPE
            SYNTAX SEQUENCE OF EthAggrPerQueueCDEntry
            MAX-ACCESS not-accessible
            STATUS current
            DESCRIPTION
                "This table contains PM per queue aggregates Current Datas counters."
            ::= { opticsIMEthPmMib 31 }

        ethAggrPerQueueCDEntry OBJECT-TYPE
            SYNTAX EthAggrPerQueueCDEntry
            MAX-ACCESS not-accessible
            STATUS current
            DESCRIPTION
                "An entry of received per queue aggregates Current Data counters table."
            INDEX { ifIndex, ethAggrPerQueueIndex }
            ::= { ethAggrPerQueueCDTable 1 }

        EthAggrPerQueueCDEntry ::=
            SEQUENCE {
                ethAggrPerQueueIndex
                    OpticsIMETSTrafficDescrType,
                ethAggrPerQueueCDTCF
                    Counter64,
                ethAggrPerQueueCDTnCF
                    Counter64,
                ethAggrPerQueueCDDiscardTCF
                    Counter64,
                ethAggrPerQueueCDDiscardTnCF
                    Counter64,
                ethAggrPerQueueCDTCO
                    Counter64,
                ethAggrPerQueueCDTnCO
                    Counter64,
                ethAggrPerQueueCDDiscardTCO
                    Counter64,
                ethAggrPerQueueCDDiscardTnCO
                    Counter64,
                ethAggrPerQueueCDLastDiscontinuityTimeStamp
                    OpticsIMPmLastDiscontinuityTimeStamp,
                ethAggrPerQueueCDStartTime
                    OpticsIMPmStartTime,
                ethAggrPerQueueCDStartByOS
                    TsdimManagerType,
                ethAggrPerQueueCDRowStatus
                    RowStatus,
                ethAggrPerQueueCDResetCounter
                    TruthValue
             }

        ethAggrPerQueueIndex OBJECT-TYPE
            SYNTAX OpticsIMETSTrafficDescrType
            MAX-ACCESS not-accessible
            STATUS current
            DESCRIPTION
                "The index indicate the queue which serve a specific TD type see OpticsIMPmQueueIndex."
            ::= { ethAggrPerQueueCDEntry 2 }

        ethAggrPerQueueCDTCF OBJECT-TYPE
            SYNTAX Counter64
            MAX-ACCESS read-only
            STATUS current
            DESCRIPTION
                "The number of Ethernet conforming frames(green) accepted by the specific queue of this Ethernet interface"
            ::= { ethAggrPerQueueCDEntry 3 }

        ethAggrPerQueueCDTnCF OBJECT-TYPE
            SYNTAX Counter64
            MAX-ACCESS read-only
            STATUS current
            DESCRIPTION
                "The number of Ethernet non conforming frames(yellow) accepted by the specific queue of this Ethernet interface"
            ::= { ethAggrPerQueueCDEntry 4 }

        ethAggrPerQueueCDDiscardTCF OBJECT-TYPE
            SYNTAX Counter64
            MAX-ACCESS read-only
            STATUS current
            DESCRIPTION
                "The number of Discarded Ethernet conforming frames(green) accepted by the specific queue of this Ethernet interface"
            ::= { ethAggrPerQueueCDEntry 5 }

        ethAggrPerQueueCDDiscardTnCF OBJECT-TYPE
            SYNTAX Counter64
            MAX-ACCESS read-only
            STATUS current
            DESCRIPTION
                "The number of Discarded Ethernet non conforming frames(yellow) accepted by the specific queue of this Ethernet interface"
            ::= { ethAggrPerQueueCDEntry 6 }

        ethAggrPerQueueCDTCO OBJECT-TYPE
            SYNTAX Counter64
            MAX-ACCESS read-only
            STATUS current
            DESCRIPTION
                "The number of Ethernet conforming octets (green) accepted by the specific queue of this Ethernet interface"
            ::= { ethAggrPerQueueCDEntry 7 }

        ethAggrPerQueueCDTnCO OBJECT-TYPE
            SYNTAX Counter64
            MAX-ACCESS read-only
            STATUS current
            DESCRIPTION
                "The number of Ethernet non conforming octets (yellow) accepted by the specific queue of this Ethernet interface"
            ::= { ethAggrPerQueueCDEntry 8 }

        ethAggrPerQueueCDDiscardTCO OBJECT-TYPE
            SYNTAX Counter64
            MAX-ACCESS read-only
            STATUS current
            DESCRIPTION
                "The number of Discarded Ethernet conforming octets (green) accepted by the specific queue of this Ethernet interface"
            ::= { ethAggrPerQueueCDEntry 9 }

        ethAggrPerQueueCDDiscardTnCO OBJECT-TYPE
            SYNTAX Counter64
            MAX-ACCESS read-only
            STATUS current
            DESCRIPTION
                "The number of Discarded Ethernet non conforming octets (yellow) accepted by the specific queue of this Ethernet interface"
            ::= { ethAggrPerQueueCDEntry 10 }


        ethAggrPerQueueCDLastDiscontinuityTimeStamp OBJECT-TYPE
            SYNTAX OpticsIMPmLastDiscontinuityTimeStamp
            MAX-ACCESS read-only
            STATUS current
            DESCRIPTION
                "See Textual Conventions."
            ::= { ethAggrPerQueueCDEntry 11 }

        ethAggrPerQueueCDStartTime OBJECT-TYPE
            SYNTAX OpticsIMPmStartTime
            MAX-ACCESS read-create
            STATUS current
            DESCRIPTION
                "See Textual Conventions.
                Even if it is defined as read-create, this objiect cannot be written by manager,
                but only read."
            ::= { ethAggrPerQueueCDEntry 12 }

        ethAggrPerQueueCDStartByOS OBJECT-TYPE
            SYNTAX TsdimManagerType
            MAX-ACCESS read-only
            STATUS current
            DESCRIPTION
                "See Textual Conventions"
            ::= { ethAggrPerQueueCDEntry 13 }

        ethAggrPerQueueCDRowStatus OBJECT-TYPE
            SYNTAX RowStatus
            MAX-ACCESS read-create
            STATUS current
            DESCRIPTION
                "See Textual Conventions"
            ::= { ethAggrPerQueueCDEntry 14 }

        ethAggrPerQueueCDResetCounter OBJECT-TYPE
            SYNTAX TruthValue
            MAX-ACCESS read-create
            STATUS current
            DESCRIPTION
             "This object allows to reset i.e. set to 0, all the curent counters
              for received frames.."
            ::= { ethAggrPerQueueCDEntry 15 }


-- received per queue aggregates history datas table
        ethAggrPerQueueHDTable OBJECT-TYPE
            SYNTAX SEQUENCE OF EthAggrPerQueueHDEntry
            MAX-ACCESS not-accessible
            STATUS current
            DESCRIPTION
                "This table contains received per queue aggregates History Datas counters."
            ::= { opticsIMEthPmMib 32 }

        ethAggrPerQueueHDEntry OBJECT-TYPE
            SYNTAX EthAggrPerQueueHDEntry
            MAX-ACCESS not-accessible
            STATUS current
            DESCRIPTION
                "An entry of received per queue aggregates History Data counters table."
            INDEX { ifIndex, ethAggrPerQueueIndex, ethAggrPerQueueHDGranularityPeriod, ethAggrPerQueueHDPeriodEndtime, ethAggrPerQueueHDIndex }
            ::= { ethAggrPerQueueHDTable 1 }

        EthAggrPerQueueHDEntry ::=
            SEQUENCE {
                ethAggrPerQueueHDGranularityPeriod
                    OpticsIMPmGranularityPeriod,
                ethAggrPerQueueHDPeriodEndtime
                    OpticsIMPmPeriodTime,
                ethAggrPerQueueHDIndex
                    OpticsIMPmIndex,
                ethAggrPerQueueHDTCF
                    Counter64,
                ethAggrPerQueueHDTnCF
                    Counter64,
                ethAggrPerQueueHDDiscardTCF
                    Counter64,
                ethAggrPerQueueHDDiscardTnCF
                    Counter64,
                ethAggrPerQueueHDTCO
                    Counter64,
                ethAggrPerQueueHDTnCO
                    Counter64,
                ethAggrPerQueueHDDiscardTCO
                    Counter64,
                ethAggrPerQueueHDDiscardTnCO
                    Counter64,
                ethAggrPerQueueHDSuspectIntervalFlag
                    OpticsIMPmSuspectIntervalFlag,
                ethAggrPerQueueHDLastDiscontinuityTimeStamp
                    OpticsIMPmLastDiscontinuityTimeStamp,
                ethAggrPerQueueHDStartByOS
                    TsdimManagerType
                  }

        ethAggrPerQueueHDGranularityPeriod OBJECT-TYPE
            SYNTAX OpticsIMPmGranularityPeriod
            MAX-ACCESS not-accessible
            STATUS current
            DESCRIPTION
                "See Textual Conventions."
            ::= { ethAggrPerQueueHDEntry 3 }

        ethAggrPerQueueHDPeriodEndtime OBJECT-TYPE
            SYNTAX OpticsIMPmPeriodTime
            MAX-ACCESS not-accessible
            STATUS current
            DESCRIPTION
                "See Textual Conventions."
            ::= { ethAggrPerQueueHDEntry 4 }

        ethAggrPerQueueHDIndex OBJECT-TYPE
            SYNTAX OpticsIMPmIndex
            MAX-ACCESS not-accessible
            STATUS current
            DESCRIPTION
                "See Textual Conventions.
                "
            ::= { ethAggrPerQueueHDEntry 5 }

        ethAggrPerQueueHDTCF OBJECT-TYPE
            SYNTAX Counter64
            MAX-ACCESS read-only
            STATUS current
            DESCRIPTION
                "The number of Ethernet conforming frames(green) accepted by the specific queue of this Ethernet interface"
            ::= { ethAggrPerQueueHDEntry 6 }

        ethAggrPerQueueHDTnCF OBJECT-TYPE
            SYNTAX Counter64
            MAX-ACCESS read-only
            STATUS current
            DESCRIPTION
                "The number of Ethernet non conforming frames(yellow) accepted by the specific queue of this Ethernet interface"
            ::= { ethAggrPerQueueHDEntry 7 }

        ethAggrPerQueueHDDiscardTCF OBJECT-TYPE
            SYNTAX Counter64
            MAX-ACCESS read-only
            STATUS current
            DESCRIPTION
                "The number of Discarded Ethernet conforming frames(green) accepted by the specific queue of this Ethernet interface"
            ::= { ethAggrPerQueueHDEntry 8 }

        ethAggrPerQueueHDDiscardTnCF OBJECT-TYPE
            SYNTAX Counter64
            MAX-ACCESS read-only
            STATUS current
            DESCRIPTION
                "The number of Discarded Ethernet non conforming frames(yellow) accepted by the specific queue of this Ethernet interface"
            ::= { ethAggrPerQueueHDEntry 9 }

        ethAggrPerQueueHDTCO OBJECT-TYPE
            SYNTAX Counter64
            MAX-ACCESS read-only
            STATUS current
            DESCRIPTION
                "The number of Ethernet conforming octets (green) accepted by the specific queue of this Ethernet interface"
            ::= { ethAggrPerQueueHDEntry 10 }

        ethAggrPerQueueHDTnCO OBJECT-TYPE
            SYNTAX Counter64
            MAX-ACCESS read-only
            STATUS current
            DESCRIPTION
                "The number of Ethernet non conforming octets (yellow) accepted by the specific queue of this Ethernet interface"
            ::= { ethAggrPerQueueHDEntry 11 }

        ethAggrPerQueueHDDiscardTCO OBJECT-TYPE
            SYNTAX Counter64
            MAX-ACCESS read-only
            STATUS current
            DESCRIPTION
                "The number of Discarded Ethernet conforming octets (green) accepted by the specific queue of this Ethernet interface"
            ::= { ethAggrPerQueueHDEntry 12 }

        ethAggrPerQueueHDDiscardTnCO OBJECT-TYPE
            SYNTAX Counter64
            MAX-ACCESS read-only
            STATUS current
            DESCRIPTION
                "The number of Discarded Ethernet non conforming octets (yellow) accepted by the specific queue of this Ethernet interface"
            ::= { ethAggrPerQueueHDEntry 13 }


        ethAggrPerQueueHDSuspectIntervalFlag OBJECT-TYPE
            SYNTAX OpticsIMPmSuspectIntervalFlag
            MAX-ACCESS read-only
            STATUS current
            DESCRIPTION
                "See Textual Conventions."
            ::= { ethAggrPerQueueHDEntry 14 }

        ethAggrPerQueueHDLastDiscontinuityTimeStamp OBJECT-TYPE
            SYNTAX OpticsIMPmLastDiscontinuityTimeStamp
            MAX-ACCESS read-only
            STATUS current
            DESCRIPTION
                "See Textual Conventions."
            ::= { ethAggrPerQueueHDEntry 15 }

        ethAggrPerQueueHDStartByOS OBJECT-TYPE
            SYNTAX TsdimManagerType
            MAX-ACCESS read-only
            STATUS current
            DESCRIPTION
                "See Textual Conventions."
            ::= { ethAggrPerQueueHDEntry 16 }



-- received per queue aggregates counters table for maintenance pourpose.
        ethAggrPerQueueMaintTable OBJECT-TYPE
            SYNTAX SEQUENCE OF EthAggrPerQueueMaintEntry
            MAX-ACCESS not-accessible
            STATUS current
            DESCRIPTION
                "This table contains received per queue aggregates maintenance counters."
            ::= { opticsIMEthPmMib 39 }

        ethAggrPerQueueMaintEntry OBJECT-TYPE
            SYNTAX EthAggrPerQueueMaintEntry
            MAX-ACCESS not-accessible
            STATUS current
            DESCRIPTION
                "An entry of received per queue aggregates maintenance counters table."
            INDEX { ifIndex, ethAggrPerQueueIndex }
            ::= { ethAggrPerQueueMaintTable 1 }

        EthAggrPerQueueMaintEntry ::=
            SEQUENCE {

                ethAggrPerQueueMaintTCF
                    Counter64,
                ethAggrPerQueueMaintTnCF
                    Counter64,
                ethAggrPerQueueMaintDiscardTCF
                    Counter64,
                ethAggrPerQueueMaintDiscardTnCF
                    Counter64,
                ethAggrPerQueueMaintTCO
                    Counter64,
                ethAggrPerQueueMaintTnCO
                    Counter64,
                ethAggrPerQueueMaintDiscardTCO
                    Counter64,
                ethAggrPerQueueMaintDiscardTnCO
                    Counter64,
                ethAggrPerQueueMaintLastDiscontinuityTimeStamp
                    OpticsIMPmLastDiscontinuityTimeStamp,
                ethAggrPerQueueMaintRetrievingTime
                    OpticsIMPmRetrievingTime,
                                ethAggrPerQueueMaintCompressedTCO
                    Counter64
             }


        ethAggrPerQueueMaintTCF OBJECT-TYPE
            SYNTAX Counter64
            MAX-ACCESS read-only
            STATUS current
            DESCRIPTION
                "The number of Ethernet conforming frames(green) accepted by the specific queue of this Ethernet interface"
            ::= { ethAggrPerQueueMaintEntry 3 }

        ethAggrPerQueueMaintTnCF OBJECT-TYPE
            SYNTAX Counter64
            MAX-ACCESS read-only
            STATUS current
            DESCRIPTION
                "The number of Ethernet non conforming frames(yellow) accepted by the specific queue of this Ethernet interface"
            ::= { ethAggrPerQueueMaintEntry 4 }

        ethAggrPerQueueMaintDiscardTCF OBJECT-TYPE
            SYNTAX Counter64
            MAX-ACCESS read-only
            STATUS current
            DESCRIPTION
                "The number of Discarded Ethernet conforming frames(green) accepted by the specific queue of this Ethernet interface"
            ::= { ethAggrPerQueueMaintEntry 5 }

        ethAggrPerQueueMaintDiscardTnCF OBJECT-TYPE
            SYNTAX Counter64
            MAX-ACCESS read-only
            STATUS current
            DESCRIPTION
                "The number of Discarded Ethernet non conforming frames(yellow) accepted by the specific queue of this Ethernet interface"
            ::= { ethAggrPerQueueMaintEntry 6 }

        ethAggrPerQueueMaintTCO OBJECT-TYPE
            SYNTAX Counter64
            MAX-ACCESS read-only
            STATUS current
            DESCRIPTION
                "The number of Ethernet conforming octets (green) accepted by the specific queue of this Ethernet interface"
            ::= { ethAggrPerQueueMaintEntry 7 }

        ethAggrPerQueueMaintTnCO OBJECT-TYPE
            SYNTAX Counter64
            MAX-ACCESS read-only
            STATUS current
            DESCRIPTION
                "The number of Ethernet non conforming octets (yellow) accepted by the specific queue of this Ethernet interface"
            ::= { ethAggrPerQueueMaintEntry 8 }

        ethAggrPerQueueMaintDiscardTCO OBJECT-TYPE
            SYNTAX Counter64
            MAX-ACCESS read-only
            STATUS current
            DESCRIPTION
                "The number of Discarded Ethernet conforming octets (green) accepted by the specific queue of this Ethernet interface"
            ::= { ethAggrPerQueueMaintEntry 9 }

        ethAggrPerQueueMaintDiscardTnCO OBJECT-TYPE
            SYNTAX Counter64
            MAX-ACCESS read-only
            STATUS current
            DESCRIPTION
                "The number of Discarded Ethernet non conforming octets (yellow) accepted by the specific queue of this Ethernet interface"
            ::= { ethAggrPerQueueMaintEntry 10 }


        ethAggrPerQueueMaintLastDiscontinuityTimeStamp OBJECT-TYPE
            SYNTAX OpticsIMPmLastDiscontinuityTimeStamp
            MAX-ACCESS read-only
            STATUS current
            DESCRIPTION
                "See Textual Conventions."
            ::= { ethAggrPerQueueMaintEntry 11 }

        ethAggrPerQueueMaintRetrievingTime OBJECT-TYPE
            SYNTAX OpticsIMPmRetrievingTime
            MAX-ACCESS read-only
            STATUS current
            DESCRIPTION
                "See Textual Conventions."
            ::= { ethAggrPerQueueMaintEntry 12 }

        ethAggrPerQueueMaintCompressedTCO OBJECT-TYPE
            SYNTAX Counter64
            MAX-ACCESS read-only
            STATUS current
            DESCRIPTION
                "The number of Ethernet conforming octets (green) at the egress of the compression module accepted by
                                 the specific queue of this Ethernet interface"
            ::= { ethAggrPerQueueMaintEntry 13 }


-- ---- BEGIN Enhanced PM Counters -------------------------------------------------------------

-- Enhanced Aggregate Rx current datas table

        enhEthAggrCDRxTable OBJECT-TYPE
            SYNTAX SEQUENCE OF EnhEthAggrCDRxEntry
            MAX-ACCESS not-accessible
            STATUS current
            DESCRIPTION
            "This table contains received enhanced aggregates Current Datas counters."
            ::= { opticsIMEthPmMib 40 }

        enhEthAggrCDRxEntry OBJECT-TYPE
            SYNTAX EnhEthAggrCDRxEntry
            MAX-ACCESS not-accessible
            STATUS current
            DESCRIPTION
            "An entry of received enhanced aggregates Current Data counters table."
            INDEX { ifIndex, enhEthAggrCDRxGranularityPeriod }
            ::= { enhEthAggrCDRxTable 1 }

        EnhEthAggrCDRxEntry ::=
            SEQUENCE {
                enhEthAggrCDRxGranularityPeriod             OpticsIMPmGranularityPeriod,
                enhEthAggrCDRxEINF                     Counter64,
                enhEthAggrCDRxEINB                     Counter64,
                enhEthAggrCDRxEINFUnicast             Counter64,
                enhEthAggrCDRxEINFMulticast         Counter64,
                enhEthAggrCDRxEINFBroadcast         Counter64,
                enhEthAggrCDRxEIFE                     Counter64,
                enhEthAggrCDRxTUF                     Counter64,
                enhEthAggrCDRxTDF                     Counter64,
                enhEthAggrCDRxStartByOS             TsdimManagerType,
                enhEthAggrCDRxResetCounter             TruthValue,
                enhEthAggrCDRxRowStatus             RowStatus,
                enhEthAggrCDRxSuspectInterval         OpticsIMPmSuspectIntervalFlag,
                enhEthAggrCDRxElapsedTime             OpticsIMPmElapsedTime,
                enhEthAggrCDRxThresholdDataInstance OpticsIMPmThresholdDataInstance,

                enhEthAggrCDRxEINBRate                    Counter64,
                                enhEthAggrCDRxEINBRatio                    Counter64,
                                enhEthAggrCDRxEIFERatio                    Counter64,
                enhEthAggrCDRxTDFRatio                    Counter64

             }

        enhEthAggrCDRxGranularityPeriod OBJECT-TYPE
            SYNTAX OpticsIMPmGranularityPeriod
            MAX-ACCESS not-accessible
            STATUS current
            DESCRIPTION
            "See Textual Conventions."
            ::= { enhEthAggrCDRxEntry 1 }

        enhEthAggrCDRxEINF OBJECT-TYPE
            SYNTAX Counter64
            MAX-ACCESS read-only
            STATUS current
            DESCRIPTION
            "The number of Ethernet frames received correctly by the Virtual Ethernet Interface."
            ::= { enhEthAggrCDRxEntry 2 }

        enhEthAggrCDRxEINB OBJECT-TYPE
            SYNTAX Counter64
            MAX-ACCESS read-only
            STATUS current
            DESCRIPTION
            "The number of octets of Ethernet frames received correctly by the Virtual Ethernet Interface, including Ethernet headers characters"
            ::= { enhEthAggrCDRxEntry 3 }

        enhEthAggrCDRxEINFUnicast OBJECT-TYPE
            SYNTAX Counter64
            MAX-ACCESS read-only
            STATUS current
            DESCRIPTION
            "The collected number of Ethernet Unicast frames received correctly by the Virtual Ethernet Interface."
            ::= { enhEthAggrCDRxEntry 4 }

        enhEthAggrCDRxEINFMulticast OBJECT-TYPE
            SYNTAX Counter64
            MAX-ACCESS read-only
            STATUS current
            DESCRIPTION
            "The collected number of Ethernet Multicast frames received
             correctly by the Virtual Ethernet Interface."
            ::= { enhEthAggrCDRxEntry 5 }

        enhEthAggrCDRxEINFBroadcast OBJECT-TYPE
            SYNTAX Counter64
            MAX-ACCESS read-only
            STATUS current
            DESCRIPTION
            "The collected number of Ethernet Broadcast frames received
             correctly by the Virtual Ethernet Interface."
            ::= { enhEthAggrCDRxEntry 6 }

        enhEthAggrCDRxEIFE OBJECT-TYPE
            SYNTAX Counter64
            MAX-ACCESS read-only
            STATUS current
            DESCRIPTION
            "This object is the collection of the sum of three contributions: dot3StatsAlignmentErrors, dot3StatsFCSErrors and dot3StatsFrameTooLongs."
            ::= { enhEthAggrCDRxEntry 7 }

        enhEthAggrCDRxTUF OBJECT-TYPE
            SYNTAX Counter64
            MAX-ACCESS read-only
            STATUS current
            DESCRIPTION
            "This object is the collection of TUF frames"
            ::= { enhEthAggrCDRxEntry 8 }

        enhEthAggrCDRxStartByOS OBJECT-TYPE
            SYNTAX TsdimManagerType
            MAX-ACCESS read-only
            STATUS current
            DESCRIPTION
            "See Textual Conventions"
            ::= { enhEthAggrCDRxEntry 9 }

        enhEthAggrCDRxResetCounter OBJECT-TYPE
            SYNTAX TruthValue
            MAX-ACCESS read-create
            STATUS current
            DESCRIPTION
            "This object allows to reset i.e. set to 0, all the curent counters
              for received frames."
            ::= { enhEthAggrCDRxEntry 10 }

        enhEthAggrCDRxRowStatus OBJECT-TYPE
            SYNTAX RowStatus
            MAX-ACCESS read-create
            STATUS current
            DESCRIPTION
            "This object is used to create a new row or modify or
             delete an existing row in this table."
            ::= { enhEthAggrCDRxEntry 11 }

        enhEthAggrCDRxTDF OBJECT-TYPE
            SYNTAX Counter64
            MAX-ACCESS read-only
            STATUS current
            DESCRIPTION
            "The number of Ethernet frames which where choosen to be discarded due to buffer congestion."
            ::= { enhEthAggrCDRxEntry 12 }

    enhEthAggrCDRxSuspectInterval     OBJECT-TYPE
            SYNTAX OpticsIMPmSuspectIntervalFlag
            MAX-ACCESS read-only
            STATUS current
            DESCRIPTION
              "See Textual Conventions."
            ::= { enhEthAggrCDRxEntry 13 }

    enhEthAggrCDRxElapsedTime     OBJECT-TYPE
            SYNTAX OpticsIMPmElapsedTime
            MAX-ACCESS read-only
            STATUS current
            DESCRIPTION
                       "See Textual Conventions."
            ::= { enhEthAggrCDRxEntry 14 }

      enhEthAggrCDRxThresholdDataInstance OBJECT-TYPE
            SYNTAX  OpticsIMPmThresholdDataInstance
             MAX-ACCESS    read-write
             STATUS        current
             DESCRIPTION
               "This is a pointer to Enhanced Aggregate PM Threshold Data."
            ::= { enhEthAggrCDRxEntry 15 }

     enhEthAggrCDRxEINBRate OBJECT-TYPE
                  SYNTAX  Counter64
                 MAX-ACCESS    read-only
                 STATUS        current
                 DESCRIPTION
            "The rate of the received good bytes (in Mbps)"
             ::= { enhEthAggrCDRxEntry 16 }


    enhEthAggrCDRxEINBRatio OBJECT-TYPE
                  SYNTAX  Counter64
                 MAX-ACCESS    read-only
                 STATUS        current
                 DESCRIPTION
            "The Ratio (throughput) of received good bytes"
                 ::= { enhEthAggrCDRxEntry 17 }


    enhEthAggrCDRxEIFERatio OBJECT-TYPE
                  SYNTAX  Counter64
                 MAX-ACCESS    read-only
                 STATUS        current
                 DESCRIPTION
            "The Ratio of received packets with service error"
                 ::= { enhEthAggrCDRxEntry 18 }

    enhEthAggrCDRxTDFRatio OBJECT-TYPE
                  SYNTAX  Counter64
                 MAX-ACCESS    read-only
                 STATUS        current
                 DESCRIPTION
            "The Ratio of packets dropped due to lack of resources"
                 ::= { enhEthAggrCDRxEntry 19 }




----
-- Enhanced Aggregate Rx history datas table

        enhEthAggrHDRxTable OBJECT-TYPE
            SYNTAX SEQUENCE OF EnhEthAggrHDRxEntry
            MAX-ACCESS not-accessible
            STATUS current
            DESCRIPTION
            "This table contains received enhanced aggregates History Datas counters."
            ::= { opticsIMEthPmMib 41 }

        enhEthAggrHDRxEntry OBJECT-TYPE
            SYNTAX EnhEthAggrHDRxEntry
            MAX-ACCESS not-accessible
            STATUS current
            DESCRIPTION
            "An entry of received enhanced aggregates History Data counters table."
            INDEX { ifIndex, enhEthAggrHDRxGranularityPeriod, enhEthAggrHDRxPeriodEndtime,
                    enhEthAggrHDRxIndex }
            ::= { enhEthAggrHDRxTable 1 }

        EnhEthAggrHDRxEntry ::=
            SEQUENCE {
                enhEthAggrHDRxGranularityPeriod             OpticsIMPmGranularityPeriod,
                enhEthAggrHDRxPeriodEndtime                 OpticsIMPmPeriodTime,
                enhEthAggrHDRxIndex                     OpticsIMPmIndex,
                enhEthAggrHDRxEINF                     Counter64,
                enhEthAggrHDRxEINB                     Counter64,
                   enhEthAggrHDRxSuspectIntervalFlag             OpticsIMPmSuspectIntervalFlag,
                enhEthAggrHDRxStartByOS                 TsdimManagerType,
                enhEthAggrHDRxEINFUnicast                 Counter64,
                enhEthAggrHDRxEINFMulticast                 Counter64,
                enhEthAggrHDRxEINFBroadcast                 Counter64,
                enhEthAggrHDRxEIFE                     Counter64,
                   enhEthAggrHDRxTUF                     Counter64,
                enhEthAggrHDRxTDF                     Counter64,
                enhEthAggrHDRxElapsedTime                 OpticsIMPmElapsedTime,

                enhEthAggrHDRxEINBRate                     Counter64,
                 enhEthAggrHDRxEINBRatio                    Counter64,
                enhEthAggrHDRxEIFERatio                    Counter64,
                 enhEthAggrHDRxTDFRatio                    Counter64

             }

        enhEthAggrHDRxGranularityPeriod OBJECT-TYPE
            SYNTAX OpticsIMPmGranularityPeriod
            MAX-ACCESS not-accessible
            STATUS current
            DESCRIPTION
            "See Textual Conventions."
            ::= { enhEthAggrHDRxEntry 1 }

        enhEthAggrHDRxPeriodEndtime OBJECT-TYPE
            SYNTAX OpticsIMPmPeriodTime
            MAX-ACCESS not-accessible
            STATUS current
            DESCRIPTION
            "See Textual Conventions."
            ::= { enhEthAggrHDRxEntry 2 }

        enhEthAggrHDRxIndex OBJECT-TYPE
            SYNTAX OpticsIMPmIndex
            MAX-ACCESS not-accessible
            STATUS current
            DESCRIPTION
            "See Textual Conventions."
            ::= { enhEthAggrHDRxEntry 3 }

        enhEthAggrHDRxEINF OBJECT-TYPE
            SYNTAX Counter64
            MAX-ACCESS read-only
            STATUS current
            DESCRIPTION
            "The number of Ethernet frames received correctly by the Virtual Ethernet Interface."
            ::= { enhEthAggrHDRxEntry 4 }

        enhEthAggrHDRxEINB OBJECT-TYPE
            SYNTAX Counter64
            MAX-ACCESS read-only
            STATUS current
            DESCRIPTION
            "The number of octets of Ethernet frames received correctly by the Virtual Ethernet Interface, including Ethernet headers characters"
            ::= { enhEthAggrHDRxEntry 5 }

        enhEthAggrHDRxSuspectIntervalFlag OBJECT-TYPE
            SYNTAX OpticsIMPmSuspectIntervalFlag
            MAX-ACCESS read-only
            STATUS current
            DESCRIPTION
            "See Textual Conventions."
            ::= { enhEthAggrHDRxEntry 6 }

        enhEthAggrHDRxStartByOS OBJECT-TYPE
            SYNTAX TsdimManagerType
            MAX-ACCESS read-only
            STATUS current
            DESCRIPTION
            "See Textual Conventions."
            ::= { enhEthAggrHDRxEntry 7 }

        enhEthAggrHDRxEINFUnicast OBJECT-TYPE
            SYNTAX Counter64
            MAX-ACCESS read-only
            STATUS current
            DESCRIPTION
            "The collected number of Ethernet Unicast frames received correctly by the Virtual Ethernet Interface."
            ::= { enhEthAggrHDRxEntry 8 }

        enhEthAggrHDRxEINFMulticast OBJECT-TYPE
            SYNTAX Counter64
            MAX-ACCESS read-only
            STATUS current
            DESCRIPTION
            "The collected number of Ethernet Multicast frames received
             correctly by the Virtual Ethernet Interface."
            ::= { enhEthAggrHDRxEntry 9 }

        enhEthAggrHDRxEINFBroadcast OBJECT-TYPE
            SYNTAX Counter64
            MAX-ACCESS read-only
            STATUS current
            DESCRIPTION
            "The collected number of Ethernet Broadcast frames received
             correctly by the Virtual Ethernet Interface."
            ::= { enhEthAggrHDRxEntry 10 }

        enhEthAggrHDRxEIFE OBJECT-TYPE
            SYNTAX Counter64
            MAX-ACCESS read-only
            STATUS current
            DESCRIPTION
            "This object is the collection of the sum of three contributions: dot3StatsAlignmentErrors, dot3StatsFCSErrors and dot3StatsFrameTooLongs."
            ::= { enhEthAggrHDRxEntry 11 }

        enhEthAggrHDRxTUF OBJECT-TYPE
            SYNTAX Counter64
            MAX-ACCESS read-only
            STATUS current
            DESCRIPTION
            "This object is the collection of TUF frames"
            ::= { enhEthAggrHDRxEntry 12 }

         enhEthAggrHDRxTDF OBJECT-TYPE
            SYNTAX Counter64
            MAX-ACCESS read-only
            STATUS current
            DESCRIPTION
            "This object is the collected number of Ethernet frames which where choosen to be discarded due to buffer congestion."
            ::= { enhEthAggrHDRxEntry 13 }

        enhEthAggrHDRxElapsedTime     OBJECT-TYPE
            SYNTAX OpticsIMPmElapsedTime
            MAX-ACCESS read-only
            STATUS current
            DESCRIPTION
                       "See Textual Conventions."
            ::= { enhEthAggrHDRxEntry 14 }

    enhEthAggrHDRxEINBRate                     OBJECT-TYPE
            SYNTAX Counter64
            MAX-ACCESS read-only
            STATUS current
            DESCRIPTION
           "The rate of the received good bytes (in Mbps)"
            ::= { enhEthAggrHDRxEntry 15 }

    enhEthAggrHDRxEINBRatio                    OBJECT-TYPE
            SYNTAX Counter64
            MAX-ACCESS read-only
            STATUS current
            DESCRIPTION
           "The Ratio (throughput) of received good bytes"
            ::= { enhEthAggrHDRxEntry 16 }

     enhEthAggrHDRxEIFERatio                    OBJECT-TYPE
            SYNTAX Counter64
            MAX-ACCESS read-only
            STATUS current
            DESCRIPTION
            "The Ratio of received packets with service error"
            ::= { enhEthAggrHDRxEntry 17 }

    enhEthAggrHDRxTDFRatio                    OBJECT-TYPE
            SYNTAX Counter64
            MAX-ACCESS read-only
            STATUS current
            DESCRIPTION
                  "The Ratio of packets dropped due to lack of resources"
            ::= { enhEthAggrHDRxEntry 18 }


-----------
-- Enhanced Aggregate Tx current datas table

        enhEthAggrCDTxTable OBJECT-TYPE
            SYNTAX SEQUENCE OF EnhEthAggrCDTxEntry
            MAX-ACCESS not-accessible
            STATUS current
            DESCRIPTION
            "This table contains enhanced transmitted aggregates Current Datas counters."
            ::= { opticsIMEthPmMib 42 }

        enhEthAggrCDTxEntry OBJECT-TYPE
            SYNTAX EnhEthAggrCDTxEntry
            MAX-ACCESS not-accessible
            STATUS current
            DESCRIPTION
            "An entry of enhanced transmitted aggregates Current Data counters table."
            INDEX { ifIndex, enhEthAggrCDTxGranularityPeriod }
            ::= { enhEthAggrCDTxTable 1 }

        EnhEthAggrCDTxEntry ::=
            SEQUENCE {
                enhEthAggrCDTxGranularityPeriod         OpticsIMPmGranularityPeriod,
                enhEthAggrCDTxEONF                 Counter64,
                enhEthAggrCDTxEONB                 Counter64,
                enhEthAggrCDTxEONFUnicast             Counter64,
                enhEthAggrCDTxEONFMulticast             Counter64,
                enhEthAggrCDTxEONFBroadcast             Counter64,
                   enhEthAggrCDTxStartByOS             TsdimManagerType,
                enhEthAggrCDTxResetCounter             TruthValue,
                   enhEthAggrCDTxRowStatus                         RowStatus,
                enhEthAggrCDTxSuspectInterval             OpticsIMPmSuspectIntervalFlag,
                enhEthAggrCDTxElapsedTime             OpticsIMPmElapsedTime,
                enhEthAggrCDTxTDF                 Counter64,
                enhEthAggrCDTxThresholdDataInstance       OpticsIMPmThresholdDataInstance,

                enhEthAggrCDTxEONBRate                 Counter64,
                enhEthAggrCDTxEONBRatio                Counter64,
                enhEthAggrCDTxTDFRatio                Counter64

               }

        enhEthAggrCDTxGranularityPeriod OBJECT-TYPE
            SYNTAX OpticsIMPmGranularityPeriod
            MAX-ACCESS not-accessible
            STATUS current
            DESCRIPTION
            "See Textual Conventions."
            ::= { enhEthAggrCDTxEntry 1 }

        enhEthAggrCDTxEONF OBJECT-TYPE
            SYNTAX Counter64
            MAX-ACCESS read-only
            STATUS current
            DESCRIPTION
            "The number of Ethernet frames transmitted out by the Virtual Ethernet Interface."
            ::= { enhEthAggrCDTxEntry 2 }

        enhEthAggrCDTxEONB OBJECT-TYPE
            SYNTAX Counter64
            MAX-ACCESS read-only
            STATUS current
            DESCRIPTION
            "The number of octets of Ethernet frames transmitted out by the Virtual Ethernet Interface, including Ethernet headers characters"
            ::= { enhEthAggrCDTxEntry 3 }

        enhEthAggrCDTxEONFUnicast OBJECT-TYPE
            SYNTAX Counter64
            MAX-ACCESS read-only
            STATUS current
            DESCRIPTION
            "The collected number of Ethernet Unicast frames transmitted out by the Virtual Ethernet Interface."
            ::= { enhEthAggrCDTxEntry 4 }

        enhEthAggrCDTxEONFMulticast OBJECT-TYPE
            SYNTAX Counter64
            MAX-ACCESS read-only
            STATUS current
            DESCRIPTION
            "The collected number of Ethernet Multicast frames transmitted
             out by the Virtual Ethernet Interface."
            ::= { enhEthAggrCDTxEntry 5 }

        enhEthAggrCDTxEONFBroadcast OBJECT-TYPE
            SYNTAX Counter64
            MAX-ACCESS read-only
            STATUS current
            DESCRIPTION
            "The collected number of Ethernet Broadcast frames transmitted out by the Virtual Ethernet Interface."
            ::= { enhEthAggrCDTxEntry 6 }

        enhEthAggrCDTxStartByOS OBJECT-TYPE
            SYNTAX TsdimManagerType
            MAX-ACCESS read-only
            STATUS current
            DESCRIPTION
            "See Textual Conventions"
            ::= { enhEthAggrCDTxEntry 7 }

        enhEthAggrCDTxResetCounter OBJECT-TYPE
            SYNTAX TruthValue
            MAX-ACCESS read-create
            STATUS current
            DESCRIPTION
            "This object allows to reset i.e. set to 0, all the curent counters
             for transmitted frames."
            ::= { enhEthAggrCDTxEntry 8 }

        enhEthAggrCDTxRowStatus OBJECT-TYPE
            SYNTAX RowStatus
            MAX-ACCESS read-create
            STATUS current
            DESCRIPTION
            "This object is used to create a new row or modify or
             delete an existing row in this table."
            ::= { enhEthAggrCDTxEntry 9 }

    enhEthAggrCDTxSuspectInterval     OBJECT-TYPE
            SYNTAX OpticsIMPmSuspectIntervalFlag
            MAX-ACCESS read-only
            STATUS current
            DESCRIPTION
              "See Textual Conventions."
            ::= { enhEthAggrCDTxEntry 10 }

    enhEthAggrCDTxElapsedTime     OBJECT-TYPE
            SYNTAX OpticsIMPmElapsedTime
            MAX-ACCESS read-only
            STATUS current
            DESCRIPTION
                       "See Textual Conventions."
            ::= { enhEthAggrCDTxEntry 11 }

    enhEthAggrCDTxTDF OBJECT-TYPE
            SYNTAX Counter64
            MAX-ACCESS read-only
            STATUS current
            DESCRIPTION
                       "The number of Ethernet frames which where choosen to be discarded due to buffer congestion "
            ::= { enhEthAggrCDTxEntry 12 }

       enhEthAggrCDTxThresholdDataInstance OBJECT-TYPE
                  SYNTAX  OpticsIMPmThresholdDataInstance
                 MAX-ACCESS    read-write
                 STATUS        current
                 DESCRIPTION
                        "This is a pointer to Enhanced Aggregate PM Threshold Data."
                  ::= { enhEthAggrCDTxEntry 13 }

    enhEthAggrCDTxEONBRate OBJECT-TYPE
            SYNTAX Counter64
            MAX-ACCESS read-only
            STATUS current
            DESCRIPTION
            "The Rate of transmitted good bytes (in Mbps)"
            ::= { enhEthAggrCDTxEntry 14 }

    enhEthAggrCDTxEONBRatio OBJECT-TYPE
            SYNTAX Counter64
            MAX-ACCESS read-only
            STATUS current
            DESCRIPTION
            "The Ratio (throughput) of transmitted good bytes"
            ::= { enhEthAggrCDTxEntry 15 }

    enhEthAggrCDTxTDFRatio OBJECT-TYPE
                  SYNTAX  Counter64
                 MAX-ACCESS    read-only
                 STATUS        current
                 DESCRIPTION
            "The Ratio of packets dropped due to lack of resources"
                 ::= { enhEthAggrCDTxEntry 16 }



-- Enhanced Aggregate Tx history datas table

        enhEthAggrHDTxTable OBJECT-TYPE
            SYNTAX SEQUENCE OF EnhEthAggrHDTxEntry
            MAX-ACCESS not-accessible
            STATUS current
            DESCRIPTION
            "This table contains enhanced transmitted aggregates History Datas counters."
            ::= { opticsIMEthPmMib 43 }

        enhEthAggrHDTxEntry OBJECT-TYPE
            SYNTAX EnhEthAggrHDTxEntry
            MAX-ACCESS not-accessible
            STATUS current
            DESCRIPTION
            "An entry of enhanced transmitted aggregates History Data counters table."
            INDEX { ifIndex, enhEthAggrHDTxGranularityPeriod, enhEthAggrHDTxPeriodEndtime,
                    enhEthAggrHDTxIndex }
            ::= { enhEthAggrHDTxTable 1 }

        EnhEthAggrHDTxEntry ::=
            SEQUENCE {
                enhEthAggrHDTxGranularityPeriod             OpticsIMPmGranularityPeriod,
                enhEthAggrHDTxPeriodEndtime                 OpticsIMPmPeriodTime,
                enhEthAggrHDTxIndex                     OpticsIMPmIndex,
                enhEthAggrHDTxEONF                     Counter64,
                enhEthAggrHDTxEONB                     Counter64,
                enhEthAggrHDTxSuspectIntervalFlag             OpticsIMPmSuspectIntervalFlag,
                enhEthAggrHDTxStartByOS                 TsdimManagerType,
                enhEthAggrHDTxEONFUnicast                 Counter64,
                enhEthAggrHDTxEONFMulticast                 Counter64,
                enhEthAggrHDTxEONFBroadcast                 Counter64,
                enhEthAggrHDTxElapsedTime                 OpticsIMPmElapsedTime,
                enhEthAggrHDTxTDF                           Counter64,

                      enhEthAggrHDTxEONBRate                     Counter64,
                enhEthAggrHDTxEONBRatio                    Counter64,
                enhEthAggrHDTxTDFRatio                    Counter64
                     }

        enhEthAggrHDTxGranularityPeriod OBJECT-TYPE
            SYNTAX OpticsIMPmGranularityPeriod
            MAX-ACCESS not-accessible
            STATUS current
            DESCRIPTION
            "See Textual Conventions."
            ::= { enhEthAggrHDTxEntry 1 }

        enhEthAggrHDTxPeriodEndtime OBJECT-TYPE
            SYNTAX OpticsIMPmPeriodTime
            MAX-ACCESS not-accessible
            STATUS current
            DESCRIPTION
            "See Textual Conventions."
            ::= { enhEthAggrHDTxEntry 2 }

        enhEthAggrHDTxIndex OBJECT-TYPE
            SYNTAX OpticsIMPmIndex
            MAX-ACCESS not-accessible
            STATUS current
            DESCRIPTION
            "See Textual Conventions."
            ::= { enhEthAggrHDTxEntry 3 }

        enhEthAggrHDTxEONF OBJECT-TYPE
            SYNTAX Counter64
            MAX-ACCESS read-only
            STATUS current
            DESCRIPTION
            "The number of Ethernet frames transmitted out by the Virtual Ethernet Interface."
            ::= { enhEthAggrHDTxEntry 4 }

        enhEthAggrHDTxEONB OBJECT-TYPE
            SYNTAX Counter64
            MAX-ACCESS read-only
            STATUS current
            DESCRIPTION
            "The number of octets of Ethernet frames transmitted out by the Virtual Ethernet Interface, including Ethernet headers characters"
            ::= { enhEthAggrHDTxEntry 5 }

        enhEthAggrHDTxSuspectIntervalFlag OBJECT-TYPE
            SYNTAX OpticsIMPmSuspectIntervalFlag
            MAX-ACCESS read-only
            STATUS current
            DESCRIPTION
            "See Textual Conventions."
            ::= { enhEthAggrHDTxEntry 6 }

        enhEthAggrHDTxStartByOS OBJECT-TYPE
            SYNTAX TsdimManagerType
            MAX-ACCESS read-only
            STATUS current
            DESCRIPTION
            "See Textual Conventions."
            ::= { enhEthAggrHDTxEntry 7 }

        enhEthAggrHDTxEONFUnicast OBJECT-TYPE
            SYNTAX Counter64
            MAX-ACCESS read-only
            STATUS current
            DESCRIPTION
            "The collected number of Ethernet Unicast frames transmitted out by the Virtual Ethernet Interface."
            ::= { enhEthAggrHDTxEntry 8 }

        enhEthAggrHDTxEONFMulticast OBJECT-TYPE
            SYNTAX Counter64
            MAX-ACCESS read-only
            STATUS current
            DESCRIPTION
            "The collected number of Ethernet Multicast frames transmitted
             out by the Virtual Ethernet Interface."
            ::= { enhEthAggrHDTxEntry 9 }

        enhEthAggrHDTxEONFBroadcast OBJECT-TYPE
            SYNTAX Counter64
            MAX-ACCESS read-only
            STATUS current
            DESCRIPTION
            "The collected number of Ethernet Broadcast frames transmitted out by the Virtual Ethernet Interface."
            ::= { enhEthAggrHDTxEntry 10 }

        enhEthAggrHDTxElapsedTime     OBJECT-TYPE
            SYNTAX OpticsIMPmElapsedTime
            MAX-ACCESS read-only
            STATUS current
            DESCRIPTION
                       "See Textual Conventions."
            ::= { enhEthAggrHDTxEntry 11 }

        enhEthAggrHDTxTDF OBJECT-TYPE
            SYNTAX Counter64
            MAX-ACCESS read-only
            STATUS current
            DESCRIPTION
                       "The number of Ethernet frames which where choosen to be discarded due to buffer congestion "
            ::= { enhEthAggrHDTxEntry 12 }

        enhEthAggrHDTxEONBRate                     OBJECT-TYPE
            SYNTAX Counter64
            MAX-ACCESS read-only
            STATUS current
            DESCRIPTION
                   "The Rate of transmitted good bytes (in Mbps)"
            ::= { enhEthAggrHDTxEntry 13 }

        enhEthAggrHDTxEONBRatio                    OBJECT-TYPE
            SYNTAX Counter64
            MAX-ACCESS read-only
            STATUS current
            DESCRIPTION
             "The Ratio (throughput) of transmitted good bytes"
            ::= { enhEthAggrHDTxEntry 14 }

        enhEthAggrHDTxTDFRatio                    OBJECT-TYPE
            SYNTAX Counter64
            MAX-ACCESS read-only
            STATUS current
            DESCRIPTION
                  "The Ratio of packets dropped due to lack of resources"
            ::= { enhEthAggrHDTxEntry 15 }




-- Enhanced received aggregates counters table for maintenance pourpose.

        enhEthAggrMaintRxTable OBJECT-TYPE
            SYNTAX SEQUENCE OF EnhEthAggrMaintRxEntry
            MAX-ACCESS not-accessible
            STATUS current
            DESCRIPTION
                "This table contains enhanced received aggregates maintenance counters."
            ::= { opticsIMEthPmMib 48 }

        enhEthAggrMaintRxEntry OBJECT-TYPE
            SYNTAX EnhEthAggrMaintRxEntry
            MAX-ACCESS not-accessible
            STATUS current
            DESCRIPTION
                "An entry of enhanced received aggregates maintenance counters table."
            INDEX { ifIndex }
            ::= { enhEthAggrMaintRxTable 1 }

        EnhEthAggrMaintRxEntry ::=
            SEQUENCE {
                enhEthAggrMaintRxEINB
                    Counter64,
                enhEthAggrMaintRxEINF
                    Counter64,
                enhEthAggrMaintRxEIFE
                    Counter64,
                enhEthAggrMaintRxTDF
                    Counter64,
                enhEthAggrMaintRxLastDiscontinuityTimeStamp
                    OpticsIMPmLastDiscontinuityTimeStamp,
                enhEthAggrMaintRxRetrievingTime
                    OpticsIMPmRetrievingTime,
                enhEthAggrMaintRxTRCFUnicast
                    Counter64,
                enhEthAggrMaintRxTRCFMulticast
                    Counter64,
                enhEthAggrMaintRxTRCFBroadcast
                    Counter64,
                enhEthAggrMaintRxReset
                    TruthValue
             }

        enhEthAggrMaintRxEINB OBJECT-TYPE
            SYNTAX Counter64
            MAX-ACCESS read-only
            STATUS current
            DESCRIPTION
                "The number of octets of Ethernet frames received correctly by the Virtual Ethernet Interface, including Ethernet headers characters"
            ::= { enhEthAggrMaintRxEntry 1 }

        enhEthAggrMaintRxEINF OBJECT-TYPE
            SYNTAX Counter64
            MAX-ACCESS read-only
            STATUS current
            DESCRIPTION
                "The number of Ethernet frames received correctly by the Virtual Ethernet Interface."
            ::= { enhEthAggrMaintRxEntry 2 }

        enhEthAggrMaintRxEIFE OBJECT-TYPE
            SYNTAX Counter64
            MAX-ACCESS read-only
            STATUS current
            DESCRIPTION
                "This object is the sum of three contributions dot3StatsAlignmentErrors, dot3StatsFCSErrors and dot3StatsFrameTooLongs"
            ::= { enhEthAggrMaintRxEntry 3 }

        enhEthAggrMaintRxTDF OBJECT-TYPE
            SYNTAX Counter64
            MAX-ACCESS read-only
            STATUS current
            DESCRIPTION
                "Total number of Ethernet frames which where choosen to be discarded due to buffer congestion"
            ::= { enhEthAggrMaintRxEntry 4 }

        enhEthAggrMaintRxLastDiscontinuityTimeStamp OBJECT-TYPE
            SYNTAX OpticsIMPmLastDiscontinuityTimeStamp
            MAX-ACCESS read-only
            STATUS current
            DESCRIPTION
                "See Textual Conventions."
            ::= { enhEthAggrMaintRxEntry 5 }

        enhEthAggrMaintRxRetrievingTime OBJECT-TYPE
            SYNTAX OpticsIMPmRetrievingTime
            MAX-ACCESS read-only
            STATUS current
            DESCRIPTION
                "See Textual Conventions."
            ::= { enhEthAggrMaintRxEntry 6 }

        enhEthAggrMaintRxTRCFUnicast OBJECT-TYPE
            SYNTAX Counter64
            MAX-ACCESS read-only
            STATUS current
            DESCRIPTION
                          "The number of Ethernet Unicast frames received correctly by the Virtual Ethernet Interface."
            ::= { enhEthAggrMaintRxEntry 7 }

        enhEthAggrMaintRxTRCFMulticast OBJECT-TYPE
            SYNTAX Counter64
            MAX-ACCESS read-only
            STATUS current
            DESCRIPTION
                      "The total number of good packets received that were directed to a multicast address.
             Note that this number does not include packets directed to the broadcast address.
             This behavior is the same performed by the counter etherStatsMulticastPkts in the IETF RMON-MIB published as RFC 2819"
            ::= { enhEthAggrMaintRxEntry 8 }

        enhEthAggrMaintRxTRCFBroadcast OBJECT-TYPE
            SYNTAX Counter64
            MAX-ACCESS read-only
            STATUS current
            DESCRIPTION
                         "The total number of good packets received that were directed to the broadcast address.
                           Note that this does not include multicast packets. This behavior is the same performed by the counter etherStatsBroadcastPkts in the IETF RMON-MIB published as RFC 2819"
            ::= { enhEthAggrMaintRxEntry 9 }

        enhEthAggrMaintRxReset OBJECT-TYPE
            SYNTAX TruthValue
            MAX-ACCESS read-write
            STATUS current
            DESCRIPTION
                    "This object allows to reset i.e. set to 0, all the curent counters for received frames."
            ::= { enhEthAggrMaintRxEntry 10 }


-- Enhanced transmitted aggregates counters table for maintenance pourpose.
        enhEthAggrMaintTxTable OBJECT-TYPE
            SYNTAX SEQUENCE OF EnhEthAggrMaintTxEntry
            MAX-ACCESS not-accessible
            STATUS current
            DESCRIPTION
                "This table contains enhanced transmitted aggregates maintenance counters."
            ::= { opticsIMEthPmMib 49 }

        enhEthAggrMaintTxEntry OBJECT-TYPE
            SYNTAX EnhEthAggrMaintTxEntry
            MAX-ACCESS not-accessible
            STATUS current
            DESCRIPTION
                "An entry of enhanced transmitted aggregate maintenance counters table."
            INDEX { ifIndex }
            ::= { enhEthAggrMaintTxTable 1 }

        EnhEthAggrMaintTxEntry ::=
            SEQUENCE {
                enhEthAggrMaintTxEONB
                    Counter64,
                enhEthAggrMaintTxEONF
                    Counter64,
                enhEthAggrMaintTxTDF
                    Counter64,
                enhEthAggrMaintTxLastDiscontinuityTimeStamp
                    OpticsIMPmLastDiscontinuityTimeStamp,
                enhEthAggrMaintTxRetrievingTime
                    OpticsIMPmRetrievingTime,
                enhEthAggrMaintTxEONFUnicast
                    Counter64,
                enhEthAggrMaintTxEONFMulticast
                    Counter64,
                enhEthAggrMaintTxEONFBroadcast
                    Counter64,
                enhEthAggrMaintTxReset
                    TruthValue
             }

        enhEthAggrMaintTxEONB OBJECT-TYPE
            SYNTAX Counter64
            MAX-ACCESS read-only
            STATUS current
            DESCRIPTION
                "The number of octets of Ethernet frames transmitted out by the Virtual Ethernet Interface, including Ethernet headers characters"
            ::= { enhEthAggrMaintTxEntry 1 }

        enhEthAggrMaintTxEONF OBJECT-TYPE
            SYNTAX Counter64
            MAX-ACCESS read-only
            STATUS current
            DESCRIPTION
                "The number of Ethernet frames transmitted out by the Virtual Ethernet Interface."
            ::= { enhEthAggrMaintTxEntry 2 }

        enhEthAggrMaintTxTDF OBJECT-TYPE
            SYNTAX Counter64
            MAX-ACCESS read-only
            STATUS current
            DESCRIPTION
                "Total number of Ethernet frames which where choosen to be discarded due to buffer congestion"
            ::= { enhEthAggrMaintTxEntry 3 }

        enhEthAggrMaintTxLastDiscontinuityTimeStamp OBJECT-TYPE
            SYNTAX OpticsIMPmLastDiscontinuityTimeStamp
            MAX-ACCESS read-only
            STATUS current
            DESCRIPTION
                "See Textual Conventions."
            ::= { enhEthAggrMaintTxEntry 4 }

        enhEthAggrMaintTxRetrievingTime OBJECT-TYPE
            SYNTAX OpticsIMPmRetrievingTime
            MAX-ACCESS read-only
            STATUS current
            DESCRIPTION
                "See Textual Conventions."
            ::= { enhEthAggrMaintTxEntry 5 }

        enhEthAggrMaintTxEONFUnicast OBJECT-TYPE
            SYNTAX Counter64
            MAX-ACCESS read-only
            STATUS current
            DESCRIPTION
                    "The number of Ethernet Unicast frames transmitted out by the Virtual Ethernet Interface."
            ::= { enhEthAggrMaintTxEntry 6 }

        enhEthAggrMaintTxEONFMulticast OBJECT-TYPE
            SYNTAX Counter64
            MAX-ACCESS read-only
            STATUS current
            DESCRIPTION
                     "The number of good packets transmitted by this address that were directed to a multicast address.
                       Note that this number does not include packets directed to the broadcast address.
                        This behavior is the same performed by the counter hostOutMulticastPkts in the IETF RMON-MIB published as RFC 2819."
            ::= { enhEthAggrMaintTxEntry 7 }

        enhEthAggrMaintTxEONFBroadcast OBJECT-TYPE
            SYNTAX Counter64
            MAX-ACCESS read-only
            STATUS current
            DESCRIPTION
                       "The number of good packets transmitted by this address that were directed to the broadcast address.
                     This behavior is the same performed by the counter hostOutBroadcastPkts in the IETF RMON-MIB published as RFC 2819."
            ::= { enhEthAggrMaintTxEntry 8 }

        enhEthAggrMaintTxReset OBJECT-TYPE
            SYNTAX TruthValue
            MAX-ACCESS read-write
            STATUS current
            DESCRIPTION
                    "This object allows to reset i.e. set to 0, all the curent counters for transmitted frames."
            ::= { enhEthAggrMaintTxEntry 9 }

-- Enhanced Incoming flow current datas table

        enhEtsInFlowCDTable OBJECT-TYPE
            SYNTAX SEQUENCE OF EnhEtsInFlowCDEntry
            MAX-ACCESS not-accessible
            STATUS current
            DESCRIPTION
            "This table contains enhanced received flows Current Datas counters."
            ::= { opticsIMEthPmMib 44 }

        enhEtsInFlowCDEntry OBJECT-TYPE
            SYNTAX EnhEtsInFlowCDEntry
            MAX-ACCESS not-accessible
            STATUS current
            DESCRIPTION
            "An entry of enhanced received flows Current Data counters table."
            INDEX { opticsIMETSInFlowIndex, enhEtsInFlowCDGranularityPeriod}
            ::= { enhEtsInFlowCDTable 1 }

        EnhEtsInFlowCDEntry ::=
            SEQUENCE {
                enhEtsInFlowCDGranularityPeriod
                    OpticsIMPmGranularityPeriod,
                enhEtsInFlowCDEINFg
                    Counter64,
                enhEtsInFlowCDEINBg
                    Counter64,
                enhEtsInFlowCDStartByOS
                    TsdimManagerType,
                enhEtsInFlowCDEINFy
                    Counter64,
                enhEtsInFlowCDEINFr
                    Counter64,
                enhEtsInFlowCDEINBy
                    Counter64,
                enhEtsInFlowCDEINBr
                    Counter64,
                enhEtsInFlowCDResetCounter
                    TruthValue,
                enhEtsInFlowCDRowStatus
                    RowStatus,
                enhEtsInFlowCDThresholdDataInstance
                    OpticsIMPmThresholdDataInstance,

                                enhEtsInFlowCDElapsedTime OpticsIMPmElapsedTime
             }

        enhEtsInFlowCDGranularityPeriod OBJECT-TYPE
            SYNTAX OpticsIMPmGranularityPeriod
            MAX-ACCESS not-accessible
            STATUS current
            DESCRIPTION
            "See Textual Conventions."
            ::= { enhEtsInFlowCDEntry 1 }

        enhEtsInFlowCDEINFg OBJECT-TYPE
            SYNTAX Counter64
            MAX-ACCESS read-only
            STATUS current
            DESCRIPTION
            "The number of green Ethernet frames received correctly."
            ::= { enhEtsInFlowCDEntry 2 }

        enhEtsInFlowCDEINBg OBJECT-TYPE
            SYNTAX Counter64
            MAX-ACCESS read-only
            STATUS current
            DESCRIPTION
            "The number of octets of  green Ethernet frames received correctly for this flow, including Ethernet headers characters"
            ::= { enhEtsInFlowCDEntry 3 }

        enhEtsInFlowCDStartByOS OBJECT-TYPE
            SYNTAX TsdimManagerType
            MAX-ACCESS read-only
            STATUS current
            DESCRIPTION
            "See Textual Conventions."
            ::= { enhEtsInFlowCDEntry 4 }

        enhEtsInFlowCDEINFy OBJECT-TYPE
            SYNTAX Counter64
            MAX-ACCESS read-only
            STATUS current
            DESCRIPTION
            "The number of yellow Ethernet frames received correctly."
            ::= { enhEtsInFlowCDEntry 5 }

        enhEtsInFlowCDEINFr OBJECT-TYPE
            SYNTAX Counter64
            MAX-ACCESS read-only
            STATUS current
            DESCRIPTION
            "The number of red Ethernet frames received correctly."
            ::= { enhEtsInFlowCDEntry 6 }

        enhEtsInFlowCDEINBy OBJECT-TYPE
            SYNTAX Counter64
            MAX-ACCESS read-only
            STATUS current
            DESCRIPTION
            " The number of octets of yellow Ethernet frames received correctly for this flow, including Ethernet headers characters."
            ::= { enhEtsInFlowCDEntry 7 }

        enhEtsInFlowCDEINBr OBJECT-TYPE
            SYNTAX Counter64
            MAX-ACCESS read-only
            STATUS current
            DESCRIPTION
            " The number of octets of red Ethernet frames received correctly for this flow, including Ethernet headers characters."
            ::= { enhEtsInFlowCDEntry 8 }

        enhEtsInFlowCDResetCounter OBJECT-TYPE
            SYNTAX TruthValue
            MAX-ACCESS read-create
            STATUS current
            DESCRIPTION
            "This object allows to reset i.e. set to 0, all the current counters
             for received frames."
            ::= { enhEtsInFlowCDEntry 9  }

        enhEtsInFlowCDRowStatus OBJECT-TYPE
            SYNTAX RowStatus
            MAX-ACCESS read-create
            STATUS current
            DESCRIPTION
            "See Textual Conventions."
            ::= { enhEtsInFlowCDEntry 10 }

        enhEtsInFlowCDThresholdDataInstance  OBJECT-TYPE
            SYNTAX  OpticsIMPmThresholdDataInstance
             MAX-ACCESS    read-write
             STATUS        current
               DESCRIPTION
                   "This is a pointer to Enhanced CD Flow PM Threshold Data."
            ::= { enhEtsInFlowCDEntry  11 }

        enhEtsInFlowCDElapsedTime     OBJECT-TYPE
        SYNTAX OpticsIMPmElapsedTime
        MAX-ACCESS read-only
        STATUS current
        DESCRIPTION
                   "See Textual Conventions."
        ::= { enhEtsInFlowCDEntry 12 }


-- Enhanced Incoming flow history datas table

        enhEtsInFlowHDTable OBJECT-TYPE
            SYNTAX SEQUENCE OF EnhEtsInFlowHDEntry
            MAX-ACCESS not-accessible
            STATUS current
            DESCRIPTION
            "This table contains enhanced received flows History Datas counters."
            ::= { opticsIMEthPmMib 45 }

        enhEtsInFlowHDEntry OBJECT-TYPE
            SYNTAX EnhEtsInFlowHDEntry
            MAX-ACCESS not-accessible
            STATUS current
            DESCRIPTION
            "An entry of enhanced transmitted flows History Data counters table."
            INDEX { opticsIMETSInFlowIndex, enhEtsInFlowHDGranularityPeriod,
                    enhEtsInFlowHDPeriodEndtime, enhEtsInFlowHDIndex }
            ::= { enhEtsInFlowHDTable 1 }

        EnhEtsInFlowHDEntry ::=
            SEQUENCE {
                enhEtsInFlowHDGranularityPeriod
                    OpticsIMPmGranularityPeriod,
                enhEtsInFlowHDPeriodEndtime
                    OpticsIMPmPeriodTime,
                enhEtsInFlowHDIndex
                    OpticsIMPmIndex,
                enhEtsInFlowHDEINFg
                    Counter64,
                enhEtsInFlowHDEINBg
                    Counter64,
                enhEtsInFlowHDSuspectIntervalFlag
                    OpticsIMPmSuspectIntervalFlag,
                enhEtsInFlowHDStartByOS
                    TsdimManagerType,
                enhEtsInFlowHDEINFy
                    Counter64,
                enhEtsInFlowHDEINFr
                    Counter64,
                enhEtsInFlowHDEINBy
                    Counter64,
                enhEtsInFlowHDEINBr
                      Counter64,
                                enhEtsInFlowHDElapsedTime OpticsIMPmElapsedTime
             }

        enhEtsInFlowHDGranularityPeriod OBJECT-TYPE
            SYNTAX OpticsIMPmGranularityPeriod
            MAX-ACCESS not-accessible
            STATUS current
            DESCRIPTION
            "See Textual Conventions."
            ::= { enhEtsInFlowHDEntry 1 }

        enhEtsInFlowHDPeriodEndtime OBJECT-TYPE
            SYNTAX OpticsIMPmPeriodTime
            MAX-ACCESS not-accessible
            STATUS current
            DESCRIPTION
            "See Textual Conventions."
            ::= { enhEtsInFlowHDEntry 2 }

        enhEtsInFlowHDIndex OBJECT-TYPE
            SYNTAX OpticsIMPmIndex
            MAX-ACCESS not-accessible
            STATUS current
            DESCRIPTION
            "See Textual Conventions."
            ::= { enhEtsInFlowHDEntry 3 }

        enhEtsInFlowHDEINFg OBJECT-TYPE
            SYNTAX Counter64
            MAX-ACCESS read-only
            STATUS current
            DESCRIPTION
            "The number of green Ethernet frames received correctly."
            ::= { enhEtsInFlowHDEntry 4 }

        enhEtsInFlowHDEINBg OBJECT-TYPE
            SYNTAX Counter64
            MAX-ACCESS read-only
            STATUS current
            DESCRIPTION
            "The number of octets of  green Ethernet frames received correctly for this flow, including Ethernet headers characters"
            ::= { enhEtsInFlowHDEntry 5 }

        enhEtsInFlowHDSuspectIntervalFlag OBJECT-TYPE
            SYNTAX OpticsIMPmSuspectIntervalFlag
            MAX-ACCESS read-only
            STATUS current
            DESCRIPTION
            "See Textual Conventions."
            ::= { enhEtsInFlowHDEntry 6 }

        enhEtsInFlowHDStartByOS OBJECT-TYPE
            SYNTAX TsdimManagerType
            MAX-ACCESS read-only
            STATUS current
            DESCRIPTION
                "See Textual Conventions."
            ::= { enhEtsInFlowHDEntry 7 }

        enhEtsInFlowHDEINFy OBJECT-TYPE
            SYNTAX Counter64
            MAX-ACCESS read-only
            STATUS current
            DESCRIPTION
            "The collected number of yellow Ethernet frames received correctly."
            ::= { enhEtsInFlowHDEntry 8 }

        enhEtsInFlowHDEINFr OBJECT-TYPE
            SYNTAX Counter64
            MAX-ACCESS read-only
            STATUS current
            DESCRIPTION
            "The collected number of red Ethernet frames received correctly."
            ::= { enhEtsInFlowHDEntry 9 }

        enhEtsInFlowHDEINBy OBJECT-TYPE
            SYNTAX Counter64
            MAX-ACCESS read-only
            STATUS current
            DESCRIPTION
            "The collected number of octets of yellow Ethernet frames received correctly for this flow,including Ethernet headers characters"
            ::= { enhEtsInFlowHDEntry 10 }

        enhEtsInFlowHDEINBr OBJECT-TYPE
            SYNTAX Counter64
            MAX-ACCESS read-only
            STATUS current
            DESCRIPTION
            "The collected number of octets of red Ethernet frames received correctly for this flow,including Ethernet headers characters"
            ::= { enhEtsInFlowHDEntry 11 }

        enhEtsInFlowHDElapsedTime     OBJECT-TYPE
                SYNTAX OpticsIMPmElapsedTime
            MAX-ACCESS read-only
            STATUS current
            DESCRIPTION
                   "See Textual Conventions."
                ::= { enhEtsInFlowHDEntry 12 }


-- Enhanced Outgoing flow current datas table

        enhEtsOutFlowCDTable OBJECT-TYPE
            SYNTAX SEQUENCE OF EnhEtsOutFlowCDEntry
            MAX-ACCESS not-accessible
            STATUS current
            DESCRIPTION
            "This table contains enhanced transmitted flows Current Datas counters."
            ::= { opticsIMEthPmMib 46 }

        enhEtsOutFlowCDEntry OBJECT-TYPE
            SYNTAX EnhEtsOutFlowCDEntry
            MAX-ACCESS not-accessible
            STATUS current
            DESCRIPTION
            "An entry of transmitted flows Current Data counters table."
            INDEX { opticsIMETSOutFlowIndex, enhEtsOutFlowCDGranularityPeriod}
            ::= { enhEtsOutFlowCDTable 1 }

        EnhEtsOutFlowCDEntry ::=
            SEQUENCE {
                enhEtsOutFlowCDGranularityPeriod
                    OpticsIMPmGranularityPeriod,
                enhEtsOutFlowCDEONFg
                    Counter64,
                enhEtsOutFlowCDEONBg
                    Counter64,
                enhEtsOutFlowCDStartByOS
                    TsdimManagerType,
                enhEtsOutFlowCDEONFy
                    Counter64,
                enhEtsOutFlowCDEONBy
                    Counter64,
                enhEtsOutFlowCDResetCounter
                    TruthValue,
                enhEtsOutFlowCDRowStatus
                    RowStatus,
                enhEtsOutFlowCDThresholdDataInstance
                    OpticsIMPmThresholdDataInstance,

                enhEtsOutFlowCDElapsedTime OpticsIMPmElapsedTime
                 }

        enhEtsOutFlowCDGranularityPeriod OBJECT-TYPE
            SYNTAX OpticsIMPmGranularityPeriod
            MAX-ACCESS not-accessible
            STATUS current
            DESCRIPTION
            "See Textual Conventions."
            ::= { enhEtsOutFlowCDEntry 1 }

        enhEtsOutFlowCDEONFg OBJECT-TYPE
            SYNTAX Counter64
            MAX-ACCESS read-only
            STATUS current
            DESCRIPTION
            "Total number of green Ethernet frames transmitted out."
            ::= { enhEtsOutFlowCDEntry 2 }

        enhEtsOutFlowCDEONBg OBJECT-TYPE
            SYNTAX Counter64
            MAX-ACCESS read-only
            STATUS current
            DESCRIPTION
            "Total number of octets of green Ethernet frames transmitted out, including  Ethernet header characters."
            ::= { enhEtsOutFlowCDEntry 3 }

        enhEtsOutFlowCDStartByOS OBJECT-TYPE
            SYNTAX TsdimManagerType
            MAX-ACCESS read-only
            STATUS current
            DESCRIPTION
            "See Textual Conventions."
            ::= { enhEtsOutFlowCDEntry 4 }

        enhEtsOutFlowCDEONFy OBJECT-TYPE
            SYNTAX Counter64
            MAX-ACCESS read-only
            STATUS current
            DESCRIPTION
            "Total number of yellow Ethernet frames transmitted out."
            ::= { enhEtsOutFlowCDEntry 5 }

        enhEtsOutFlowCDEONBy OBJECT-TYPE
            SYNTAX Counter64
            MAX-ACCESS read-only
            STATUS current
            DESCRIPTION
            "Total number of octets of yellow Ethernet frames transmitted out,including Ethernet header characters."
            ::= { enhEtsOutFlowCDEntry 6 }

        enhEtsOutFlowCDResetCounter OBJECT-TYPE
            SYNTAX TruthValue
            MAX-ACCESS read-create
            STATUS current
            DESCRIPTION
            "This object allows to reset i.e. set to 0, all the curent counters
             for transmitted frames."
            ::= { enhEtsOutFlowCDEntry 7 }

        enhEtsOutFlowCDRowStatus OBJECT-TYPE
            SYNTAX RowStatus
            MAX-ACCESS read-create
            STATUS current
            DESCRIPTION
            "See Textual Conventions."
            ::= { enhEtsOutFlowCDEntry 8 }

            enhEtsOutFlowCDThresholdDataInstance  OBJECT-TYPE
                  SYNTAX  OpticsIMPmThresholdDataInstance
                 MAX-ACCESS    read-write
                 STATUS        current
                 DESCRIPTION
                        "This is a pointer to Enhanced CD Flow PM Threshold Data."
                  ::= { enhEtsOutFlowCDEntry  9 }


        enhEtsOutFlowCDElapsedTime     OBJECT-TYPE
                SYNTAX OpticsIMPmElapsedTime
            MAX-ACCESS read-only
            STATUS current
            DESCRIPTION
                   "See Textual Conventions."
                ::= { enhEtsOutFlowCDEntry 10 }

-- Enhanced Outgoing flow history datas table

        enhEtsOutFlowHDTable OBJECT-TYPE
            SYNTAX SEQUENCE OF EnhEtsOutFlowHDEntry
            MAX-ACCESS not-accessible
            STATUS current
            DESCRIPTION
            "This table contains transmitted flows History Datas counters."
            ::= { opticsIMEthPmMib 47 }

        enhEtsOutFlowHDEntry OBJECT-TYPE
            SYNTAX EnhEtsOutFlowHDEntry
            MAX-ACCESS not-accessible
            STATUS current
            DESCRIPTION
            "An entry of transmitted  flow counters History Datatable."
            INDEX { opticsIMETSOutFlowIndex, enhEtsOutFlowHDGranularityPeriod,
                    enhEtsOutFlowHDPeriodEndtime, enhEtsOutFlowHDIndex }
            ::= { enhEtsOutFlowHDTable 1 }

        EnhEtsOutFlowHDEntry ::=
            SEQUENCE {
                enhEtsOutFlowHDGranularityPeriod
                    OpticsIMPmGranularityPeriod,
                enhEtsOutFlowHDPeriodEndtime
                    OpticsIMPmPeriodTime,
                enhEtsOutFlowHDIndex
                    OpticsIMPmIndex,
                enhEtsOutFlowHDEONFg
                    Counter64,
                enhEtsOutFlowHDEONBg
                    Counter64,
                enhEtsOutFlowHDSuspectIntervalFlag
                    OpticsIMPmSuspectIntervalFlag,
                enhEtsOutFlowHDStartByOS
                    TsdimManagerType,
                enhEtsOutFlowHDEONFy
                    Counter64,
                enhEtsOutFlowHDEONBy
                    Counter64,

                                enhEtsOutFlowHDElapsedTime OpticsIMPmElapsedTime
             }

        enhEtsOutFlowHDGranularityPeriod OBJECT-TYPE
            SYNTAX OpticsIMPmGranularityPeriod
            MAX-ACCESS not-accessible
            STATUS current
            DESCRIPTION
            "See Textual Conventions."
            ::= { enhEtsOutFlowHDEntry 1 }

        enhEtsOutFlowHDPeriodEndtime OBJECT-TYPE
            SYNTAX OpticsIMPmPeriodTime
            MAX-ACCESS not-accessible
            STATUS current
            DESCRIPTION
            "See Textual Conventions."
            ::= { enhEtsOutFlowHDEntry 2 }

        enhEtsOutFlowHDIndex OBJECT-TYPE
            SYNTAX OpticsIMPmIndex
            MAX-ACCESS not-accessible
            STATUS current
            DESCRIPTION
            "See Textual Conventions."
            ::= { enhEtsOutFlowHDEntry 3 }

        enhEtsOutFlowHDEONFg OBJECT-TYPE
            SYNTAX Counter64
            MAX-ACCESS read-only
            STATUS current
            DESCRIPTION
            "Total number of green Ethernet frames transmitted out"
            ::= { enhEtsOutFlowHDEntry 4 }

        enhEtsOutFlowHDEONBg OBJECT-TYPE
            SYNTAX Counter64
            MAX-ACCESS read-only
            STATUS current
            DESCRIPTION
            "Total number of octets of green Ethernet frames transmitted out, including  Ethernet header characters."
            ::= { enhEtsOutFlowHDEntry 5 }

        enhEtsOutFlowHDSuspectIntervalFlag OBJECT-TYPE
            SYNTAX OpticsIMPmSuspectIntervalFlag
            MAX-ACCESS read-only
            STATUS current
            DESCRIPTION
            "See Textual Conventions."
            ::= { enhEtsOutFlowHDEntry 6 }

        enhEtsOutFlowHDStartByOS OBJECT-TYPE
            SYNTAX TsdimManagerType
            MAX-ACCESS read-only
            STATUS current
            DESCRIPTION
            "See Textual Conventions."
            ::= { enhEtsOutFlowHDEntry 7 }

        enhEtsOutFlowHDEONFy OBJECT-TYPE
            SYNTAX Counter64
            MAX-ACCESS read-only
            STATUS current
            DESCRIPTION
            "Total collected number of yellow Ethernet frames transmitted out"
            ::= { enhEtsOutFlowHDEntry 8 }

        enhEtsOutFlowHDEONBy OBJECT-TYPE
            SYNTAX Counter64
            MAX-ACCESS read-only
            STATUS current
            DESCRIPTION
            "Total collected number of octets of yellow Ethernet frames transmitted out,including Ethernet header characters."
            ::= { enhEtsOutFlowHDEntry 9 }

        enhEtsOutFlowHDElapsedTime     OBJECT-TYPE
                SYNTAX OpticsIMPmElapsedTime
            MAX-ACCESS read-only
            STATUS current
            DESCRIPTION
                   "See Textual Conventions."
                ::= { enhEtsOutFlowHDEntry 10 }


-- Enhanced Aggregate CD Threshold

enhEthAggrCDThresholdIndexNext OBJECT-TYPE
      SYNTAX        Unsigned32
      MAX-ACCESS    read-only
      STATUS        current
      DESCRIPTION
         "Value to be used as the index of the threshold
         profile in order to create a new row in the table."
::= { opticsIMEthPmMib 50 }

enhEthAggrCDThresholdTable OBJECT-TYPE
    SYNTAX   SEQUENCE OF EnhEthAggrCDThresholdEntry
    MAX-ACCESS    not-accessible
    STATUS        current
    DESCRIPTION
          "This table contains the high and low thresholds
           for the Enhanced Aggregate CD  Threshold Crossing Alert and Reset."
::= { opticsIMEthPmMib 51 }

enhEthAggrCDThresholdEntry  OBJECT-TYPE
      SYNTAX        EnhEthAggrCDThresholdEntry
      MAX-ACCESS    not-accessible
      STATUS        current
      DESCRIPTION
         "An entry (row) containing Enhanced Aggregate CD  high and low threshold
          values."
      INDEX { enhEthAggrCDThresholdIndex, enhEthAggrCDThresholdGranularityPeriod }
 ::= { enhEthAggrCDThresholdTable 1 }

EnhEthAggrCDThresholdEntry  ::=
  SEQUENCE {
    enhEthAggrCDThresholdIndex                       INTEGER,
    enhEthAggrCDThresholdGranularityPeriod           OpticsIMPmGranularityPeriod,
    enhEthAggrCDThresholdRxEINFEnable                TruthValue,
    enhEthAggrCDThresholdRxEINFHighThr                Gauge32,
    enhEthAggrCDThresholdRxEINFLowThr                 Gauge32,
    enhEthAggrCDThresholdRxEINBEnable                 TruthValue,
    enhEthAggrCDThresholdRxEINBHighThr                Gauge32,
    enhEthAggrCDThresholdRxEINBLowThr                 Gauge32,
    enhEthAggrCDThresholdRxEINFUnicastEnable          TruthValue,
    enhEthAggrCDThresholdRxEINFUnicastHighThr         Gauge32,
    enhEthAggrCDThresholdRxEINFUnicastLowThr          Gauge32,
    enhEthAggrCDThresholdRxEINFMulticastEnable        TruthValue,
    enhEthAggrCDThresholdRxEINFMulticastHighThr       Gauge32,
    enhEthAggrCDThresholdRxEINFMulticastLowThr        Gauge32,
    enhEthAggrCDThresholdRxEINFBroadcastEnable        TruthValue,
    enhEthAggrCDThresholdRxEINFBroadcastHighThr       Gauge32,
    enhEthAggrCDThresholdRxEINFBroadcastLowThr        Gauge32,
    enhEthAggrCDThresholdRxEIFEEnable                 TruthValue,
    enhEthAggrCDThresholdRxEIFEHighThr                Gauge32,
    enhEthAggrCDThresholdRxEIFELowThr                 Gauge32,
    enhEthAggrCDThresholdRxTUFEnable                  TruthValue,
    enhEthAggrCDThresholdRxTUFHighThr                 Gauge32,
    enhEthAggrCDThresholdRxTUFLowThr                  Gauge32,
    enhEthAggrCDThresholdRxTDFEnable                  TruthValue,
    enhEthAggrCDThresholdRxTDFHighThr                 Gauge32,
    enhEthAggrCDThresholdRxTDFLowThr                  Gauge32,
    enhEthAggrCDThresholdTxEONFEnable                 TruthValue,
    enhEthAggrCDThresholdTxEONFHighThr                Gauge32,
    enhEthAggrCDThresholdTxEONFLowThr                 Gauge32,
    enhEthAggrCDThresholdTxEONBEnable                 TruthValue,
    enhEthAggrCDThresholdTxEONBHighThr                Gauge32,
    enhEthAggrCDThresholdTxEONBLowThr                 Gauge32,
    enhEthAggrCDThresholdTxEONFUnicastEnable          TruthValue,
    enhEthAggrCDThresholdTxEONFUnicastHighThr         Gauge32,
    enhEthAggrCDThresholdTxEONFUnicastLowThr          Gauge32,
    enhEthAggrCDThresholdTxEONFMulticastEnable        TruthValue,
    enhEthAggrCDThresholdTxEONFMulticastHighThr       Gauge32,
    enhEthAggrCDThresholdTxEONFMulticastLowThr        Gauge32,
    enhEthAggrCDThresholdTxEONFBroadcastEnable        TruthValue,
    enhEthAggrCDThresholdTxEONFBroadcastHighThr       Gauge32,
    enhEthAggrCDThresholdTxEONFBroadcastLowThr        Gauge32,
    enhEthAggrCDThresholdTxTDFEnable                  TruthValue,
    enhEthAggrCDThresholdTxTDFHighThr                 Gauge32,
    enhEthAggrCDThresholdTxTDFLowThr                  Gauge32,
    enhEthAggrCDThresholdUserLabel                    OCTET STRING,
    enhEthAggrCDThresholdRowStatus                    RowStatus,
    enhEthAggrCDThresholdRxEINBRateEnable             TruthValue,
    enhEthAggrCDThresholdRxEINBRateHighThr            Gauge32,
    enhEthAggrCDThresholdRxEINBRateLowThr             Gauge32,
    enhEthAggrCDThresholdRxEINBRatioEnable            TruthValue,
    enhEthAggrCDThresholdRxEINBRatioHighThr           Gauge32,
    enhEthAggrCDThresholdRxEINBRatioLowThr            Gauge32,
    enhEthAggrCDThresholdRxEIFERatioEnable            TruthValue,
    enhEthAggrCDThresholdRxEIFERatioHighThr           Gauge32,
    enhEthAggrCDThresholdRxEIFERatioLowThr            Gauge32,
    enhEthAggrCDThresholdRxTDFRatioEnable             TruthValue,
    enhEthAggrCDThresholdRxTDFRatioHighThr            Gauge32,
    enhEthAggrCDThresholdRxTDFRatioLowThr             Gauge32,
    enhEthAggrCDThresholdTxEONBRateEnable             TruthValue,
    enhEthAggrCDThresholdTxEONBRateHighThr            Gauge32,
    enhEthAggrCDThresholdTxEONBRateLowThr             Gauge32,
    enhEthAggrCDThresholdTxEONBRatioEnable            TruthValue,
    enhEthAggrCDThresholdTxEONBRatioHighThr           Gauge32,
    enhEthAggrCDThresholdTxEONBRatioLowThr            Gauge32,
    enhEthAggrCDThresholdTxTDFRatioEnable             TruthValue,
    enhEthAggrCDThresholdTxTDFRatioHighThr            Gauge32,
    enhEthAggrCDThresholdTxTDFRatioLowThr             Gauge32,

--- TSDnm92784: April2011 Begin
    enhEthAggrCDThreshold64RxEINFEnable                 TruthValue,
    enhEthAggrCDThreshold64RxEINFHighThr                Counter64,
    enhEthAggrCDThreshold64RxEINFLowThr                 Counter64,
    enhEthAggrCDThreshold64RxEINBEnable                 TruthValue,
    enhEthAggrCDThreshold64RxEINBHighThr                Counter64,
    enhEthAggrCDThreshold64RxEINBLowThr                 Counter64,
    enhEthAggrCDThreshold64RxEINFUnicastEnable          TruthValue,
    enhEthAggrCDThreshold64RxEINFUnicastHighThr         Counter64,
    enhEthAggrCDThreshold64RxEINFUnicastLowThr          Counter64,
    enhEthAggrCDThreshold64RxEINFMulticastEnable        TruthValue,
    enhEthAggrCDThreshold64RxEINFMulticastHighThr       Counter64,
    enhEthAggrCDThreshold64RxEINFMulticastLowThr        Counter64,
    enhEthAggrCDThreshold64RxEINFBroadcastEnable        TruthValue,
    enhEthAggrCDThreshold64RxEINFBroadcastHighThr       Counter64,
    enhEthAggrCDThreshold64RxEINFBroadcastLowThr        Counter64,
    enhEthAggrCDThreshold64TxEONFEnable                 TruthValue,
    enhEthAggrCDThreshold64TxEONFHighThr                Counter64,
    enhEthAggrCDThreshold64TxEONFLowThr                 Counter64,
    enhEthAggrCDThreshold64TxEONBEnable                 TruthValue,
    enhEthAggrCDThreshold64TxEONBHighThr                Counter64,
    enhEthAggrCDThreshold64TxEONBLowThr                 Counter64,
    enhEthAggrCDThreshold64TxEONFUnicastEnable          TruthValue,
    enhEthAggrCDThreshold64TxEONFUnicastHighThr         Counter64,
    enhEthAggrCDThreshold64TxEONFUnicastLowThr          Counter64,
    enhEthAggrCDThreshold64TxEONFMulticastEnable        TruthValue,
    enhEthAggrCDThreshold64TxEONFMulticastHighThr       Counter64,
    enhEthAggrCDThreshold64TxEONFMulticastLowThr        Counter64,
    enhEthAggrCDThreshold64TxEONFBroadcastEnable        TruthValue,
    enhEthAggrCDThreshold64TxEONFBroadcastHighThr       Counter64,
    enhEthAggrCDThreshold64TxEONFBroadcastLowThr        Counter64

--- TSDnm92784: April 2011 End

}

enhEthAggrCDThresholdIndex OBJECT-TYPE
     SYNTAX        INTEGER
     MAX-ACCESS    not-accessible
     STATUS        current
     DESCRIPTION
         "This is the index to the Enhanced (Granularity-based) threshold row."
 ::= { enhEthAggrCDThresholdEntry  1 }

enhEthAggrCDThresholdGranularityPeriod OBJECT-TYPE
     SYNTAX        OpticsIMPmGranularityPeriod
     MAX-ACCESS    not-accessible
     STATUS        current
     DESCRIPTION
         "This is the last index to the Enhanced (Granularity-based) Threshold row -
          See Textual Convention."
 ::= { enhEthAggrCDThresholdEntry  2 }


enhEthAggrCDThresholdRxEINFEnable OBJECT-TYPE
    SYNTAX TruthValue
    MAX-ACCESS read-write
    STATUS current
    DESCRIPTION
        "Enabled/Disabled TCA over the number of Ethernet frames received correctly.
             Default value: False(Disabled TCA)"
::= { enhEthAggrCDThresholdEntry  3 }

enhEthAggrCDThresholdRxEINFHighThr  OBJECT-TYPE
    SYNTAX Gauge32
    MAX-ACCESS read-write
    STATUS current
    DESCRIPTION
        "This is the high Threshold for the number of Ethernet frames received correctly
             related to current interval. Default value is NE-Product specific"
::= { enhEthAggrCDThresholdEntry  4 }

enhEthAggrCDThresholdRxEINFLowThr  OBJECT-TYPE
    SYNTAX Gauge32
    MAX-ACCESS read-write
    STATUS current
    DESCRIPTION
        "This is the low Threshold for The number of Ethernet frames received correctly
             related to current interval. Default value is NE-Product specific ."
::= { enhEthAggrCDThresholdEntry  5 }

enhEthAggrCDThresholdRxEINBEnable  OBJECT-TYPE
    SYNTAX TruthValue
    MAX-ACCESS read-write
    STATUS current
    DESCRIPTION
        "Enabled/Disabled TCA over the number of octets of Ethernet frames received correctly,
             including Ethernet headers characters Default value: False(Disabled TCA)"
::= { enhEthAggrCDThresholdEntry  6 }

enhEthAggrCDThresholdRxEINBHighThr  OBJECT-TYPE
    SYNTAX Gauge32
    MAX-ACCESS read-write
    STATUS current
    DESCRIPTION
        "The number of octets of Ethernet frames received correctly, including Ethernet headers characters
             related to current interval. Default value is NE-Product specific"
::= { enhEthAggrCDThresholdEntry  7 }

enhEthAggrCDThresholdRxEINBLowThr  OBJECT-TYPE
    SYNTAX Gauge32
    MAX-ACCESS read-write
    STATUS current
    DESCRIPTION
        "This is the low Threshold for The number of octets of Ethernet frames received correctly,
              including Ethernet headers characters related to current interval. Default value is NE-Product specific"
::= { enhEthAggrCDThresholdEntry  8 }


enhEthAggrCDThresholdRxEINFUnicastEnable  OBJECT-TYPE
    SYNTAX TruthValue
    MAX-ACCESS read-write
    STATUS current
    DESCRIPTION
           "Enabled/Disabled TCA over the collected number of Ethernet Unicast frames received correctly.
            Default value: False(Disabled TCA)"
::= { enhEthAggrCDThresholdEntry  9 }

enhEthAggrCDThresholdRxEINFUnicastHighThr  OBJECT-TYPE
    SYNTAX Gauge32
    MAX-ACCESS read-write
    STATUS current
    DESCRIPTION
           "This is the high Threshold for the collected number of Ethernet Unicast frames received correctly by the Virtual Ethernet Interface
             related to current interval. Default value is NE-Product specific."
::= { enhEthAggrCDThresholdEntry  10 }

enhEthAggrCDThresholdRxEINFUnicastLowThr  OBJECT-TYPE
    SYNTAX Gauge32
    MAX-ACCESS read-write
    STATUS current
    DESCRIPTION
           "This is the low Threshold for The collected number of Ethernet Unicast frames received correctly by the Virtual Ethernet Interface
             related to current interval. Default value is NE-Product specific."
::= { enhEthAggrCDThresholdEntry  11 }


enhEthAggrCDThresholdRxEINFMulticastEnable  OBJECT-TYPE
    SYNTAX TruthValue
    MAX-ACCESS read-write
    STATUS current
    DESCRIPTION
            "Enabled/Disabled TCA over The collected number of Ethernet Multicast frames received correctly. Default value: False(Disabled TCA)"
::= { enhEthAggrCDThresholdEntry  12 }

enhEthAggrCDThresholdRxEINFMulticastHighThr  OBJECT-TYPE
    SYNTAX Gauge32
    MAX-ACCESS read-write
    STATUS current
    DESCRIPTION
            "This is the high Threshold for The collected number of Ethernet Multicast frames received
             correctly related to current interval. Default value is NE-Product specific ."
::= { enhEthAggrCDThresholdEntry  13 }

enhEthAggrCDThresholdRxEINFMulticastLowThr  OBJECT-TYPE
    SYNTAX Gauge32
    MAX-ACCESS read-write
    STATUS current
    DESCRIPTION
            "This is the low Threshold for The collected number of Ethernet Multicast frames received
             correctly related to current interval. Default value is NE-Product specific ."
::= { enhEthAggrCDThresholdEntry  14 }

enhEthAggrCDThresholdRxEINFBroadcastEnable  OBJECT-TYPE
    SYNTAX TruthValue
    MAX-ACCESS read-write
    STATUS current
    DESCRIPTION
            "Enabled/Disabled TCA over The collected number of Ethernet Broadcast frames received
             correctly. Default value: False(Disabled TCA)"
::= { enhEthAggrCDThresholdEntry  15 }

enhEthAggrCDThresholdRxEINFBroadcastHighThr  OBJECT-TYPE
    SYNTAX Gauge32
    MAX-ACCESS read-write
    STATUS current
    DESCRIPTION
            "This is the high Threshold for The collected number of Ethernet Broadcast frames received
             correctly related to current interval. Default value is NE-Product specific ."
::= { enhEthAggrCDThresholdEntry  16 }

enhEthAggrCDThresholdRxEINFBroadcastLowThr  OBJECT-TYPE
    SYNTAX Gauge32
    MAX-ACCESS read-write
    STATUS current
    DESCRIPTION
            "This is the low Threshold for The collected number of Ethernet Broadcast frames received
             correctly related to current interval. Default value is NE-Product specific."
::= { enhEthAggrCDThresholdEntry  17 }


enhEthAggrCDThresholdRxEIFEEnable  OBJECT-TYPE
    SYNTAX TruthValue
    MAX-ACCESS read-write
    STATUS current
    DESCRIPTION
            "Enabled/Disabled TCA over EIFE Frames. Default value: False(Disabled TCA)"
::= { enhEthAggrCDThresholdEntry  18 }
enhEthAggrCDThresholdRxEIFEHighThr  OBJECT-TYPE
    SYNTAX Gauge32
    MAX-ACCESS read-write
    STATUS current
    DESCRIPTION
            "This is the high Threshold for EIFE Frames related to current interval. Default value is NE-Product specific."
::= { enhEthAggrCDThresholdEntry  19 }

enhEthAggrCDThresholdRxEIFELowThr  OBJECT-TYPE
    SYNTAX Gauge32
    MAX-ACCESS read-write
    STATUS current
    DESCRIPTION
            "This is the low Threshold for EIFE frames related to current interval. Default value is NE-Product specific ."
::= { enhEthAggrCDThresholdEntry  20 }

enhEthAggrCDThresholdRxTUFEnable  OBJECT-TYPE
    SYNTAX TruthValue
    MAX-ACCESS read-write
    STATUS current
    DESCRIPTION
            "Enabled/Disabled TCA over of TUF frames. Default value: False(Disabled TCA)"
::= { enhEthAggrCDThresholdEntry  21 }
enhEthAggrCDThresholdRxTUFHighThr  OBJECT-TYPE
    SYNTAX Gauge32
    MAX-ACCESS read-write
    STATUS current
    DESCRIPTION
            "This is the high Threshold for TUF frames related to current interval. Default value is NE-Product specific "
::= { enhEthAggrCDThresholdEntry  22 }
enhEthAggrCDThresholdRxTUFLowThr  OBJECT-TYPE
    SYNTAX Gauge32
    MAX-ACCESS read-write
    STATUS current
    DESCRIPTION
            "This is the low Threshold forTUF frames related to current interval. Default value is NE-Product specific "
::= { enhEthAggrCDThresholdEntry  23 }

enhEthAggrCDThresholdRxTDFEnable  OBJECT-TYPE
    SYNTAX TruthValue
    MAX-ACCESS read-write
    STATUS current
    DESCRIPTION
            "Enabled/Disabled TCA over TDF frames. Default value: False(Disabled TCA)"
::= { enhEthAggrCDThresholdEntry  24 }

enhEthAggrCDThresholdRxTDFHighThr  OBJECT-TYPE
    SYNTAX Gauge32
    MAX-ACCESS read-write
    STATUS current
    DESCRIPTION
            "This is the high Threshold for TDF frames related to current interval. Default value is NE-Product specific."
::= { enhEthAggrCDThresholdEntry  25 }

enhEthAggrCDThresholdRxTDFLowThr  OBJECT-TYPE
    SYNTAX Gauge32
    MAX-ACCESS read-write
    STATUS current
    DESCRIPTION
            "This is the low Threshold for TDF frames related to current interval. Default value is NE-Product specific."
::= { enhEthAggrCDThresholdEntry  26 }

enhEthAggrCDThresholdTxEONFEnable  OBJECT-TYPE
    SYNTAX TruthValue
    MAX-ACCESS read-write
    STATUS current
    DESCRIPTION
        "Enabled/Disabled TCA over The number of Ethernet frames transmitted out.Default value: False(Disabled TCA)"
::= { enhEthAggrCDThresholdEntry  27 }
enhEthAggrCDThresholdTxEONFHighThr  OBJECT-TYPE
    SYNTAX Gauge32
    MAX-ACCESS read-write
    STATUS current
    DESCRIPTION
        "This is the high Threshold for the number of Ethernet frames transmitted out related to current interval. Default value is NE-Product specific ."
::= { enhEthAggrCDThresholdEntry  28 }
enhEthAggrCDThresholdTxEONFLowThr  OBJECT-TYPE
    SYNTAX Gauge32
    MAX-ACCESS read-write
    STATUS current
    DESCRIPTION
        "This is the low Threshold for The number of Ethernet frames transmitted out related to current interval. Default value is NE-Product specific."
::= { enhEthAggrCDThresholdEntry  29 }

enhEthAggrCDThresholdTxEONBEnable  OBJECT-TYPE
    SYNTAX TruthValue
    MAX-ACCESS read-write
    STATUS current
    DESCRIPTION
        "Enabled/Disabled TCA over The number of octets of Ethernet frames transmitted out,
              including Ethernet headers characters. Default value: False(Disabled TCA)"
::= { enhEthAggrCDThresholdEntry  30 }

enhEthAggrCDThresholdTxEONBHighThr  OBJECT-TYPE
    SYNTAX Gauge32
    MAX-ACCESS read-write
    STATUS current
    DESCRIPTION
        "The number of octets of Ethernet frames transmitted out, including Ethernet headers characters
             related to current interval. Default value is NE-Product specific"
::= { enhEthAggrCDThresholdEntry  31 }

enhEthAggrCDThresholdTxEONBLowThr  OBJECT-TYPE
    SYNTAX Gauge32
    MAX-ACCESS read-write
    STATUS current
    DESCRIPTION
        "This is the low Threshold for The number of octets of Ethernet frames transmitted out,
             including Ethernet headers characters related to current interval. Default value is NE-Product specific "
::= { enhEthAggrCDThresholdEntry  32 }

enhEthAggrCDThresholdTxEONFUnicastEnable  OBJECT-TYPE
    SYNTAX TruthValue
    MAX-ACCESS read-write
    STATUS current
    DESCRIPTION
            "Enabled/Disabled TCA over The collected number of Ethernet Unicast frames transmitted out.
             Default value: False(Disabled TCA)"
::= { enhEthAggrCDThresholdEntry  33 }

enhEthAggrCDThresholdTxEONFUnicastHighThr  OBJECT-TYPE
    SYNTAX Gauge32
    MAX-ACCESS read-write
    STATUS current
    DESCRIPTION
            "This is the high Threshold for the collected number of Ethernet Unicast frames transmitted out
             related to current interval. Default value is NE-Product specific."
::= { enhEthAggrCDThresholdEntry  34 }

enhEthAggrCDThresholdTxEONFUnicastLowThr  OBJECT-TYPE
    SYNTAX Gauge32
    MAX-ACCESS read-write
    STATUS current
    DESCRIPTION
            "This is the low Threshold for the collected number of Ethernet Unicast frames transmitted out
             related to current interval. Default value is NE-Product specific."
::= { enhEthAggrCDThresholdEntry  35 }


enhEthAggrCDThresholdTxEONFMulticastEnable  OBJECT-TYPE
    SYNTAX TruthValue
    MAX-ACCESS read-write
    STATUS current
    DESCRIPTION
            "Enabled/Disabled TCA over The collected number of Ethernet Multicast frames transmitted
             out. Default value: False(Disabled TCA)"
::= { enhEthAggrCDThresholdEntry  36 }
enhEthAggrCDThresholdTxEONFMulticastHighThr  OBJECT-TYPE
    SYNTAX Gauge32
    MAX-ACCESS read-write
    STATUS current
    DESCRIPTION
            "This is the high Threshold for The collected number of Ethernet Multicast frames transmitted
             out related to current interval. Default value is NE-Product specific."
::= { enhEthAggrCDThresholdEntry  37 }
enhEthAggrCDThresholdTxEONFMulticastLowThr  OBJECT-TYPE
    SYNTAX Gauge32
    MAX-ACCESS read-write
    STATUS current
    DESCRIPTION
            "This is the low Threshold for The collected number of Ethernet Multicast frames transmitted
             out related to current interval. Default value is NE-Product specific."
::= { enhEthAggrCDThresholdEntry  38 }

enhEthAggrCDThresholdTxEONFBroadcastEnable  OBJECT-TYPE
    SYNTAX TruthValue
    MAX-ACCESS read-write
    STATUS current
    DESCRIPTION
            "Enabled/Disabled TCA over the collected number of Ethernet Broadcast frames transmitted out.
             Default value: False(Disabled TCA)"
::= { enhEthAggrCDThresholdEntry  39 }

enhEthAggrCDThresholdTxEONFBroadcastHighThr  OBJECT-TYPE
    SYNTAX Gauge32
    MAX-ACCESS read-write
    STATUS current
    DESCRIPTION
            "This is the high Threshold for the collected number of Ethernet Broadcast frames transmitted out
             related to current interval. Default value is NE-Product specific."
::= { enhEthAggrCDThresholdEntry  40 }
enhEthAggrCDThresholdTxEONFBroadcastLowThr  OBJECT-TYPE
    SYNTAX Gauge32
    MAX-ACCESS read-write
    STATUS current
    DESCRIPTION
            "This is the low Threshold for The collected number of Ethernet Broadcast frames transmitted out
              related to current interval. Default value is NE-Product specific."
::= { enhEthAggrCDThresholdEntry  41 }

enhEthAggrCDThresholdTxTDFEnable  OBJECT-TYPE
    SYNTAX TruthValue
    MAX-ACCESS read-write
    STATUS current
    DESCRIPTION
            "Enabled/Disabled TCA over TDF frames. Default value: False(Disabled TCA)"
::= { enhEthAggrCDThresholdEntry  42 }

enhEthAggrCDThresholdTxTDFHighThr  OBJECT-TYPE
    SYNTAX Gauge32
    MAX-ACCESS read-write
    STATUS current
    DESCRIPTION
            "This is the high Threshold for TDF frames related to current interval. Default value is NE-Product specific"
::= { enhEthAggrCDThresholdEntry  43 }

enhEthAggrCDThresholdTxTDFLowThr  OBJECT-TYPE
    SYNTAX Gauge32
    MAX-ACCESS read-write
    STATUS current
    DESCRIPTION
            "This is the low Threshold for TDF frames related to current interval. Default value is NE-Product specific"
::= { enhEthAggrCDThresholdEntry  44 }

enhEthAggrCDThresholdUserLabel  OBJECT-TYPE
     SYNTAX        OCTET STRING
     MAX-ACCESS    read-write
     STATUS        current
     DESCRIPTION
         "This is the user label used to identify the profile."
 ::= { enhEthAggrCDThresholdEntry  45 }

enhEthAggrCDThresholdRowStatus  OBJECT-TYPE
     SYNTAX        RowStatus
     MAX-ACCESS    read-create
     STATUS        current
     DESCRIPTION
         "This is the status of the row. It can be used to
         create/destroy the row."
 ::= { enhEthAggrCDThresholdEntry  46 }

---

enhEthAggrCDThresholdRxEINBRateEnable  OBJECT-TYPE
    SYNTAX TruthValue
    MAX-ACCESS read-write
    STATUS current
    DESCRIPTION
            "Enabled/Disabled TCA over rate of the received good bytes. Default value: False(Disabled TCA)"
::= { enhEthAggrCDThresholdEntry  47 }

enhEthAggrCDThresholdRxEINBRateHighThr OBJECT-TYPE
    SYNTAX Gauge32
    MAX-ACCESS read-write
    STATUS current
    DESCRIPTION
            "This is the high Threshold for rate of the received good bytes related to current interval. Default value is NE-Product specific"
::= { enhEthAggrCDThresholdEntry  48 }

enhEthAggrCDThresholdRxEINBRateLowThr OBJECT-TYPE
    SYNTAX Gauge32
    MAX-ACCESS read-write
    STATUS current
    DESCRIPTION
            "This is the low Threshold for rate of the received good bytes related to current interval. Default value is NE-Product specific"
::= { enhEthAggrCDThresholdEntry  49 }

enhEthAggrCDThresholdRxEINBRatioEnable          OBJECT-TYPE
    SYNTAX TruthValue
    MAX-ACCESS read-write
    STATUS current
    DESCRIPTION
            "Enabled/Disabled TCA over the Ratio (throughput) of received good bytes. Default value: False(Disabled TCA)"
::= { enhEthAggrCDThresholdEntry  50 }

enhEthAggrCDThresholdRxEINBRatioHighThr           OBJECT-TYPE
    SYNTAX Gauge32
    MAX-ACCESS read-write
    STATUS current
    DESCRIPTION
            "This is the high Threshold for the Ratio (throughput) of received good bytes related to current interval. Default value is NE-Product specific"
::= { enhEthAggrCDThresholdEntry  51 }

enhEthAggrCDThresholdRxEINBRatioLowThr            OBJECT-TYPE
    SYNTAX Gauge32
    MAX-ACCESS read-write
    STATUS current
    DESCRIPTION
            "This is the low Threshold for the Ratio (throughput) of received good bytes related to current interval. Default value is NE-Product specific"
::= { enhEthAggrCDThresholdEntry  52 }

enhEthAggrCDThresholdRxEIFERatioEnable              OBJECT-TYPE
    SYNTAX TruthValue
    MAX-ACCESS read-write
    STATUS current
    DESCRIPTION
            "Enabled/Disabled TCA over the Ratio of received packets with service error. Default value: False(Disabled TCA)"
::= { enhEthAggrCDThresholdEntry  53 }

enhEthAggrCDThresholdRxEIFERatioHighThr             OBJECT-TYPE
    SYNTAX Gauge32
    MAX-ACCESS read-write
    STATUS current
    DESCRIPTION
            "This is the high Threshold for the Ratio of received packets with service error related to current interval. Default value is NE-Product specific"
::= { enhEthAggrCDThresholdEntry  54 }

enhEthAggrCDThresholdRxEIFERatioLowThr              OBJECT-TYPE
    SYNTAX Gauge32
    MAX-ACCESS read-write
    STATUS current
    DESCRIPTION
            "This is the low Threshold for the Ratio of received packets with service error related to current interval. Default value is NE-Product specific"
::= { enhEthAggrCDThresholdEntry  55 }

enhEthAggrCDThresholdRxTDFRatioEnable             OBJECT-TYPE
    SYNTAX TruthValue
    MAX-ACCESS read-write
    STATUS current
    DESCRIPTION
            "Enabled/Disabled TCA over the Ratio of TDF frames. Default value: False(Disabled TCA)"
::= { enhEthAggrCDThresholdEntry  56 }

enhEthAggrCDThresholdRxTDFRatioHighThr            OBJECT-TYPE
    SYNTAX Gauge32
    MAX-ACCESS read-write
    STATUS current
    DESCRIPTION
            "This is the high Threshold for the Ratio of TDF frames related to current interval. Default value is NE-Product specific"
::= { enhEthAggrCDThresholdEntry  57 }

enhEthAggrCDThresholdRxTDFRatioLowThr             OBJECT-TYPE
    SYNTAX Gauge32
    MAX-ACCESS read-write
    STATUS current
    DESCRIPTION
            "This is the low Threshold for the Ratio of TDF frames related to current interval. Default value is NE-Product specific"
::= { enhEthAggrCDThresholdEntry  58 }

enhEthAggrCDThresholdTxEONBRateEnable             OBJECT-TYPE
    SYNTAX TruthValue
    MAX-ACCESS read-write
    STATUS current
    DESCRIPTION
            "Enabled/Disabled TCA over the Rate of transmitted good bytes (in Mbps). Default value: False(Disabled TCA)"
::= { enhEthAggrCDThresholdEntry  59 }

enhEthAggrCDThresholdTxEONBRateHighThr            OBJECT-TYPE
    SYNTAX Gauge32
    MAX-ACCESS read-write
    STATUS current
    DESCRIPTION
            "This is the high Threshold for the Rate of transmitted good bytes (in Mbps) related to current interval. Default value is NE-Product specific"
::= { enhEthAggrCDThresholdEntry  60 }

enhEthAggrCDThresholdTxEONBRateLowThr             OBJECT-TYPE
    SYNTAX Gauge32
    MAX-ACCESS read-write
    STATUS current
    DESCRIPTION
            "This is the low Threshold for the Rate of transmitted good bytes (in Mbps) related to current interval. Default value is NE-Product specific"
::= { enhEthAggrCDThresholdEntry  61 }

enhEthAggrCDThresholdTxEONBRatioEnable            OBJECT-TYPE
    SYNTAX TruthValue
    MAX-ACCESS read-write
    STATUS current
    DESCRIPTION
            "Enabled/Disabled TCA over the Ratio (throughput) of transmitted good bytes. Default value: False(Disabled TCA)"
::= { enhEthAggrCDThresholdEntry  62 }

enhEthAggrCDThresholdTxEONBRatioHighThr           OBJECT-TYPE
    SYNTAX Gauge32
    MAX-ACCESS read-write
    STATUS current
    DESCRIPTION
            "This is the high Threshold for the Ratio (throughput) of transmitted good bytes related to current interval. Default value is NE-Product specific"
::= { enhEthAggrCDThresholdEntry  63 }

enhEthAggrCDThresholdTxEONBRatioLowThr            OBJECT-TYPE
    SYNTAX Gauge32
    MAX-ACCESS read-write
    STATUS current
    DESCRIPTION
            "This is the low Threshold for the Ratio (throughput) of transmitted good bytes related to current interval. Default value is NE-Product specific"
::= { enhEthAggrCDThresholdEntry  64 }

enhEthAggrCDThresholdTxTDFRatioEnable             OBJECT-TYPE
    SYNTAX TruthValue
    MAX-ACCESS read-write
    STATUS current
    DESCRIPTION
            "Enabled/Disabled TCA over the Ratio of TDF frames. Default value: False(Disabled TCA)"
::= { enhEthAggrCDThresholdEntry  65 }

enhEthAggrCDThresholdTxTDFRatioHighThr            OBJECT-TYPE
    SYNTAX Gauge32
    MAX-ACCESS read-write
    STATUS current
    DESCRIPTION
            "This is the high Threshold for the Ratio of TDF frames related to current interval. Default value is NE-Product specific"
::= { enhEthAggrCDThresholdEntry  66 }

enhEthAggrCDThresholdTxTDFRatioLowThr             OBJECT-TYPE
    SYNTAX Gauge32
    MAX-ACCESS read-write
    STATUS current
    DESCRIPTION
            "This is the low Threshold for the Ratio of TDF frames related to current interval. Default value is NE-Product specific"
::= { enhEthAggrCDThresholdEntry  67 }

---


--- April2011 Begin

enhEthAggrCDThreshold64RxEINFEnable OBJECT-TYPE
    SYNTAX TruthValue
    MAX-ACCESS read-write
    STATUS current
    DESCRIPTION
        "Enabled/Disabled TCA over the number of 64bits Ethernet frames received correctly.
             Default value: False(Disabled TCA)"
::= { enhEthAggrCDThresholdEntry  68 }

enhEthAggrCDThreshold64RxEINFHighThr  OBJECT-TYPE
    SYNTAX Counter64
    MAX-ACCESS read-write
    STATUS current
    DESCRIPTION
        "This is the 64bits high Threshold for the number of Ethernet frames received correctly
             related to current interval. Default value is NE-Product specific"
::= { enhEthAggrCDThresholdEntry  69 }

enhEthAggrCDThreshold64RxEINFLowThr  OBJECT-TYPE
    SYNTAX Counter64
    MAX-ACCESS read-write
    STATUS current
    DESCRIPTION
        "This is the 64bits low Threshold for The number of Ethernet frames received correctly
             related to current interval. Default value is NE-Product specific ."
::= { enhEthAggrCDThresholdEntry  70 }

enhEthAggrCDThreshold64RxEINBEnable  OBJECT-TYPE
    SYNTAX TruthValue
    MAX-ACCESS read-write
    STATUS current
    DESCRIPTION
        "Enabled/Disabled TCA over the number of octets of 64bits Ethernet frames received correctly,
             including Ethernet headers characters Default value: False(Disabled TCA)"
::= { enhEthAggrCDThresholdEntry  71 }

enhEthAggrCDThreshold64RxEINBHighThr  OBJECT-TYPE
    SYNTAX Counter64
    MAX-ACCESS read-write
    STATUS current
    DESCRIPTION
        "The 64bits number of octets of Ethernet frames received correctly, including Ethernet headers characters
             related to current interval. Default value is NE-Product specific"
::= { enhEthAggrCDThresholdEntry  72 }

enhEthAggrCDThreshold64RxEINBLowThr  OBJECT-TYPE
    SYNTAX Counter64
    MAX-ACCESS read-write
    STATUS current
    DESCRIPTION
        "This is the 64bits low Threshold for The number of octets of Ethernet frames received correctly,
              including Ethernet headers characters related to current interval. Default value is NE-Product specific"
::= { enhEthAggrCDThresholdEntry  73 }


enhEthAggrCDThreshold64RxEINFUnicastEnable  OBJECT-TYPE
    SYNTAX TruthValue
    MAX-ACCESS read-write
    STATUS current
    DESCRIPTION
           "Enabled/Disabled TCA over the 64bits collected number of Ethernet Unicast frames received correctly.
            Default value: False(Disabled TCA)"
::= { enhEthAggrCDThresholdEntry  74 }

enhEthAggrCDThreshold64RxEINFUnicastHighThr  OBJECT-TYPE
    SYNTAX Counter64
    MAX-ACCESS read-write
    STATUS current
    DESCRIPTION
           "This is the 64bits high Threshold for the collected number of Ethernet Unicast frames received correctly by the Virtual Ethernet Interface
             related to current interval. Default value is NE-Product specific."
::= { enhEthAggrCDThresholdEntry  75 }

enhEthAggrCDThreshold64RxEINFUnicastLowThr  OBJECT-TYPE
    SYNTAX Counter64
    MAX-ACCESS read-write
    STATUS current
    DESCRIPTION
           "This is the 64bits low Threshold for The collected number of Ethernet Unicast frames received correctly by the Virtual Ethernet Interface
             related to current interval. Default value is NE-Product specific."
::= { enhEthAggrCDThresholdEntry  76 }


enhEthAggrCDThreshold64RxEINFMulticastEnable  OBJECT-TYPE
    SYNTAX TruthValue
    MAX-ACCESS read-write
    STATUS current
    DESCRIPTION
            "Enabled/Disabled TCA over The 64bits collected number of Ethernet Multicast frames received correctly. Default value: False(Disabled TCA)"
::= { enhEthAggrCDThresholdEntry  77 }

enhEthAggrCDThreshold64RxEINFMulticastHighThr  OBJECT-TYPE
    SYNTAX Counter64
    MAX-ACCESS read-write
    STATUS current
    DESCRIPTION
            "This is the 64bits high Threshold for The collected number of Ethernet Multicast frames received
             correctly related to current interval. Default value is NE-Product specific ."
::= { enhEthAggrCDThresholdEntry  78 }

enhEthAggrCDThreshold64RxEINFMulticastLowThr  OBJECT-TYPE
    SYNTAX Counter64
    MAX-ACCESS read-write
    STATUS current
    DESCRIPTION
            "This is the 64bits low Threshold for The collected number of Ethernet Multicast frames received
             correctly related to current interval. Default value is NE-Product specific ."
::= { enhEthAggrCDThresholdEntry  79 }

enhEthAggrCDThreshold64RxEINFBroadcastEnable  OBJECT-TYPE
    SYNTAX TruthValue
    MAX-ACCESS read-write
    STATUS current
    DESCRIPTION
            "Enabled/Disabled TCA over The 64bits collected number of Ethernet Broadcast frames received
             correctly. Default value: False(Disabled TCA)"
::= { enhEthAggrCDThresholdEntry  80 }

enhEthAggrCDThreshold64RxEINFBroadcastHighThr  OBJECT-TYPE
    SYNTAX Counter64
    MAX-ACCESS read-write
    STATUS current
    DESCRIPTION
            "This is the 64bits high Threshold for The collected number of Ethernet Broadcast frames received
             correctly related to current interval. Default value is NE-Product specific ."
::= { enhEthAggrCDThresholdEntry  81 }

enhEthAggrCDThreshold64RxEINFBroadcastLowThr  OBJECT-TYPE
    SYNTAX Counter64
    MAX-ACCESS read-write
    STATUS current
    DESCRIPTION
            "This is the 64bits low Threshold for The collected number of Ethernet Broadcast frames received
             correctly related to current interval. Default value is NE-Product specific."
::= { enhEthAggrCDThresholdEntry  82 }



enhEthAggrCDThreshold64TxEONFEnable  OBJECT-TYPE
    SYNTAX TruthValue
    MAX-ACCESS read-write
    STATUS current
    DESCRIPTION
        "Enabled/Disabled TCA over The 64bits number of Ethernet frames transmitted out.Default value: False(Disabled TCA)"
::= { enhEthAggrCDThresholdEntry  83 }
enhEthAggrCDThreshold64TxEONFHighThr  OBJECT-TYPE
    SYNTAX Counter64
    MAX-ACCESS read-write
    STATUS current
    DESCRIPTION
        "This is the 64bits high Threshold for the number of Ethernet frames transmitted out related to current interval. Default value is NE-Product specific ."
::= { enhEthAggrCDThresholdEntry  84 }
enhEthAggrCDThreshold64TxEONFLowThr  OBJECT-TYPE
    SYNTAX Counter64
    MAX-ACCESS read-write
    STATUS current
    DESCRIPTION
        "This is the 64bits low Threshold for The number of Ethernet frames transmitted out related to current interval. Default value is NE-Product specific."
::= { enhEthAggrCDThresholdEntry  85 }

enhEthAggrCDThreshold64TxEONBEnable  OBJECT-TYPE
    SYNTAX TruthValue
    MAX-ACCESS read-write
    STATUS current
    DESCRIPTION
        "Enabled/Disabled TCA over The 64bits number of octets of Ethernet frames transmitted out,
              including Ethernet headers characters. Default value: False(Disabled TCA)"
::= { enhEthAggrCDThresholdEntry  86 }

enhEthAggrCDThreshold64TxEONBHighThr  OBJECT-TYPE
    SYNTAX Counter64
    MAX-ACCESS read-write
    STATUS current
    DESCRIPTION
        "The 64bits number of octets of Ethernet frames transmitted out, including Ethernet headers characters
             related to current interval. Default value is NE-Product specific"
::= { enhEthAggrCDThresholdEntry  87 }

enhEthAggrCDThreshold64TxEONBLowThr  OBJECT-TYPE
    SYNTAX Counter64
    MAX-ACCESS read-write
    STATUS current
    DESCRIPTION
        "This is the 64bits low Threshold for The number of octets of Ethernet frames transmitted out,
             including Ethernet headers characters related to current interval. Default value is NE-Product specific "
::= { enhEthAggrCDThresholdEntry  88 }

enhEthAggrCDThreshold64TxEONFUnicastEnable  OBJECT-TYPE
    SYNTAX TruthValue
    MAX-ACCESS read-write
    STATUS current
    DESCRIPTION
            "Enabled/Disabled TCA over The 64bits collected number of Ethernet Unicast frames transmitted out.
             Default value: False(Disabled TCA)"
::= { enhEthAggrCDThresholdEntry  89 }

enhEthAggrCDThreshold64TxEONFUnicastHighThr  OBJECT-TYPE
    SYNTAX Counter64
    MAX-ACCESS read-write
    STATUS current
    DESCRIPTION
            "This is the 64bits high Threshold for the collected number of Ethernet Unicast frames transmitted out
             related to current interval. Default value is NE-Product specific."
::= { enhEthAggrCDThresholdEntry  90 }

enhEthAggrCDThreshold64TxEONFUnicastLowThr  OBJECT-TYPE
    SYNTAX Counter64
    MAX-ACCESS read-write
    STATUS current
    DESCRIPTION
            "This is the 64bits low Threshold for the collected number of Ethernet Unicast frames transmitted out
             related to current interval. Default value is NE-Product specific."
::= { enhEthAggrCDThresholdEntry  91 }


enhEthAggrCDThreshold64TxEONFMulticastEnable  OBJECT-TYPE
    SYNTAX TruthValue
    MAX-ACCESS read-write
    STATUS current
    DESCRIPTION
            "Enabled/Disabled TCA over The 64bits collected number of Ethernet Multicast frames transmitted
             out. Default value: False(Disabled TCA)"
::= { enhEthAggrCDThresholdEntry  92 }
enhEthAggrCDThreshold64TxEONFMulticastHighThr  OBJECT-TYPE
    SYNTAX Counter64
    MAX-ACCESS read-write
    STATUS current
    DESCRIPTION
            "This is the 64bits high Threshold for The collected number of Ethernet Multicast frames transmitted
             out related to current interval. Default value is NE-Product specific."
::= { enhEthAggrCDThresholdEntry  93 }
enhEthAggrCDThreshold64TxEONFMulticastLowThr  OBJECT-TYPE
    SYNTAX Counter64
    MAX-ACCESS read-write
    STATUS current
    DESCRIPTION
            "This is the 64bits low Threshold for The collected number of Ethernet Multicast frames transmitted
             out related to current interval. Default value is NE-Product specific."
::= { enhEthAggrCDThresholdEntry  94 }

enhEthAggrCDThreshold64TxEONFBroadcastEnable  OBJECT-TYPE
    SYNTAX TruthValue
    MAX-ACCESS read-write
    STATUS current
    DESCRIPTION
            "Enabled/Disabled TCA over the 64bits collected number of Ethernet Broadcast frames transmitted out.
             Default value: False(Disabled TCA)"
::= { enhEthAggrCDThresholdEntry  95 }

enhEthAggrCDThreshold64TxEONFBroadcastHighThr  OBJECT-TYPE
    SYNTAX Counter64
    MAX-ACCESS read-write
    STATUS current
    DESCRIPTION
            "This is the 64bits high Threshold for the collected number of Ethernet Broadcast frames transmitted out
             related to current interval. Default value is NE-Product specific."
::= { enhEthAggrCDThresholdEntry  96 }
enhEthAggrCDThreshold64TxEONFBroadcastLowThr  OBJECT-TYPE
    SYNTAX Counter64
    MAX-ACCESS read-write
    STATUS current
    DESCRIPTION
            "This is the 64bits low Threshold for The collected number of Ethernet Broadcast frames transmitted out
              related to current interval. Default value is NE-Product specific."
::= { enhEthAggrCDThresholdEntry  97 }


--- April2011 End











enhEtsFlowCDThresholdIndexNext OBJECT-TYPE
      SYNTAX        Unsigned32
      MAX-ACCESS    read-only
      STATUS        current
      DESCRIPTION
         "Value to be used as the index of the threshold
         profile in order to create a new row in the table."
::= { opticsIMEthPmMib 52 }

enhEtsFlowCDThresholdTable OBJECT-TYPE
    SYNTAX        SEQUENCE OF EnhEtsFlowCDThresholdEntry
    MAX-ACCESS    not-accessible
    STATUS        current
    DESCRIPTION
          "This table contains the high and low thresholds
           for the Enhanced Flow CD  Threshold Crossing Alert and Reset."
::= { opticsIMEthPmMib 53 }

enhEtsFlowCDThresholdEntry OBJECT-TYPE
      SYNTAX        EnhEtsFlowCDThresholdEntry
      MAX-ACCESS    not-accessible
      STATUS        current
      DESCRIPTION
         "An entry (row) containing Enhanced Flow CD  Granularity-based high and low threshold
          values."
      INDEX { enhEtsFlowCDThresholdIndex, enhEtsFlowCDThresholdGranularityPeriod }
 ::= { enhEtsFlowCDThresholdTable 1 }

EnhEtsFlowCDThresholdEntry ::=
  SEQUENCE {
    enhEtsFlowCDThresholdIndex                  INTEGER,
    enhEtsFlowCDThresholdGranularityPeriod      OpticsIMPmGranularityPeriod,
    enhEtsFlowCDThresholdEINFgEnable             TruthValue,
    enhEtsFlowCDThresholdEINFgHighThr            Gauge32,
    enhEtsFlowCDThresholdEINFgLowThr             Gauge32,
    enhEtsFlowCDThresholdEINBgEnable                TruthValue,
    enhEtsFlowCDThresholdEINBgHighThr            Gauge32,
    enhEtsFlowCDThresholdEINBgLowThr              Gauge32,
    enhEtsFlowCDThresholdEINFyEnable              TruthValue,
    enhEtsFlowCDThresholdEINFyHighThr             Gauge32,
    enhEtsFlowCDThresholdEINFyLowThr              Gauge32,
    enhEtsFlowCDThresholdEINFrEnable              TruthValue,
    enhEtsFlowCDThresholdEINFrHighThr              Gauge32,
    enhEtsFlowCDThresholdEINFrLowThr              Gauge32,
    enhEtsFlowCDThresholdEINByEnable              TruthValue,
    enhEtsFlowCDThresholdEINByHighThr              Gauge32,
    enhEtsFlowCDThresholdEINByLowThr              Gauge32,
    enhEtsFlowCDThresholdEINBrEnable              TruthValue,
    enhEtsFlowCDThresholdEINBrHighThr              Gauge32,
    enhEtsFlowCDThresholdEINBrLowThr              Gauge32,
    enhEtsFlowCDThresholdEONFgEnable              TruthValue,
    enhEtsFlowCDThresholdEONFgHighThr              Gauge32,
    enhEtsFlowCDThresholdEONFgLowThr              Gauge32,
    enhEtsFlowCDThresholdEONBgEnable              TruthValue,
    enhEtsFlowCDThresholdEONBgHighThr              Gauge32,
    enhEtsFlowCDThresholdEONBgLowThr              Gauge32,
    enhEtsFlowCDThresholdEONFyEnable              TruthValue,
    enhEtsFlowCDThresholdEONFyHighThr              Gauge32,
    enhEtsFlowCDThresholdEONFyLowThr              Gauge32,
    enhEtsFlowCDThresholdEONByEnable              TruthValue,
    enhEtsFlowCDThresholdEONByHighThr              Gauge32,
    enhEtsFlowCDThresholdEONByLowThr              Gauge32,
    enhEtsFlowCDThresholdUserLabel               OCTET STRING,
    enhEtsFlowCDThresholdRowStatus               RowStatus,

---April2011 Begin

    enhEtsFlowCDThreshold64EINFgEnable               TruthValue,
    enhEtsFlowCDThreshold64EINFgHighThr              Counter64,
    enhEtsFlowCDThreshold64EINFgLowThr               Counter64,
    enhEtsFlowCDThreshold64EINBgEnable            TruthValue,
    enhEtsFlowCDThreshold64EINBgHighThr              Counter64,
    enhEtsFlowCDThreshold64EINBgLowThr              Counter64,
    enhEtsFlowCDThreshold64EINFyEnable              TruthValue,
    enhEtsFlowCDThreshold64EINFyHighThr             Counter64,
    enhEtsFlowCDThreshold64EINFyLowThr              Counter64,
    enhEtsFlowCDThreshold64EINFrEnable              TruthValue,
    enhEtsFlowCDThreshold64EINFrHighThr          Counter64,
    enhEtsFlowCDThreshold64EINFrLowThr              Counter64,
    enhEtsFlowCDThreshold64EINByEnable              TruthValue,
    enhEtsFlowCDThreshold64EINByHighThr          Counter64,
    enhEtsFlowCDThreshold64EINByLowThr              Counter64,
    enhEtsFlowCDThreshold64EINBrEnable              TruthValue,
    enhEtsFlowCDThreshold64EINBrHighThr             Counter64,
    enhEtsFlowCDThreshold64EINBrLowThr              Counter64,
    enhEtsFlowCDThreshold64EONFgEnable           TruthValue,
    enhEtsFlowCDThreshold64EONFgHighThr          Counter64,
    enhEtsFlowCDThreshold64EONFgLowThr                  Counter64,
    enhEtsFlowCDThreshold64EONBgEnable              TruthValue,
    enhEtsFlowCDThreshold64EONBgHighThr          Counter64,
    enhEtsFlowCDThreshold64EONBgLowThr              Counter64,
    enhEtsFlowCDThreshold64EONFyEnable              TruthValue,
    enhEtsFlowCDThreshold64EONFyHighThr          Counter64,
    enhEtsFlowCDThreshold64EONFyLowThr              Counter64,
    enhEtsFlowCDThreshold64EONByEnable              TruthValue,
    enhEtsFlowCDThreshold64EONByHighThr             Counter64,
    enhEtsFlowCDThreshold64EONByLowThr              Counter64

---April2011 End


}

enhEtsFlowCDThresholdIndex OBJECT-TYPE
     SYNTAX        INTEGER
     MAX-ACCESS    not-accessible
     STATUS        current
     DESCRIPTION
         "This is the index to the Enhanced (Granularity-based) threshold row."
 ::= { enhEtsFlowCDThresholdEntry 1 }

enhEtsFlowCDThresholdGranularityPeriod OBJECT-TYPE
     SYNTAX        OpticsIMPmGranularityPeriod
     MAX-ACCESS    not-accessible
     STATUS        current
     DESCRIPTION
         "This is the last index to the Enhanced (Granularity-based) Threshold row -
          See Textual Convention."
 ::= { enhEtsFlowCDThresholdEntry 2 }

enhEtsFlowCDThresholdEINFgEnable  OBJECT-TYPE
    SYNTAX TruthValue
    MAX-ACCESS read-write
    STATUS current
    DESCRIPTION
    "Enabled/Disabled TCA over number of green Ethernet frames received correctly."
    ::= { enhEtsFlowCDThresholdEntry 3 }

    enhEtsFlowCDThresholdEINFgHighThr  OBJECT-TYPE
    SYNTAX Gauge32
    MAX-ACCESS read-write
    STATUS current
    DESCRIPTION
    "This is the high Threshold for number of green Ethernet frames received correctly related to current interval. Default value is NE-Product specific ."
    ::= { enhEtsFlowCDThresholdEntry 4 }

enhEtsFlowCDThresholdEINFgLowThr  OBJECT-TYPE
    SYNTAX Gauge32
    MAX-ACCESS read-write
    STATUS current
    DESCRIPTION
    "This is the low Threshold for number of green Ethernet frames received correctly related to current interval. Default value is NE-Product specific."
    ::= { enhEtsFlowCDThresholdEntry 5 }


enhEtsFlowCDThresholdEINBgEnable    OBJECT-TYPE
    SYNTAX TruthValue
    MAX-ACCESS read-write
    STATUS current
    DESCRIPTION
    "Enabled/Disabled TCA over number of octets of  green Ethernet frames received correctly for this flow, including Ethernet headers characters
       Default value: False(Disabled TCA)"
    ::= { enhEtsFlowCDThresholdEntry 6 }

    enhEtsFlowCDThresholdEINBgHighThr    OBJECT-TYPE
    SYNTAX Gauge32
    MAX-ACCESS read-write
    STATUS current
    DESCRIPTION
    "This is the high Threshold for number of octets of  green Ethernet frames received correctly for this flow, including Ethernet headers characters
       related to current interval. Default value is NE-Product specific"
    ::= { enhEtsFlowCDThresholdEntry 7 }

enhEtsFlowCDThresholdEINBgLowThr  OBJECT-TYPE
    SYNTAX Gauge32
    MAX-ACCESS read-write
    STATUS current
    DESCRIPTION
    "This is the low Threshold for number of octets of  green Ethernet frames received correctly for this flow, including Ethernet headers characters
       related to current interval. Default value is NE-Product specific"
    ::= { enhEtsFlowCDThresholdEntry 8 }

enhEtsFlowCDThresholdEINFyEnable  OBJECT-TYPE
    SYNTAX TruthValue
    MAX-ACCESS read-write
    STATUS current
    DESCRIPTION
      "Enabled/Disabled TCA over number of yellow Ethernet frames received correctly. Default value: False(Disabled TCA)"
    ::= { enhEtsFlowCDThresholdEntry 9 }
enhEtsFlowCDThresholdEINFyHighThr OBJECT-TYPE
    SYNTAX Gauge32
    MAX-ACCESS read-write
    STATUS current
    DESCRIPTION
      "This is the high Threshold for number of yellow Ethernet frames received correctly related to current interval.
       Default value is NE-Product specific."
    ::= { enhEtsFlowCDThresholdEntry 10 }

enhEtsFlowCDThresholdEINFyLowThr OBJECT-TYPE
    SYNTAX Gauge32
    MAX-ACCESS read-write
    STATUS current
    DESCRIPTION
      "This is the low Threshold for number of yellow Ethernet frames received correctly related to current interval.
       Default value is NE-Product specific ."
    ::= { enhEtsFlowCDThresholdEntry 11 }

enhEtsFlowCDThresholdEINFrEnable OBJECT-TYPE
    SYNTAX TruthValue
    MAX-ACCESS read-write
    STATUS current
    DESCRIPTION
      "Enabled/Disabled TCA over number of red Ethernet frames received correctly.Default value: False(Disabled TCA)"
    ::= { enhEtsFlowCDThresholdEntry 12 }

enhEtsFlowCDThresholdEINFrHighThr OBJECT-TYPE
    SYNTAX Gauge32
    MAX-ACCESS read-write
    STATUS current
    DESCRIPTION
      "This is the high Threshold for number of red Ethernet frames received correctly related to current interval. Default value is NE-Product specific."
    ::= { enhEtsFlowCDThresholdEntry 13 }

enhEtsFlowCDThresholdEINFrLowThr OBJECT-TYPE
    SYNTAX Gauge32
    MAX-ACCESS read-write
    STATUS current
    DESCRIPTION
      "This is the low Threshold for number of red Ethernet frames received correctly related to current interval. Default value is NE-Product specific."
    ::= { enhEtsFlowCDThresholdEntry 14 }

enhEtsFlowCDThresholdEINByEnable OBJECT-TYPE
    SYNTAX TruthValue
    MAX-ACCESS read-write
    STATUS current
    DESCRIPTION
      " Enabled/Disabled TCA over number of octets of yellow Ethernet frames received correctly for this flow, including Ethernet headers characters.
        Default value: False(Disabled TCA)"
    ::= { enhEtsFlowCDThresholdEntry 15 }

enhEtsFlowCDThresholdEINByHighThr OBJECT-TYPE
    SYNTAX Gauge32
    MAX-ACCESS read-write
    STATUS current
    DESCRIPTION
      "This is the high Threshold for number of octets of yellow Ethernet frames received correctly for this flow, including Ethernet
       headers characters related to current interval. Default value is NE-Product specific."
    ::= { enhEtsFlowCDThresholdEntry 16 }
enhEtsFlowCDThresholdEINByLowThr OBJECT-TYPE
    SYNTAX Gauge32
    MAX-ACCESS read-write
    STATUS current
    DESCRIPTION
      " This is the low Threshold for number of octets of yellow Ethernet frames received correctly for this flow,
        including Ethernet headers characters related to current interval. Default value is NE-Product specific."
    ::= { enhEtsFlowCDThresholdEntry 17 }

enhEtsFlowCDThresholdEINBrEnable OBJECT-TYPE
    SYNTAX TruthValue
    MAX-ACCESS read-write
    STATUS current
    DESCRIPTION
      "Enabled/Disabled TCA over number of octets of red Ethernet frames received correctly for this flow, including Ethernet headers characters.
       Default value: False(Disabled TCA)"
    ::= { enhEtsFlowCDThresholdEntry 18 }
enhEtsFlowCDThresholdEINBrHighThr OBJECT-TYPE
    SYNTAX Gauge32
    MAX-ACCESS read-write
    STATUS current
    DESCRIPTION
      " This is the high Threshold for number of octets of red Ethernet frames received correctly for this flow, including Ethernet headers characters
       related to current interval. Default value is NE-Product specific."
::= { enhEtsFlowCDThresholdEntry 19 }
enhEtsFlowCDThresholdEINBrLowThr OBJECT-TYPE
    SYNTAX Gauge32
    MAX-ACCESS read-write
    STATUS current
    DESCRIPTION
      " This is the low Threshold for number of octets of red Ethernet frames received correctly for this flow, including Ethernet headers characters
         related to current interval. Default value is NE-Product specific."
::= { enhEtsFlowCDThresholdEntry 20 }

enhEtsFlowCDThresholdEONFgEnable OBJECT-TYPE
    SYNTAX TruthValue
    MAX-ACCESS read-write
    STATUS current
    DESCRIPTION
    "Enabled/Disabled TCA over Total number of green Ethernet frames transmitted out.Default value: False(Disabled TCA)"
::= { enhEtsFlowCDThresholdEntry 21 }

enhEtsFlowCDThresholdEONFgHighThr OBJECT-TYPE
    SYNTAX Gauge32
    MAX-ACCESS read-write
    STATUS current
    DESCRIPTION
    "This is the high Threshold for Total number of green Ethernet frames transmitted out related to current interval.
         Default value is NE-Product specific."
::= { enhEtsFlowCDThresholdEntry 22 }

enhEtsFlowCDThresholdEONFgLowThr OBJECT-TYPE
    SYNTAX Gauge32
    MAX-ACCESS read-write
    STATUS current
    DESCRIPTION
    "This is the low Threshold for Total number of green Ethernet frames transmitted out related to current interval.
         Default value is NE-Product specific."
::= { enhEtsFlowCDThresholdEntry 23 }

enhEtsFlowCDThresholdEONBgEnable OBJECT-TYPE
    SYNTAX TruthValue
    MAX-ACCESS read-write
    STATUS current
    DESCRIPTION
    "Enabled/Disabled TCA over Total number of octets of green Ethernet frames transmitted out, including  Ethernet header characters.
       Default value: False(Disabled TCA)"
::= { enhEtsFlowCDThresholdEntry 24 }

enhEtsFlowCDThresholdEONBgHighThr OBJECT-TYPE
    SYNTAX Gauge32
    MAX-ACCESS read-write
    STATUS current
    DESCRIPTION
    "This is the high Threshold for Total number of octets of green Ethernet frames transmitted out, including  Ethernet header characters
       related to current interval. Default value is NE-Product specific."
::= { enhEtsFlowCDThresholdEntry 25 }

enhEtsFlowCDThresholdEONBgLowThr OBJECT-TYPE
    SYNTAX Gauge32
    MAX-ACCESS read-write
    STATUS current
    DESCRIPTION
    "This is the low Threshold for Total number of octets of green Ethernet frames transmitted out, including  Ethernet header characters
       related to current interval. Default value is NE-Product specific."
::= { enhEtsFlowCDThresholdEntry 26}


enhEtsFlowCDThresholdEONFyEnable OBJECT-TYPE
    SYNTAX TruthValue
    MAX-ACCESS read-write
    STATUS current
    DESCRIPTION
      "Enabled/Disabled TCA over Total number of yellow Ethernet frames transmitted out.Default value: False(Disabled TCA)"
::= { enhEtsFlowCDThresholdEntry 27 }

enhEtsFlowCDThresholdEONFyHighThr OBJECT-TYPE
    SYNTAX Gauge32
    MAX-ACCESS read-write
    STATUS current
    DESCRIPTION
      "This is the high Threshold for Total number of yellow Ethernet frames transmitted out related to current interval.
       Default value is NE-Product specific."
::= { enhEtsFlowCDThresholdEntry 28 }

enhEtsFlowCDThresholdEONFyLowThr OBJECT-TYPE
    SYNTAX Gauge32
    MAX-ACCESS read-write
    STATUS current
    DESCRIPTION
      "This is the low Threshold for Total number of yellow Ethernet frames transmitted out related to current interval.
       Default value is NE-Product specific."
::= { enhEtsFlowCDThresholdEntry 29 }


enhEtsFlowCDThresholdEONByEnable OBJECT-TYPE
    SYNTAX TruthValue
    MAX-ACCESS read-write
    STATUS current
    DESCRIPTION
      "Enabled/Disabled TCA over Total number of octets of yellow Ethernet frames transmitted out,including Ethernet header characters.
      Default value: False(Disabled TCA)"
::= { enhEtsFlowCDThresholdEntry 30 }

enhEtsFlowCDThresholdEONByHighThr OBJECT-TYPE
    SYNTAX Gauge32
    MAX-ACCESS read-write
    STATUS current
    DESCRIPTION
      "This is the high Threshold for Total number of octets of yellow Ethernet frames transmitted out,including Ethernet header characters related to current interval.
      Default value is NE-Product specific."
::= { enhEtsFlowCDThresholdEntry 31 }

enhEtsFlowCDThresholdEONByLowThr OBJECT-TYPE
    SYNTAX Gauge32
    MAX-ACCESS read-write
    STATUS current
    DESCRIPTION
      "This is the low Threshold for Total number of octets of yellow Ethernet frames transmitted out,including Ethernet header characters related to current interval.
      Default value is NE-Product specific."
::= { enhEtsFlowCDThresholdEntry 32 }

enhEtsFlowCDThresholdUserLabel OBJECT-TYPE
     SYNTAX        OCTET STRING
     MAX-ACCESS    read-write
     STATUS        current
     DESCRIPTION
         "This is the user label used to identify the profile."
 ::= { enhEtsFlowCDThresholdEntry 33 }

enhEtsFlowCDThresholdRowStatus OBJECT-TYPE
     SYNTAX        RowStatus
     MAX-ACCESS    read-create
     STATUS        current
     DESCRIPTION
         "This is the status of the row. It can be used to
         create/destroy the row."
 ::= { enhEtsFlowCDThresholdEntry 34 }

---April2011 Begin

enhEtsFlowCDThreshold64EINFgEnable  OBJECT-TYPE
    SYNTAX TruthValue
    MAX-ACCESS read-write
    STATUS current
    DESCRIPTION
    "Enabled/Disabled TCA over 64bits number of green Ethernet frames received correctly."
    ::= { enhEtsFlowCDThresholdEntry 35 }

    enhEtsFlowCDThreshold64EINFgHighThr  OBJECT-TYPE
    SYNTAX Counter64
    MAX-ACCESS read-write
    STATUS current
    DESCRIPTION
    "This is the 64bits high Threshold for number of green Ethernet frames received correctly related to current interval. Default value is NE-Product specific ."
    ::= { enhEtsFlowCDThresholdEntry 36 }

enhEtsFlowCDThreshold64EINFgLowThr  OBJECT-TYPE
    SYNTAX Counter64
    MAX-ACCESS read-write
    STATUS current
    DESCRIPTION
    "This is the 64bits low Threshold for number of green Ethernet frames received correctly related to current interval. Default value is NE-Product specific."
    ::= { enhEtsFlowCDThresholdEntry 37 }


enhEtsFlowCDThreshold64EINBgEnable    OBJECT-TYPE
    SYNTAX TruthValue
    MAX-ACCESS read-write
    STATUS current
    DESCRIPTION
    "Enabled/Disabled TCA over 64bits number of octets of  green Ethernet frames received correctly for this flow, including Ethernet headers characters
       Default value: False(Disabled TCA)"
    ::= { enhEtsFlowCDThresholdEntry 38 }

    enhEtsFlowCDThreshold64EINBgHighThr    OBJECT-TYPE
    SYNTAX Counter64
    MAX-ACCESS read-write
    STATUS current
    DESCRIPTION
    "This is the 64bits high Threshold for number of octets of  green Ethernet frames received correctly for this flow, including Ethernet headers characters
       related to current interval. Default value is NE-Product specific"
    ::= { enhEtsFlowCDThresholdEntry 39 }

enhEtsFlowCDThreshold64EINBgLowThr  OBJECT-TYPE
    SYNTAX Counter64
    MAX-ACCESS read-write
    STATUS current
    DESCRIPTION
    "This is the 64bits low Threshold for number of octets of  green Ethernet frames received correctly for this flow, including Ethernet headers characters
       related to current interval. Default value is NE-Product specific"
    ::= { enhEtsFlowCDThresholdEntry 40 }

enhEtsFlowCDThreshold64EINFyEnable  OBJECT-TYPE
    SYNTAX TruthValue
    MAX-ACCESS read-write
    STATUS current
    DESCRIPTION
      "Enabled/Disabled TCA over 64bits number of yellow Ethernet frames received correctly. Default value: False(Disabled TCA)"
    ::= { enhEtsFlowCDThresholdEntry 41 }
enhEtsFlowCDThreshold64EINFyHighThr OBJECT-TYPE
    SYNTAX Counter64
    MAX-ACCESS read-write
    STATUS current
    DESCRIPTION
      "This is the 64bits high Threshold for number of yellow Ethernet frames received correctly related to current interval.
       Default value is NE-Product specific."
    ::= { enhEtsFlowCDThresholdEntry 42 }

enhEtsFlowCDThreshold64EINFyLowThr OBJECT-TYPE
    SYNTAX Counter64
    MAX-ACCESS read-write
    STATUS current
    DESCRIPTION
      "This is the 64bits low Threshold for number of yellow Ethernet frames received correctly related to current interval.
       Default value is NE-Product specific ."
    ::= { enhEtsFlowCDThresholdEntry 43 }

enhEtsFlowCDThreshold64EINFrEnable OBJECT-TYPE
    SYNTAX TruthValue
    MAX-ACCESS read-write
    STATUS current
    DESCRIPTION
      "Enabled/Disabled TCA over 64bits number of red Ethernet frames received correctly.Default value: False(Disabled TCA)"
    ::= { enhEtsFlowCDThresholdEntry 44 }

enhEtsFlowCDThreshold64EINFrHighThr OBJECT-TYPE
    SYNTAX Counter64
    MAX-ACCESS read-write
    STATUS current
    DESCRIPTION
      "This is the 64bits high Threshold for number of red Ethernet frames received correctly related to current interval. Default value is NE-Product specific."
    ::= { enhEtsFlowCDThresholdEntry 45 }

enhEtsFlowCDThreshold64EINFrLowThr OBJECT-TYPE
    SYNTAX Counter64
    MAX-ACCESS read-write
    STATUS current
    DESCRIPTION
      "This is the 64bits low Threshold for number of red Ethernet frames received correctly related to current interval. Default value is NE-Product specific."
    ::= { enhEtsFlowCDThresholdEntry 46 }

enhEtsFlowCDThreshold64EINByEnable OBJECT-TYPE
    SYNTAX TruthValue
    MAX-ACCESS read-write
    STATUS current
    DESCRIPTION
      " Enabled/Disabled TCA over 64bits number of octets of yellow Ethernet frames received correctly for this flow, including Ethernet headers characters.
        Default value: False(Disabled TCA)"
    ::= { enhEtsFlowCDThresholdEntry 47 }

enhEtsFlowCDThreshold64EINByHighThr OBJECT-TYPE
    SYNTAX Counter64
    MAX-ACCESS read-write
    STATUS current
    DESCRIPTION
      "This is the 64bits high Threshold for number of octets of yellow Ethernet frames received correctly for this flow, including Ethernet
       headers characters related to current interval. Default value is NE-Product specific."
    ::= { enhEtsFlowCDThresholdEntry 48 }
enhEtsFlowCDThreshold64EINByLowThr OBJECT-TYPE
    SYNTAX Counter64
    MAX-ACCESS read-write
    STATUS current
    DESCRIPTION
      " This is the 64bits low Threshold for number of octets of yellow Ethernet frames received correctly for this flow,
        including Ethernet headers characters related to current interval. Default value is NE-Product specific."
    ::= { enhEtsFlowCDThresholdEntry 49 }

enhEtsFlowCDThreshold64EINBrEnable OBJECT-TYPE
    SYNTAX TruthValue
    MAX-ACCESS read-write
    STATUS current
    DESCRIPTION
      "Enabled/Disabled TCA over 64bits number of octets of red Ethernet frames received correctly for this flow, including Ethernet headers characters.
       Default value: False(Disabled TCA)"
    ::= { enhEtsFlowCDThresholdEntry 50 }

enhEtsFlowCDThreshold64EINBrHighThr OBJECT-TYPE
    SYNTAX Counter64
    MAX-ACCESS read-write
    STATUS current
    DESCRIPTION
      " This is the 64bits high Threshold for number of octets of red Ethernet frames received correctly for this flow, including Ethernet headers characters
       related to current interval. Default value is NE-Product specific."
::= { enhEtsFlowCDThresholdEntry 51 }

enhEtsFlowCDThreshold64EINBrLowThr OBJECT-TYPE
    SYNTAX Counter64
    MAX-ACCESS read-write
    STATUS current
    DESCRIPTION
      " This is the 64bits low Threshold for number of octets of red Ethernet frames received correctly for this flow, including Ethernet headers characters
         related to current interval. Default value is NE-Product specific."
::= { enhEtsFlowCDThresholdEntry 52 }

enhEtsFlowCDThreshold64EONFgEnable OBJECT-TYPE
    SYNTAX TruthValue
    MAX-ACCESS read-write
    STATUS current
    DESCRIPTION
    "Enabled/Disabled TCA over 64bits Total number of green Ethernet frames transmitted out.Default value: False(Disabled TCA)"
::= { enhEtsFlowCDThresholdEntry 53 }

enhEtsFlowCDThreshold64EONFgHighThr OBJECT-TYPE
    SYNTAX Counter64
    MAX-ACCESS read-write
    STATUS current
    DESCRIPTION
    "This is the 64bits high Threshold for Total number of green Ethernet frames transmitted out related to current interval.
         Default value is NE-Product specific."
::= { enhEtsFlowCDThresholdEntry 54 }

enhEtsFlowCDThreshold64EONFgLowThr OBJECT-TYPE
    SYNTAX Counter64
    MAX-ACCESS read-write
    STATUS current
    DESCRIPTION
    "This is the 64bits low Threshold for Total number of green Ethernet frames transmitted out related to current interval.
         Default value is NE-Product specific."
::= { enhEtsFlowCDThresholdEntry 55 }

enhEtsFlowCDThreshold64EONBgEnable OBJECT-TYPE
    SYNTAX TruthValue
    MAX-ACCESS read-write
    STATUS current
    DESCRIPTION
    "Enabled/Disabled TCA over 64bits  Total number of octets of green Ethernet frames transmitted out, including  Ethernet header characters.
       Default value: False(Disabled TCA)"
::= { enhEtsFlowCDThresholdEntry 56 }

enhEtsFlowCDThreshold64EONBgHighThr OBJECT-TYPE
    SYNTAX Counter64
    MAX-ACCESS read-write
    STATUS current
    DESCRIPTION
    "This is the 64bits high Threshold for Total number of octets of green Ethernet frames transmitted out, including  Ethernet header characters
       related to current interval. Default value is NE-Product specific."
::= { enhEtsFlowCDThresholdEntry 57 }

enhEtsFlowCDThreshold64EONBgLowThr OBJECT-TYPE
    SYNTAX Counter64
    MAX-ACCESS read-write
    STATUS current
    DESCRIPTION
    "This is the 64bits low Threshold for Total number of octets of green Ethernet frames transmitted out, including  Ethernet header characters
       related to current interval. Default value is NE-Product specific."
::= { enhEtsFlowCDThresholdEntry 58}


enhEtsFlowCDThreshold64EONFyEnable OBJECT-TYPE
    SYNTAX TruthValue
    MAX-ACCESS read-write
    STATUS current
    DESCRIPTION
      "Enabled/Disabled TCA over 64bits Total number of yellow Ethernet frames transmitted out.Default value: False(Disabled TCA)"
::= { enhEtsFlowCDThresholdEntry 59 }

enhEtsFlowCDThreshold64EONFyHighThr OBJECT-TYPE
    SYNTAX Counter64
    MAX-ACCESS read-write
    STATUS current
    DESCRIPTION
      "This is the 64bits high Threshold for Total number of yellow Ethernet frames transmitted out related to current interval.
       Default value is NE-Product specific."
::= { enhEtsFlowCDThresholdEntry 60 }

enhEtsFlowCDThreshold64EONFyLowThr OBJECT-TYPE
    SYNTAX Counter64
    MAX-ACCESS read-write
    STATUS current
    DESCRIPTION
      "This is the 64bits low Threshold for Total number of yellow Ethernet frames transmitted out related to current interval.
       Default value is NE-Product specific."
::= { enhEtsFlowCDThresholdEntry 61 }


enhEtsFlowCDThreshold64EONByEnable OBJECT-TYPE
    SYNTAX TruthValue
    MAX-ACCESS read-write
    STATUS current
    DESCRIPTION
      "Enabled/Disabled TCA over 64bits Total number of octets of yellow Ethernet frames transmitted out,including Ethernet header characters.
      Default value: False(Disabled TCA)"
::= { enhEtsFlowCDThresholdEntry 62 }

enhEtsFlowCDThreshold64EONByHighThr OBJECT-TYPE
    SYNTAX Counter64
    MAX-ACCESS read-write
    STATUS current
    DESCRIPTION
      "This is the 64bits high Threshold for Total number of octets of yellow Ethernet frames transmitted out,including Ethernet header characters related to current interval.
      Default value is NE-Product specific."
::= { enhEtsFlowCDThresholdEntry 63 }

enhEtsFlowCDThreshold64EONByLowThr OBJECT-TYPE
    SYNTAX Counter64
    MAX-ACCESS read-write
    STATUS current
    DESCRIPTION
      "This is the 64bits low Threshold for Total number of octets of yellow Ethernet frames transmitted out,including Ethernet header characters related to current interval.
      Default value is NE-Product specific."
::= { enhEtsFlowCDThresholdEntry 64 }



---April2011 End




----------------------------------------------------
-- Enhanced Aggregate Per Queue current datas table
----------------------------------------------------

        enhEthAggrPerQueueCDTable OBJECT-TYPE
            SYNTAX SEQUENCE OF EnhEthAggrPerQueueCDEntry
            MAX-ACCESS not-accessible
            STATUS current
            DESCRIPTION
                "This table contains enhanced transmitted aggregates per queue Current Datas counters."
            ::= { opticsIMEthPmMib 54 }

        enhEthAggrPerQueueCDEntry OBJECT-TYPE
            SYNTAX EnhEthAggrPerQueueCDEntry
            MAX-ACCESS not-accessible
            STATUS current
            DESCRIPTION
                "An entry of enhanced transmitted aggregates per queue Current Data counters table."
            INDEX { ifIndex, enhEthAggrPerQueueIndex, enhEthAggrPerQueueCDGranularityPeriod }
            ::= { enhEthAggrPerQueueCDTable 1 }

        EnhEthAggrPerQueueCDEntry ::=
            SEQUENCE {
                enhEthAggrPerQueueIndex
                    OpticsIMETSTrafficDescrType,
                enhEthAggrPerQueueCDGranularityPeriod
                    OpticsIMPmGranularityPeriod,
                enhEthAggrPerQueueCDEONF
                    Counter64,
                enhEthAggrPerQueueCDEONB
                    Counter64,
                enhEthAggrPerQueueCDEONFUnicast
                    Counter64,
                enhEthAggrPerQueueCDEONFMulticast
                    Counter64,
                enhEthAggrPerQueueCDEONFBroadcast
                    Counter64,
                enhEthAggrPerQueueCDStartByOS
                    TsdimManagerType,
                enhEthAggrPerQueueCDResetCounter
                    TruthValue,
                enhEthAggrPerQueueCDRowStatus
                    RowStatus,
                enhEthAggrPerQueueCDSuspectInterval
                    OpticsIMPmSuspectIntervalFlag,
                enhEthAggrPerQueueCDElapsedTime
                    OpticsIMPmElapsedTime,
                enhEthAggrPerQueueCDTDF
                    Counter64,
                        enhEthAggrPerQueueCDThresholdDataInstance
                    OpticsIMPmThresholdDataInstance,
                enhEthAggrPerQueueCDEONBRate
                    Counter64,
                enhEthAggrPerQueueCDEONBRatio
                    Counter64,
                enhEthAggrPerQueueCDTDFRatio
                    Counter64
             }

        enhEthAggrPerQueueIndex OBJECT-TYPE
            SYNTAX OpticsIMETSTrafficDescrType
            MAX-ACCESS not-accessible
            STATUS current
            DESCRIPTION
                "The index indicate the queue which serve a specific TD type see OpticsIMPmQueueIndex."
            ::= { enhEthAggrPerQueueCDEntry 1 }

        enhEthAggrPerQueueCDGranularityPeriod OBJECT-TYPE
            SYNTAX OpticsIMPmGranularityPeriod
            MAX-ACCESS not-accessible
            STATUS current
            DESCRIPTION
                "See Textual Conventions"
            ::= { enhEthAggrPerQueueCDEntry 2 }

        enhEthAggrPerQueueCDEONF OBJECT-TYPE
            SYNTAX Counter64
            MAX-ACCESS read-only
            STATUS current
            DESCRIPTION
                "The number of Ethernet frames accepted by the specific queue of this Ethernet Interface."
            ::= { enhEthAggrPerQueueCDEntry 3 }

        enhEthAggrPerQueueCDEONB OBJECT-TYPE
            SYNTAX Counter64
            MAX-ACCESS read-only
            STATUS current
            DESCRIPTION
                "The number of octects of Ethernet frames accepted by the specific queue of this Ethernet Interface,
            including Ethernet header characters."
            ::= { enhEthAggrPerQueueCDEntry 4 }

        enhEthAggrPerQueueCDEONFUnicast OBJECT-TYPE
            SYNTAX Counter64
            MAX-ACCESS read-only
            STATUS current
            DESCRIPTION
                "The number of Ethernet Unicast frames accepted by the specific queue of this Ethernet Interface."
            ::= { enhEthAggrPerQueueCDEntry 5 }

        enhEthAggrPerQueueCDEONFMulticast OBJECT-TYPE
            SYNTAX Counter64
            MAX-ACCESS read-only
            STATUS current
            DESCRIPTION
                "The number of Ethernet Multicast frames accepted by the specific queue of this Ethernet Interface."
            ::= { enhEthAggrPerQueueCDEntry 6 }

        enhEthAggrPerQueueCDEONFBroadcast OBJECT-TYPE
            SYNTAX Counter64
            MAX-ACCESS read-only
            STATUS current
            DESCRIPTION
                "The number of Ethernet Broadcast frames accepted by the specific queue of this Ethernet Interface."
            ::= { enhEthAggrPerQueueCDEntry 7 }

        enhEthAggrPerQueueCDStartByOS OBJECT-TYPE
            SYNTAX TsdimManagerType
            MAX-ACCESS read-only
            STATUS current
            DESCRIPTION
                "See Textual Conventions."
            ::= { enhEthAggrPerQueueCDEntry 8 }

        enhEthAggrPerQueueCDResetCounter OBJECT-TYPE
            SYNTAX TruthValue
            MAX-ACCESS read-create
            STATUS current
            DESCRIPTION
                     "This object allows to reset i.e. set to 0, all the current counters of the queue."
            ::= { enhEthAggrPerQueueCDEntry 9 }

        enhEthAggrPerQueueCDRowStatus OBJECT-TYPE
            SYNTAX RowStatus
            MAX-ACCESS read-create
            STATUS current
            DESCRIPTION
                "See Textual Conventions"
            ::= { enhEthAggrPerQueueCDEntry 10 }

        enhEthAggrPerQueueCDSuspectInterval OBJECT-TYPE
            SYNTAX OpticsIMPmSuspectIntervalFlag
            MAX-ACCESS read-only
            STATUS current
            DESCRIPTION
                  "See Textual Conventions."
            ::= { enhEthAggrPerQueueCDEntry 11 }

        enhEthAggrPerQueueCDElapsedTime OBJECT-TYPE
            SYNTAX OpticsIMPmElapsedTime
            MAX-ACCESS read-only
            STATUS current
            DESCRIPTION
                       "See Textual Conventions."
            ::= { enhEthAggrPerQueueCDEntry 12 }

        enhEthAggrPerQueueCDTDF OBJECT-TYPE
            SYNTAX Counter64
            MAX-ACCESS read-only
            STATUS current
            DESCRIPTION
                "The number of Ethernet frames discarded by the specific queue due to buffer congestion."
            ::= { enhEthAggrPerQueueCDEntry 13 }

           enhEthAggrPerQueueCDThresholdDataInstance OBJECT-TYPE
                  SYNTAX  OpticsIMPmThresholdDataInstance
                 MAX-ACCESS read-write
                 STATUS current
                 DESCRIPTION
                        "This is a pointer to Enhanced Aggregate PM Threshold Data."
                  ::= { enhEthAggrPerQueueCDEntry 14 }

        enhEthAggrPerQueueCDEONBRate OBJECT-TYPE
            SYNTAX Counter64
            MAX-ACCESS read-only
            STATUS current
            DESCRIPTION
            "The Rate of transmitted good bytes (in Mbps) by the specific queue"
            ::= { enhEthAggrPerQueueCDEntry 15 }

        enhEthAggrPerQueueCDEONBRatio OBJECT-TYPE
            SYNTAX Counter64
            MAX-ACCESS read-only
            STATUS current
            DESCRIPTION
            "The Ratio of transmitted good bytes by the specific queue"
            ::= { enhEthAggrPerQueueCDEntry 16 }

        enhEthAggrPerQueueCDTDFRatio OBJECT-TYPE
                  SYNTAX  Counter64
                 MAX-ACCESS read-only
                 STATUS current
                 DESCRIPTION
            "The Ratio of packets dropped by the specific queue due to lack of resources"
                  ::= { enhEthAggrPerQueueCDEntry 17 }


---------------------------------------------------
-- Enhanced Aggregate Per Queue hystory datas table
---------------------------------------------------

        enhEthAggrPerQueueHDTable OBJECT-TYPE
            SYNTAX SEQUENCE OF EnhEthAggrPerQueueHDEntry
            MAX-ACCESS not-accessible
            STATUS current
            DESCRIPTION
                "This table contains enhanced transmitted aggregates per queue Hystory Datas counters."
            ::= { opticsIMEthPmMib 55 }

        enhEthAggrPerQueueHDEntry OBJECT-TYPE
            SYNTAX EnhEthAggrPerQueueHDEntry
            MAX-ACCESS not-accessible
            STATUS current
            DESCRIPTION
                "An entry of enhanced transmitted aggregates per queue Hystory Data counters table."
            INDEX { ifIndex, enhEthAggrPerQueueIndex, enhEthAggrPerQueueHDGranularityPeriod,
                enhEthAggrPerQueueHDPeriodEndTime, enhEthAggrPerQueueHDIndex }
            ::= { enhEthAggrPerQueueHDTable 1 }

        EnhEthAggrPerQueueHDEntry ::=
            SEQUENCE {
                enhEthAggrPerQueueHDGranularityPeriod
                    OpticsIMPmGranularityPeriod,
                enhEthAggrPerQueueHDPeriodEndTime
                    OpticsIMPmPeriodTime,
                enhEthAggrPerQueueHDIndex
                    OpticsIMPmIndex,
                enhEthAggrPerQueueHDEONF
                    Counter64,
                enhEthAggrPerQueueHDEONB
                    Counter64,
                enhEthAggrPerQueueHDEONFUnicast
                    Counter64,
                enhEthAggrPerQueueHDEONFMulticast
                    Counter64,
                enhEthAggrPerQueueHDEONFBroadcast
                    Counter64,
                enhEthAggrPerQueueHDStartByOS
                    TsdimManagerType,
                enhEthAggrPerQueueHDSuspectInterval
                    OpticsIMPmSuspectIntervalFlag,
                enhEthAggrPerQueueHDElapsedTime
                    OpticsIMPmElapsedTime,
                enhEthAggrPerQueueHDTDF
                    Counter64,
                enhEthAggrPerQueueHDEONBRate
                    Counter64,
                enhEthAggrPerQueueHDEONBRatio
                    Counter64,
                enhEthAggrPerQueueHDTDFRatio
                    Counter64
             }


        enhEthAggrPerQueueHDGranularityPeriod OBJECT-TYPE
            SYNTAX OpticsIMPmGranularityPeriod
            MAX-ACCESS not-accessible
            STATUS current
            DESCRIPTION
                "See Textual Conventions"
            ::= { enhEthAggrPerQueueHDEntry 1 }

        enhEthAggrPerQueueHDPeriodEndTime OBJECT-TYPE
            SYNTAX OpticsIMPmPeriodTime
            MAX-ACCESS not-accessible
            STATUS current
            DESCRIPTION
                "See Textual Conventions"
            ::= { enhEthAggrPerQueueHDEntry 2 }

        enhEthAggrPerQueueHDIndex OBJECT-TYPE
            SYNTAX OpticsIMPmIndex
            MAX-ACCESS not-accessible
            STATUS current
            DESCRIPTION
                "See Textual Conventions"
            ::= { enhEthAggrPerQueueHDEntry 3 }

        enhEthAggrPerQueueHDEONF OBJECT-TYPE
            SYNTAX Counter64
            MAX-ACCESS read-only
            STATUS current
            DESCRIPTION
                "The number of Ethernet frames accepted by the specific queue of this Ethernet Interface."
            ::= { enhEthAggrPerQueueHDEntry 4 }

        enhEthAggrPerQueueHDEONB OBJECT-TYPE
            SYNTAX Counter64
            MAX-ACCESS read-only
            STATUS current
            DESCRIPTION
                "The number of octects of Ethernet frames accepted by the specific queue of this Ethernet Interface,
            including Ethernet header characters."
            ::= { enhEthAggrPerQueueHDEntry 5 }

        enhEthAggrPerQueueHDEONFUnicast OBJECT-TYPE
            SYNTAX Counter64
            MAX-ACCESS read-only
            STATUS current
            DESCRIPTION
                "The number of Ethernet Unicast frames accepted by the specific queue of this Ethernet Interface."
            ::= { enhEthAggrPerQueueHDEntry 6 }

        enhEthAggrPerQueueHDEONFMulticast OBJECT-TYPE
            SYNTAX Counter64
            MAX-ACCESS read-only
            STATUS current
            DESCRIPTION
                "The number of Ethernet Multicast frames accepted by the specific queue of this Ethernet Interface."
            ::= { enhEthAggrPerQueueHDEntry 7 }

        enhEthAggrPerQueueHDEONFBroadcast OBJECT-TYPE
            SYNTAX Counter64
            MAX-ACCESS read-only
            STATUS current
            DESCRIPTION
                "The number of Ethernet Broadcast frames accepted by the specific queue of this Ethernet Interface."
            ::= { enhEthAggrPerQueueHDEntry 8 }

        enhEthAggrPerQueueHDStartByOS OBJECT-TYPE
            SYNTAX TsdimManagerType
            MAX-ACCESS read-only
            STATUS current
            DESCRIPTION
                "See Textual Conventions."
            ::= { enhEthAggrPerQueueHDEntry 9 }

        enhEthAggrPerQueueHDSuspectInterval OBJECT-TYPE
            SYNTAX OpticsIMPmSuspectIntervalFlag
            MAX-ACCESS read-only
            STATUS current
            DESCRIPTION
                  "See Textual Conventions."
            ::= { enhEthAggrPerQueueHDEntry 10 }

        enhEthAggrPerQueueHDElapsedTime OBJECT-TYPE
            SYNTAX OpticsIMPmElapsedTime
            MAX-ACCESS read-only
            STATUS current
            DESCRIPTION
                       "See Textual Conventions."
            ::= { enhEthAggrPerQueueHDEntry 11 }

        enhEthAggrPerQueueHDTDF OBJECT-TYPE
            SYNTAX Counter64
            MAX-ACCESS read-only
            STATUS current
            DESCRIPTION
                "The number of Ethernet frames discarded by the specific queue due to buffer congestion."
            ::= { enhEthAggrPerQueueHDEntry 12 }

        enhEthAggrPerQueueHDEONBRate OBJECT-TYPE
            SYNTAX Counter64
            MAX-ACCESS read-only
            STATUS current
            DESCRIPTION
            "The Rate of transmitted good bytes (in Mbps) by the specific queue"
            ::= { enhEthAggrPerQueueHDEntry 13 }

        enhEthAggrPerQueueHDEONBRatio OBJECT-TYPE
            SYNTAX Counter64
            MAX-ACCESS read-only
            STATUS current
            DESCRIPTION
            "The Ratio of transmitted good bytes by the specific queue"
            ::= { enhEthAggrPerQueueHDEntry 14 }

        enhEthAggrPerQueueHDTDFRatio OBJECT-TYPE
                  SYNTAX  Counter64
                 MAX-ACCESS read-only
                 STATUS current
                 DESCRIPTION
            "The Ratio of packets dropped by the specific queue due to lack of resources"
                  ::= { enhEthAggrPerQueueHDEntry 15 }


-- Incoming ethernet ACL PM current datas table

        ethAclCDRxTable OBJECT-TYPE
            SYNTAX SEQUENCE OF EthAclCDRxEntry
            MAX-ACCESS not-accessible
            STATUS current
            DESCRIPTION
            "This table contains received ACL Current Datas counters."
            ::= { opticsIMEthPmMib 56 }

        ethAclCDRxEntry OBJECT-TYPE
            SYNTAX EthAclCDRxEntry
            MAX-ACCESS not-accessible
            STATUS current
            DESCRIPTION
            "An entry of received ACL Current Data counters table."
            INDEX { opticsIMaclIndex,opticsIMaclMacAceIndex, ethAclCDRxGranularityPeriod}
            ::= { ethAclCDRxTable 1 }

        EthAclCDRxEntry ::=
            SEQUENCE {
                ethAclCDRxGranularityPeriod
                    OpticsIMPmGranularityPeriod,
                ethAclCDRxEINF
                    Counter64,
                ethAclCDRxEINB
                    Counter64,
                ethAclCDRxStartByOS
                    TsdimManagerType,
                ethAclCDRxResetCounter
                    TruthValue,
                ethAclCDRxThresholdDataInstance
                            OpticsIMPmThresholdDataInstance,
                ethAclCDRxElapsedTime OpticsIMPmElapsedTime,
                   ethAclCDRxRowStatus    RowStatus

             }

        ethAclCDRxGranularityPeriod OBJECT-TYPE
            SYNTAX OpticsIMPmGranularityPeriod
            MAX-ACCESS not-accessible
            STATUS current
            DESCRIPTION
            "See Textual Conventions."
            ::= { ethAclCDRxEntry 1 }

        ethAclCDRxEINF OBJECT-TYPE
            SYNTAX Counter64
            MAX-ACCESS read-only
            STATUS current
            DESCRIPTION
            "The number of Ethernet frames received which is matched a specific ACL rule, the default is zero."
            ::= { ethAclCDRxEntry 2 }

        ethAclCDRxEINB OBJECT-TYPE
            SYNTAX Counter64
            MAX-ACCESS read-only
            STATUS current
            DESCRIPTION
            "The number of Ethernet bytes received which is matched a specific ACL rule, the default is zero."
            ::= { ethAclCDRxEntry 3 }

        ethAclCDRxStartByOS OBJECT-TYPE
            SYNTAX TsdimManagerType
            MAX-ACCESS read-only
            STATUS current
            DESCRIPTION
            "See Textual Conventions."
            ::= { ethAclCDRxEntry 4 }

        ethAclCDRxResetCounter OBJECT-TYPE
            SYNTAX TruthValue
            MAX-ACCESS read-create
            STATUS current
            DESCRIPTION
            "This object allows to reset i.e. set to 0, all the current counters
             for received frames."
            ::= { ethAclCDRxEntry 5  }

        ethAclCDRxThresholdDataInstance  OBJECT-TYPE
            SYNTAX  OpticsIMPmThresholdDataInstance
             MAX-ACCESS    read-create
             STATUS        current
               DESCRIPTION
                   "This is a pointer to CD ACL PM Threshold Data, the default value is the default index of ACL PM Threshold profile"
            ::= { ethAclCDRxEntry  6 }

        ethAclCDRxElapsedTime     OBJECT-TYPE
        SYNTAX OpticsIMPmElapsedTime
        MAX-ACCESS read-only
        STATUS current
        DESCRIPTION
                   "See Textual Conventions."
        ::= { ethAclCDRxEntry 7 }

        ethAclCDRxRowStatus OBJECT-TYPE
        SYNTAX RowStatus
        MAX-ACCESS read-create
        STATUS current
        DESCRIPTION
            "See Textual Conventions."
            ::= { ethAclCDRxEntry 8 }



--  Incoming ACL PM history datas table

        ethAclHDRxTable OBJECT-TYPE
            SYNTAX SEQUENCE OF EthAclHDRxEntry
            MAX-ACCESS not-accessible
            STATUS current
            DESCRIPTION
            "This table contains received ACL History Datas counters."
            ::= { opticsIMEthPmMib 57 }

        ethAclHDRxEntry OBJECT-TYPE
            SYNTAX EthAclHDRxEntry
            MAX-ACCESS not-accessible
            STATUS current
            DESCRIPTION
            "An entry of transmitted ALC History Data counters table."
            INDEX { opticsIMaclIndex,opticsIMaclMacAceIndex, ethAclHDRxGranularityPeriod,
                   ethAclHDRxPeriodEndtime, ethAclHDRxIndex }
            ::= { ethAclHDRxTable 1 }

        EthAclHDRxEntry ::=
            SEQUENCE {
                ethAclHDRxGranularityPeriod
                    OpticsIMPmGranularityPeriod,
                ethAclHDRxPeriodEndtime
                    OpticsIMPmPeriodTime,
                ethAclHDRxIndex
                    OpticsIMPmIndex,
                ethAclHDRxEINF
                    Counter64,
                ethAclHDRxEINB
                    Counter64,
                ethAclHDRxSuspectIntervalFlag
                    OpticsIMPmSuspectIntervalFlag,
                ethAclHDRxStartByOS
                    TsdimManagerType,
         ethAclHDRxElapsedTime OpticsIMPmElapsedTime
             }

        ethAclHDRxGranularityPeriod OBJECT-TYPE
            SYNTAX OpticsIMPmGranularityPeriod
            MAX-ACCESS not-accessible
            STATUS current
            DESCRIPTION
            "See Textual Conventions."
            ::= { ethAclHDRxEntry 1 }

        ethAclHDRxPeriodEndtime OBJECT-TYPE
            SYNTAX OpticsIMPmPeriodTime
            MAX-ACCESS not-accessible
            STATUS current
            DESCRIPTION
            "See Textual Conventions."
            ::= { ethAclHDRxEntry 2 }

        ethAclHDRxIndex OBJECT-TYPE
            SYNTAX OpticsIMPmIndex
            MAX-ACCESS not-accessible
            STATUS current
            DESCRIPTION
            "See Textual Conventions."
            ::= { ethAclHDRxEntry 3 }

        ethAclHDRxEINF OBJECT-TYPE
            SYNTAX Counter64
            MAX-ACCESS read-only
            STATUS current
            DESCRIPTION
            "The number of Ethernet frames received which is matched a specific ACL rule."
            ::= { ethAclHDRxEntry 4 }

        ethAclHDRxEINB OBJECT-TYPE
            SYNTAX Counter64
            MAX-ACCESS read-only
            STATUS current
            DESCRIPTION
            "The number of Ethernet bytes received which is matched a specific ACL rule"
            ::= { ethAclHDRxEntry 5 }

        ethAclHDRxSuspectIntervalFlag OBJECT-TYPE
            SYNTAX OpticsIMPmSuspectIntervalFlag
            MAX-ACCESS read-only
            STATUS current
            DESCRIPTION
            "See Textual Conventions."
            ::= { ethAclHDRxEntry 6 }

        ethAclHDRxStartByOS OBJECT-TYPE
            SYNTAX TsdimManagerType
            MAX-ACCESS read-only
            STATUS current
            DESCRIPTION
                "See Textual Conventions."
            ::= { ethAclHDRxEntry 7 }

        ethAclHDRxElapsedTime     OBJECT-TYPE
                SYNTAX OpticsIMPmElapsedTime
            MAX-ACCESS read-only
            STATUS current
            DESCRIPTION
                   "See Textual Conventions."
                ::= { ethAclHDRxEntry 8 }

-- Ethernet ACL PM     CD threshold table

ethAclCDRxThresholdIndexNext OBJECT-TYPE
      SYNTAX        Unsigned32
      MAX-ACCESS    read-only
      STATUS        current
      DESCRIPTION
         "Value to be used as the index of the threshold
         profile in order to create a new row in the table ethAclCDRxThresholdTable."
::= { opticsIMEthPmMib 58 }

ethAclCDRxThresholdTable OBJECT-TYPE
    SYNTAX        SEQUENCE OF EthAclCDRxThresholdEntry
    MAX-ACCESS    not-accessible
    STATUS        current
    DESCRIPTION
          "This table contains the high and low thresholds
           for the ACL PM CD Threshold Crossing Alert and Reset."
::= { opticsIMEthPmMib 59 }

ethAclCDRxThresholdEntry OBJECT-TYPE
      SYNTAX        EthAclCDRxThresholdEntry
      MAX-ACCESS    not-accessible
      STATUS        current
      DESCRIPTION
         "An entry (row) containing ethernet ACL PM CD  Granularity-based high and low threshold
          values."
      INDEX { ethAclCDRxThresholdIndex, ethAclCDRxThresholdGranularityPeriod}
 ::= { ethAclCDRxThresholdTable 1 }

EthAclCDRxThresholdEntry ::=
  SEQUENCE {
    ethAclCDRxThresholdIndex                        INTEGER,
    ethAclCDRxThresholdGranularityPeriod      OpticsIMPmGranularityPeriod,
    ethAclCDRxThresholdEINFEnable             TruthValue,
    ethAclCDRxThresholdEINFHighThr           Gauge32,
    ethAclCDRxThresholdEINFLowThr           Gauge32,
    ethAclCDRxThresholdEINBEnable           TruthValue,
    ethAclCDRxThresholdEINBHighThr           Gauge32,
    ethAclCDRxThresholdEINBLowThr         Gauge32,
    ethAclCDRxThresholdUserLabel                OCTET STRING,
    ethAclCDRxThresholdRowStatus               RowStatus
}

ethAclCDRxThresholdIndex OBJECT-TYPE
     SYNTAX        INTEGER
     MAX-ACCESS    not-accessible
     STATUS        current
     DESCRIPTION
         "This is the index to the Ethernet ACL PM (Granularity-based) threshold row."
 ::= { ethAclCDRxThresholdEntry 1 }

ethAclCDRxThresholdGranularityPeriod OBJECT-TYPE
     SYNTAX        OpticsIMPmGranularityPeriod
     MAX-ACCESS    not-accessible
     STATUS        current
     DESCRIPTION
         "This is the last index to the Ethernet ACL PM (Granularity-based) Threshold row -
          See Textual Convention."
 ::= { ethAclCDRxThresholdEntry 2 }

ethAclCDRxThresholdEINFEnable  OBJECT-TYPE
    SYNTAX TruthValue
    MAX-ACCESS read-create
    STATUS current
    DESCRIPTION
    "Enabled/Disabled TCA over number of Ethernet frames received which is match a specific ACL rule."
    ::= { ethAclCDRxThresholdEntry 3 }

    ethAclCDRxThresholdEINFHighThr  OBJECT-TYPE
    SYNTAX Gauge32
    MAX-ACCESS read-create
    STATUS current
    DESCRIPTION
    "This is the low Threshold for number of Ethernet frame received correctly related to current interval. Default value is NE-Product specific."
    ::= { ethAclCDRxThresholdEntry 4 }

ethAclCDRxThresholdEINFLowThr  OBJECT-TYPE
    SYNTAX Gauge32
    MAX-ACCESS read-create
    STATUS current
    DESCRIPTION
    "This is the low Threshold for number of Ethernet frame received correctly related to current interval. Default value is NE-Product specific."
    ::= { ethAclCDRxThresholdEntry 5 }


ethAclCDRxThresholdEINBEnable    OBJECT-TYPE
    SYNTAX TruthValue
    MAX-ACCESS read-create
    STATUS current
    DESCRIPTION
    "Enabled/Disabled TCA over number of Ethernet bytes received which is match a specific ACL rule."
    ::= { ethAclCDRxThresholdEntry 6 }

    ethAclCDRxThresholdEINBHighThr    OBJECT-TYPE
    SYNTAX Gauge32
    MAX-ACCESS read-create
    STATUS current
    DESCRIPTION
    "This is the low Threshold for number of Ethernet bytes received correctly related to current interval. Default value is NE-Product specific"
    ::= { ethAclCDRxThresholdEntry 7 }

ethAclCDRxThresholdEINBLowThr  OBJECT-TYPE
    SYNTAX Gauge32
    MAX-ACCESS read-create
    STATUS current
    DESCRIPTION
    "This is the low Threshold for number of Ethernet bytes received correctly related to current interval. Default value is NE-Product specific"
    ::= { ethAclCDRxThresholdEntry 8 }

ethAclCDRxThresholdUserLabel OBJECT-TYPE
     SYNTAX        OCTET STRING
     MAX-ACCESS    read-create
     STATUS        current
     DESCRIPTION
         "This is the user label used to identify the profile."
 ::= { ethAclCDRxThresholdEntry 9 }

ethAclCDRxThresholdRowStatus OBJECT-TYPE
     SYNTAX        RowStatus
     MAX-ACCESS    read-create
     STATUS        current
     DESCRIPTION
         "This is the status of the row. It can be used to
         create/destroy the row."
 ::= { ethAclCDRxThresholdEntry 10 }


-- Conformance information

opticsimEthPMMCConf         OBJECT IDENTIFIER ::= { opticsimEthMC 50 }
opticsimEthPMMCCompl        OBJECT IDENTIFIER ::= { opticsimEthPMMCConf 1 }
opticsimEthPMMCGroup        OBJECT IDENTIFIER ::= { opticsimEthPMMCConf 2 }

-- Compliance statements

ethAggrCDRxTableObjectsGroup   OBJECT-GROUP
  OBJECTS {
        ethAggrCDRxTRCF,
        ethAggrCDRxTRCO,
        ethAggrCDRxLastDiscontinuityTimeStamp,
        ethAggrCDRxStartTime,
        ethAggrCDRxStartByOS,
        ethAggrCDRxRowStatus,
        ethAggrCDRxTRCFUnicast,
        ethAggrCDRxTRCFMulticast,
        ethAggrCDRxTRCFBroadcast,
        ethAggrCDRxTDF,
        ethAggrCDRxTRSEF,
        ethAggrCDRxResetCounter
  }
  STATUS  current
  DESCRIPTION
          "Collection of objects of ethAggrCDRxTable."
  ::= { opticsimEthPMMCGroup 1 }


ethAggrHDRxTableObjectsGroup   OBJECT-GROUP
  OBJECTS {
         ethAggrHDRxTRCF,
                 ethAggrHDRxTRCO,
                 ethAggrHDRxSuspectIntervalFlag,
                 ethAggrHDRxLastDiscontinuityTimeStamp,
                 ethAggrHDRxStartByOS,
                 ethAggrHDRxTRCFUnicast,
                 ethAggrHDRxTRCFMulticast,
                 ethAggrHDRxTRCFBroadcast,
                 ethAggrHDRxTDF,
                 ethAggrHDRxTRSEF
  }
STATUS  current
  DESCRIPTION
          "Collection of objects of ethAggrHDRxTable."
  ::= { opticsimEthPMMCGroup 2 }


ethAggrCDTxTableObjectsGroup   OBJECT-GROUP
  OBJECTS {
        ethAggrCDTxTTF,
        ethAggrCDTxTTO,
        ethAggrCDTxLastDiscontinuityTimeStamp,
        ethAggrCDTxStartTime,
        ethAggrCDTxStartByOS,
        ethAggrCDTxRowStatus,
        ethAggrCDTxTTFUnicast,
        ethAggrCDTxTTFMulticast,
        ethAggrCDTxTTFBroadcast,
        ethAggrCDTxTDF,
        ethAggrCDTxResetCounter
  }
STATUS  current
  DESCRIPTION
          "Collection of objects of ethAggrCDTxTable."
  ::= { opticsimEthPMMCGroup 3 }


ethAggrHDTxTableObjectsGroup   OBJECT-GROUP
  OBJECTS {
         ethAggrHDTxTTF,
                 ethAggrHDTxTTO,
                 ethAggrHDTxSuspectIntervalFlag,
                 ethAggrHDTxLastDiscontinuityTimeStamp,
                 ethAggrHDTxStartByOS,
                 ethAggrHDTxTTFUnicast,
                 ethAggrHDTxTTFMulticast,
                 ethAggrHDTxTTFBroadcast,
                 ethAggrHDTxTDF
  }
STATUS  current
  DESCRIPTION
          "Collection of objects of ethAggrHDTxTable."
  ::= { opticsimEthPMMCGroup 4 }


etsInFlowCDTableObjectsGroup   OBJECT-GROUP
  OBJECTS {
        etsInFlowCDTRCFg,
        etsInFlowCDTRCOg,
        etsInFlowCDLastDiscontinuityTimeStamp,
        etsInFlowCDStartTime,
        etsInFlowCDStartByOS,
        etsInFlowCDRowStatus,
        etsInFlowCDTRCFy,
        etsInFlowCDTRCFr,
        etsInFlowCDTRCOy,
        etsInFlowCDTRCOr,
        etsInFlowCDResetCounter
  }
STATUS  current
  DESCRIPTION
          "Collection of objects of etsInFlowCDTable."
  ::= { opticsimEthPMMCGroup 5 }


etsInFlowHDTableObjectsGroup   OBJECT-GROUP
  OBJECTS {
        etsInFlowHDTRCFg,
        etsInFlowHDTRCOg,
        etsInFlowHDSuspectIntervalFlag,
        etsInFlowHDLastDiscontinuityTimeStamp,
        etsInFlowHDStartByOS,
        etsInFlowHDTRCFy,
        etsInFlowHDTRCFr,
        etsInFlowHDTRCOy,
        etsInFlowHDTRCOr
  }
STATUS  current
  DESCRIPTION
          "Collection of objects of etsInFlowHDTable."
  ::= { opticsimEthPMMCGroup 6 }


etsOutFlowCDTableObjectsGroup   OBJECT-GROUP
  OBJECTS {
        etsOutFlowCDTTFg,
        etsOutFlowCDTTOg,
        etsOutFlowCDLastDiscontinuityTimeStamp,
        etsOutFlowCDStartTime,
        etsOutFlowCDStartByOS,
        etsOutFlowCDRowStatus,
        etsOutFlowCDTTFy,
        etsOutFlowCDTTOy,
        etsOutFlowCDTDFg,
        etsOutFlowCDTDFy,
        etsOutFlowCDTDOg,
        etsOutFlowCDTDOy,
        etsOutFlowCDResetCounter
  }
STATUS  current
  DESCRIPTION
          "Collection of objects of etsOutFlowCDTable."
  ::= { opticsimEthPMMCGroup 7 }


etsOutFlowHDTableObjectsGroup   OBJECT-GROUP
  OBJECTS {
        etsOutFlowHDTTFg,
        etsOutFlowHDTTOg,
        etsOutFlowHDSuspectIntervalFlag,
        etsOutFlowHDLastDiscontinuityTimeStamp,
        etsOutFlowHDStartByOS,
        etsOutFlowHDTTFy,
        etsOutFlowHDTTOy,
        etsOutFlowHDTDFg,
        etsOutFlowHDTDFy,
        etsOutFlowHDTDOg,
        etsOutFlowHDTDOy
  }
STATUS  current
  DESCRIPTION
          "Collection of objects of etsOutFlowHDTable."
  ::= { opticsimEthPMMCGroup 8 }


ethAggrMaintRxTableObjectsGroup   OBJECT-GROUP
  OBJECTS {
        ethAggrMaintRxTRCO,
        ethAggrMaintRxTRCF,
        ethAggrMaintRxTRSEF,
        ethAggrMaintRxTDF,
        ethAggrMaintRxLastDiscontinuityTimeStamp,
        ethAggrMaintRxRetrievingTime,
        ethAggrMaintRxTRCFUnicast,
        ethAggrMaintRxTRCFMulticast,
        ethAggrMaintRxTRCFBroadcast,
        ethAggrMaintRxReset
  }
STATUS  current
  DESCRIPTION
          "Collection of objects of ethAggrMaintRxTable."
  ::= { opticsimEthPMMCGroup 9 }


ethAggrMaintTxTableObjectsGroup   OBJECT-GROUP
  OBJECTS {
        ethAggrMaintTxTTO,
        ethAggrMaintTxTTF,
        ethAggrMaintTxTDF,
        ethAggrMaintTxLastDiscontinuityTimeStamp,
        ethAggrMaintTxRetrievingTime,
        ethAggrMaintTxTTFUnicast,
        ethAggrMaintTxTTFMulticast,
        ethAggrMaintTxTTFBroadcast,
        ethAggrMaintTxReset
  }
STATUS  current
  DESCRIPTION
          "Collection of objects of ethAggrMaintTxTable."
  ::= { opticsimEthPMMCGroup 11 }


etsInFlowMaintTableObjectsGroup   OBJECT-GROUP
  OBJECTS {
        etsInFlowMaintTRCOg,
        etsInFlowMaintTRCFg,
        etsInFlowMaintTRCOy,
        etsInFlowMaintTRCFy,
        etsInFlowMaintTRCOr,
        etsInFlowMaintTRCFr,
        etsInFlowMaintRetrievingTime,
        etsInFlowMaintLastDiscontinuityTimeStamp
  }
STATUS  current
  DESCRIPTION
          "Collection of objects of etsInFlowMaintTable."
  ::= { opticsimEthPMMCGroup 17 }


etsOutFlowMaintTableObjectsGroup   OBJECT-GROUP
  OBJECTS {
        etsOutFlowMaintTTOg,
        etsOutFlowMaintTTFg,
        etsOutFlowMaintTDFg,
        etsOutFlowMaintTTOy,
        etsOutFlowMaintTTFy,
        etsOutFlowMaintTDFy,
        etsOutFlowMaintRetrievingTime,
        etsOutFlowMaintLastDiscontinuityTimeStamp
  }
STATUS  current
  DESCRIPTION
          "Collection of objects of etsOutFlowMaintTable."
  ::= { opticsimEthPMMCGroup 18 }


pmHistoryDataGranularityGroup   OBJECT-GROUP
  OBJECTS {
        pmHistoryDataGranularityConfiguration
  }
STATUS  current
  DESCRIPTION
          "Compliance object for pmHistoryDataGranularityConfiguration."
  ::= { opticsimEthPMMCGroup 19 }


ethAggrPerQueueCDTableObjectsGroup   OBJECT-GROUP
  OBJECTS {
        ethAggrPerQueueCDTCF,
        ethAggrPerQueueCDTnCF,
        ethAggrPerQueueCDDiscardTCF,
        ethAggrPerQueueCDDiscardTnCF,
        ethAggrPerQueueCDTCO,
        ethAggrPerQueueCDTnCO,
        ethAggrPerQueueCDDiscardTCO,
        ethAggrPerQueueCDDiscardTnCO,
        ethAggrPerQueueCDLastDiscontinuityTimeStamp,
        ethAggrPerQueueCDStartTime,
        ethAggrPerQueueCDStartByOS,
        ethAggrPerQueueCDRowStatus,
        ethAggrPerQueueCDResetCounter
  }
STATUS  current
  DESCRIPTION
          "Collection of objects of ethAggrPerQueueCDTable."
  ::= { opticsimEthPMMCGroup 31 }


ethAggrPerQueueHDTableObjectsGroup   OBJECT-GROUP
  OBJECTS {
        ethAggrPerQueueHDTCF,
        ethAggrPerQueueHDTnCF,
        ethAggrPerQueueHDDiscardTCF,
        ethAggrPerQueueHDDiscardTnCF,
        ethAggrPerQueueHDTCO,
        ethAggrPerQueueHDTnCO,
        ethAggrPerQueueHDDiscardTCO,
        ethAggrPerQueueHDDiscardTnCO,
        ethAggrPerQueueHDSuspectIntervalFlag,
        ethAggrPerQueueHDLastDiscontinuityTimeStamp,
        ethAggrPerQueueHDStartByOS
  }
STATUS  current
  DESCRIPTION
          "Collection of objects of ethAggrPerQueueHDTable."
  ::= { opticsimEthPMMCGroup 32 }


ethAggrPerQueueMaintTableObjectsGroup   OBJECT-GROUP
  OBJECTS {
        ethAggrPerQueueMaintTCF,
        ethAggrPerQueueMaintTnCF,
        ethAggrPerQueueMaintDiscardTCF,
        ethAggrPerQueueMaintDiscardTnCF,
        ethAggrPerQueueMaintTCO,
        ethAggrPerQueueMaintTnCO,
        ethAggrPerQueueMaintDiscardTCO,
        ethAggrPerQueueMaintDiscardTnCO,
        ethAggrPerQueueMaintLastDiscontinuityTimeStamp,
        ethAggrPerQueueMaintRetrievingTime
  }
STATUS  current
  DESCRIPTION
          "Collection of objects of ethAggrPerQueueMaintTable."
  ::= { opticsimEthPMMCGroup 39 }


enhEthAggrCDRxTableObjectsGroup   OBJECT-GROUP
  OBJECTS {
        enhEthAggrCDRxEINF,
        enhEthAggrCDRxEINB,
        enhEthAggrCDRxEINFUnicast,
        enhEthAggrCDRxEINFMulticast,
        enhEthAggrCDRxEINFBroadcast,
        enhEthAggrCDRxEIFE,
        enhEthAggrCDRxTUF,
        enhEthAggrCDRxTDF,
        enhEthAggrCDRxStartByOS,
        enhEthAggrCDRxResetCounter,
        enhEthAggrCDRxRowStatus,
        enhEthAggrCDRxSuspectInterval,
        enhEthAggrCDRxElapsedTime,
        enhEthAggrCDRxThresholdDataInstance
  }
STATUS  current
  DESCRIPTION
          "Collection of objects of enhEthAggrCDRxTable."
  ::= { opticsimEthPMMCGroup 40 }


enhEthAggrHDRxTableObjectsGroup   OBJECT-GROUP
  OBJECTS {
        enhEthAggrHDRxEINF,
        enhEthAggrHDRxEINB,
        enhEthAggrHDRxSuspectIntervalFlag,
        enhEthAggrHDRxStartByOS,
        enhEthAggrHDRxEINFUnicast,
        enhEthAggrHDRxEINFMulticast,
        enhEthAggrHDRxEINFBroadcast,
        enhEthAggrHDRxEIFE,
        enhEthAggrHDRxTUF,
        enhEthAggrHDRxTDF,
        enhEthAggrHDRxElapsedTime
  }
STATUS  current
  DESCRIPTION
          "Collection of objects of enhEthAggrHDRxTable."
  ::= { opticsimEthPMMCGroup 41 }


enhEthAggrCDTxTableObjectsGroup   OBJECT-GROUP
  OBJECTS {
        enhEthAggrCDTxEONF,
        enhEthAggrCDTxEONB,
        enhEthAggrCDTxEONFUnicast,
        enhEthAggrCDTxEONFMulticast,
        enhEthAggrCDTxEONFBroadcast,
        enhEthAggrCDTxStartByOS,
        enhEthAggrCDTxResetCounter,
        enhEthAggrCDTxRowStatus,
        enhEthAggrCDTxSuspectInterval,
        enhEthAggrCDTxElapsedTime,
        enhEthAggrCDTxTDF,
        enhEthAggrCDTxThresholdDataInstance
  }
STATUS  current
  DESCRIPTION
          "Collection of objects of enhEthAggrCDTxTable."
  ::= { opticsimEthPMMCGroup 42 }


enhEthAggrHDTxTableObjectsGroup   OBJECT-GROUP
  OBJECTS {
        enhEthAggrHDTxEONF,
        enhEthAggrHDTxEONB,
        enhEthAggrHDTxSuspectIntervalFlag,
        enhEthAggrHDTxStartByOS,
        enhEthAggrHDTxEONFUnicast,
        enhEthAggrHDTxEONFMulticast,
        enhEthAggrHDTxEONFBroadcast,
        enhEthAggrHDTxElapsedTime,
        enhEthAggrHDTxTDF
  }
STATUS  current
  DESCRIPTION
          "Collection of objects of enhEthAggrHDTxTable."
  ::= { opticsimEthPMMCGroup 43 }


enhEtsInFlowCDTableObjectsGroup   OBJECT-GROUP
  OBJECTS {
        enhEtsInFlowCDEINFg,
        enhEtsInFlowCDEINBg,
                enhEtsInFlowCDStartByOS,
        enhEtsInFlowCDEINFy,
        enhEtsInFlowCDEINFr,
        enhEtsInFlowCDEINBy,
        enhEtsInFlowCDEINBr,
                enhEtsInFlowCDResetCounter,
        enhEtsInFlowCDRowStatus
  }
STATUS  current
  DESCRIPTION
          "Collection of objects of enhEtsInFlowCDTable."
  ::= { opticsimEthPMMCGroup 44 }


enhEtsInFlowHDTableObjectsGroup   OBJECT-GROUP
  OBJECTS {
        enhEtsInFlowHDEINFg,
        enhEtsInFlowHDEINBg,
        enhEtsInFlowHDSuspectIntervalFlag,
        enhEtsInFlowHDStartByOS,
        enhEtsInFlowHDEINFy,
        enhEtsInFlowHDEINFr,
        enhEtsInFlowHDEINBy,
        enhEtsInFlowHDEINBr
  }
STATUS  current
  DESCRIPTION
          "Collection of objects of enhEtsInFlowHDTable."
  ::= { opticsimEthPMMCGroup 45 }


enhEtsOutFlowCDTableObjectsGroup   OBJECT-GROUP
  OBJECTS {
        enhEtsOutFlowCDEONFg,
        enhEtsOutFlowCDEONBg,
        enhEtsOutFlowCDStartByOS,
        enhEtsOutFlowCDEONFy,
        enhEtsOutFlowCDEONBy,
        enhEtsOutFlowCDResetCounter,
        enhEtsOutFlowCDRowStatus,
        enhEtsOutFlowCDThresholdDataInstance
  }
STATUS  current
  DESCRIPTION
          "Collection of objects of enhEtsOutFlowCDTable."
  ::= { opticsimEthPMMCGroup 46 }


enhEtsOutFlowHDTableObjectsGroup   OBJECT-GROUP
  OBJECTS {
        enhEtsOutFlowHDEONFg,
        enhEtsOutFlowHDEONBg,
        enhEtsOutFlowHDSuspectIntervalFlag,
        enhEtsOutFlowHDStartByOS,
        enhEtsOutFlowHDEONFy,
        enhEtsOutFlowHDEONBy
  }
STATUS  current
  DESCRIPTION
          "Collection of objects of enhEtsOutFlowHDTable."
  ::= { opticsimEthPMMCGroup 47 }


enhEthAggrMaintRxTableObjectsGroup   OBJECT-GROUP
  OBJECTS {
        enhEthAggrMaintRxEINB,
        enhEthAggrMaintRxEINF,
        enhEthAggrMaintRxEIFE,
        enhEthAggrMaintRxTDF,
        enhEthAggrMaintRxLastDiscontinuityTimeStamp,
        enhEthAggrMaintRxRetrievingTime,
        enhEthAggrMaintRxTRCFUnicast,
        enhEthAggrMaintRxTRCFMulticast,
        enhEthAggrMaintRxTRCFBroadcast,
        enhEthAggrMaintRxReset
  }
STATUS  current
  DESCRIPTION
          "Collection of objects of enhEthAggrMaintRxTable."
  ::= { opticsimEthPMMCGroup 48 }


enhEthAggrMaintTxTableObjectsGroup   OBJECT-GROUP
  OBJECTS {
        enhEthAggrMaintTxEONB,
        enhEthAggrMaintTxEONF,
        enhEthAggrMaintTxTDF,
        enhEthAggrMaintTxLastDiscontinuityTimeStamp,
        enhEthAggrMaintTxRetrievingTime,
        enhEthAggrMaintTxEONFUnicast,
        enhEthAggrMaintTxEONFMulticast,
        enhEthAggrMaintTxEONFBroadcast,
        enhEthAggrMaintTxReset
  }
STATUS  current
  DESCRIPTION
          "Collection of objects of enhEthAggrMaintTxTable."
  ::= { opticsimEthPMMCGroup 49 }


enhEthAggrCDThresholdTableObjectsGroup   OBJECT-GROUP
  OBJECTS {
    enhEthAggrCDThresholdRxEINFEnable,
    enhEthAggrCDThresholdRxEINFHighThr ,
    enhEthAggrCDThresholdRxEINFLowThr ,
    enhEthAggrCDThresholdRxEINBEnable ,
    enhEthAggrCDThresholdRxEINBHighThr ,
    enhEthAggrCDThresholdRxEINBLowThr ,
    enhEthAggrCDThresholdRxEINFUnicastEnable ,
    enhEthAggrCDThresholdRxEINFUnicastHighThr ,
    enhEthAggrCDThresholdRxEINFUnicastLowThr ,
    enhEthAggrCDThresholdRxEINFMulticastEnable ,
    enhEthAggrCDThresholdRxEINFMulticastHighThr ,
    enhEthAggrCDThresholdRxEINFMulticastLowThr ,
    enhEthAggrCDThresholdRxEINFBroadcastEnable ,
    enhEthAggrCDThresholdRxEINFBroadcastHighThr ,
    enhEthAggrCDThresholdRxEINFBroadcastLowThr ,
    enhEthAggrCDThresholdRxEIFEEnable ,
    enhEthAggrCDThresholdRxEIFEHighThr ,
    enhEthAggrCDThresholdRxEIFELowThr ,
    enhEthAggrCDThresholdRxTUFEnable ,
    enhEthAggrCDThresholdRxTUFHighThr ,
    enhEthAggrCDThresholdRxTUFLowThr ,
    enhEthAggrCDThresholdRxTDFEnable ,
    enhEthAggrCDThresholdRxTDFHighThr ,
    enhEthAggrCDThresholdRxTDFLowThr ,
    enhEthAggrCDThresholdTxEONFEnable ,
    enhEthAggrCDThresholdTxEONFHighThr ,
    enhEthAggrCDThresholdTxEONFLowThr ,
    enhEthAggrCDThresholdTxEONBEnable ,
    enhEthAggrCDThresholdTxEONBHighThr ,
    enhEthAggrCDThresholdTxEONBLowThr ,
    enhEthAggrCDThresholdTxEONFUnicastEnable ,
    enhEthAggrCDThresholdTxEONFUnicastHighThr ,
    enhEthAggrCDThresholdTxEONFUnicastLowThr ,
    enhEthAggrCDThresholdTxEONFMulticastEnable ,
    enhEthAggrCDThresholdTxEONFMulticastHighThr ,
    enhEthAggrCDThresholdTxEONFMulticastLowThr ,
    enhEthAggrCDThresholdTxEONFBroadcastEnable ,
    enhEthAggrCDThresholdTxEONFBroadcastHighThr ,
    enhEthAggrCDThresholdTxEONFBroadcastLowThr ,
    enhEthAggrCDThresholdTxTDFEnable ,
    enhEthAggrCDThresholdTxTDFHighThr ,
    enhEthAggrCDThresholdTxTDFLowThr ,
    enhEthAggrCDThresholdUserLabel ,
    enhEthAggrCDThresholdRowStatus
  }
STATUS  current
  DESCRIPTION
          "Collection of objects of enhEthAggrCDThresholdTable."
  ::= { opticsimEthPMMCGroup 50 }

enhEtsFlowCDThresholdTableObjectsGroup   OBJECT-GROUP
  OBJECTS {
    enhEtsFlowCDThresholdEINFgEnable ,
    enhEtsFlowCDThresholdEINFgHighThr ,
    enhEtsFlowCDThresholdEINFgLowThr ,
    enhEtsFlowCDThresholdEINBgEnable   ,
    enhEtsFlowCDThresholdEINBgHighThr  ,
    enhEtsFlowCDThresholdEINBgLowThr ,
    enhEtsFlowCDThresholdEINFyEnable ,
    enhEtsFlowCDThresholdEINFyHighThr,
    enhEtsFlowCDThresholdEINFyLowThr,
    enhEtsFlowCDThresholdEINFrEnable,
    enhEtsFlowCDThresholdEINFrHighThr,
    enhEtsFlowCDThresholdEINFrLowThr,
    enhEtsFlowCDThresholdEINByEnable,
    enhEtsFlowCDThresholdEINByHighThr,
    enhEtsFlowCDThresholdEINByLowThr,
    enhEtsFlowCDThresholdEINBrEnable,
    enhEtsFlowCDThresholdEINBrHighThr,
    enhEtsFlowCDThresholdEINBrLowThr,
    enhEtsFlowCDThresholdEONFgEnable,
    enhEtsFlowCDThresholdEONFgHighThr,
    enhEtsFlowCDThresholdEONFgLowThr,
    enhEtsFlowCDThresholdEONBgEnable,
    enhEtsFlowCDThresholdEONBgHighThr,
    enhEtsFlowCDThresholdEONBgLowThr,
    enhEtsFlowCDThresholdEONFyEnable,
    enhEtsFlowCDThresholdEONFyHighThr,
    enhEtsFlowCDThresholdEONFyLowThr,
    enhEtsFlowCDThresholdEONByEnable,
    enhEtsFlowCDThresholdEONByHighThr,
    enhEtsFlowCDThresholdEONByLowThr,
    enhEtsFlowCDThresholdUserLabel,
    enhEtsFlowCDThresholdRowStatus
 }
 STATUS  current
  DESCRIPTION
          "Collection of objects of enhEtsFlowCDThresholdTable."
  ::= { opticsimEthPMMCGroup 51 }

ethAclCDRxTableObjectsGroup   OBJECT-GROUP
  OBJECTS {
        ethAclCDRxEINF,
        ethAclCDRxEINB,
        ethAclCDRxStartByOS,
        ethAclCDRxResetCounter,
        ethAclCDRxThresholdDataInstance,
        ethAclCDRxElapsedTime,
        ethAclCDRxRowStatus
  }
STATUS  current
  DESCRIPTION
          "Collection of objects of ethAclCDRxTable"
  ::= { opticsimEthPMMCGroup 52 }


ethAclHDRxTableObjectsGroup   OBJECT-GROUP
  OBJECTS {
        ethAclHDRxEINF,
        ethAclHDRxEINB,
        ethAclHDRxSuspectIntervalFlag,
        ethAclHDRxStartByOS,
        ethAclHDRxElapsedTime
  }
STATUS  current
  DESCRIPTION
          "Collection of objects of ethAclHDRxTable."
  ::= { opticsimEthPMMCGroup 53 }

ethAclCDRxThresholdTableObjectsGroup   OBJECT-GROUP
  OBJECTS {
        ethAclCDRxThresholdEINFEnable,
        ethAclCDRxThresholdEINFHighThr,
        ethAclCDRxThresholdEINFLowThr,
        ethAclCDRxThresholdEINBEnable,
        ethAclCDRxThresholdEINBHighThr,
        ethAclCDRxThresholdEINBLowThr,
        ethAclCDRxThresholdUserLabel,
        ethAclCDRxThresholdRowStatus
 }
 STATUS  current
  DESCRIPTION
          "Collection of objects of ethAclCDRxThresholdTable."
  ::= { opticsimEthPMMCGroup 54 }

 END


--
-- OPTICSIM-ETHPM-MIB.my
--
